module TIMETRA-PORT-MIB {
  namespace "urn:ietf:params:xml:ns:yang:smiv2:TIMETRA-PORT-MIB";
  prefix timetra-port;

  import ATM-TC-MIB {
    prefix atm-tc;
  }
  import SNMP-FRAMEWORK-MIB {
    prefix snmp-framework;
  }
  import SNMPv2-TC {
    prefix snmpv2-tc;
  }
  import TIMETRA-CHASSIS-MIB {
    prefix timetra-chassis;
  }
  import TIMETRA-TC-MIB {
    prefix timetra-tc;
  }
  import ietf-inet-types {
    prefix inet;
  }
  import ietf-yang-smiv2 {
    prefix smiv2;
  }
  import ietf-yang-types {
    prefix yang;
  }

  organization "Alcatel-Lucent";
  contact
    "Alcatel-Lucent SROS Support
     Web: http://support.alcatel-lucent.com";
  description
    "This document is the SNMP MIB module to manage and provision the
     hardware components of the Alcatel-Lucent SROS device.
     
     Copyright 2003-2013 Alcatel-Lucent.  All rights reserved.
     Reproduction of this document is authorized on the condition that
     the foregoing copyright notice is included.
     
     This SNMP MIB module (Specification) embodies Alcatel-Lucent's
     proprietary intellectual property.  Alcatel-Lucent retains
     all title and ownership in the Specification, including any
     revisions.
     
     Alcatel-Lucent grants all interested parties a non-exclusive
     license to use and distribute an unmodified copy of this
     Specification in connection with management of Alcatel-Lucent
     products, and without fee, provided this copyright notice and
     license appear on all copies.
     
     This Specification is supplied 'as is', and Alcatel-Lucent
     makes no warranty, either express or implied, as to the use,
     operation, condition, or performance of the Specification.";

  revision 2011-02-01 {
    description
      "[Revision added by libsmi due to a LAST-UPDATED clause.]";
  }
  revision 1911-02-01 {
    description
      "Rev 9.0                 1 Feb 2011 00:00
       9.0 release of the TIMETRA-PORT-MIB.";
  }
  revision 1909-02-28 {
    description
      "Rev 7.0                28 Feb 2009 00:00
       7.0 release of the TIMETRA-PORT-MIB.";
  }
  revision 1908-07-01 {
    description
      "Rev 6.1                01 Jul 2008 00:00
       6.1 release of the TIMETRA-PORT-MIB.";
  }
  revision 1908-01-01 {
    description
      "Rev 6.0                01 Jan 2008 00:00
       6.0 release of the TIMETRA-PORT-MIB.";
  }
  revision 1907-01-01 {
    description
      "Rev 5.0                01 Jan 2007 00:00
       5.0 release of the TIMETRA-PORT-MIB.";
  }
  revision 1906-03-16 {
    description
      "Rev 4.0                16 Mar 2006 00:00
       4.0 release of the TIMETRA-PORT-MIB.";
  }
  revision 1905-08-31 {
    description
      "Rev 3.0                31 Aug 2005 00:00
       3.0 release of the TIMETRA-PORT-MIB.";
  }
  revision 1905-01-24 {
    description
      "Rev 2.1                24 Jan 2005 00:00
       2.1 release of the TIMETRA-PORT-MIB.";
  }
  revision 1904-03-01 {
    description
      "Rev 2.0                01 Mar 2004 00:00
       2.0 release of the TIMETRA-PORT-MIB.";
  }

  typedef TmnxPortOperStatus {
    type enumeration {
      enum "unknown" {
        value 1;
      }
      enum "inService" {
        value 2;
      }
      enum "outOfService" {
        value 3;
      }
      enum "diagnosing" {
        value 4;
      }
      enum "failed" {
        value 5;
      }
    }
    description
      "The current operational status of this port.";
  }

  typedef TmnxPortEtherReportValue {
    type enumeration {
      enum "notUsed" {
        value 0;
      }
      enum "signalFailure" {
        value 1;
      }
      enum "remoteFault" {
        value 2;
      }
      enum "localFault" {
        value 3;
      }
      enum "noFrameLock" {
        value 4;
      }
      enum "highBer" {
        value 5;
      }
      enum "noBlockLock" {
        value 6;
      }
      enum "noAmLock" {
        value 7;
      }
      enum "duplicateLane" {
        value 8;
      }
    }
    description
      "The TmnxPortEtherReportValue is an enumerated integer that describes
       the values used to identify the reason an alarm has been raised on an
       Ethernet Port.";
  }

  typedef TmnxPortEtherReportStatus {
    type bits {
      bit notUsed {
        position 0;
      }
      bit signalFailure {
        position 1;
      }
      bit remoteFault {
        position 2;
      }
      bit localFault {
        position 3;
      }
      bit noFrameLock {
        position 4;
      }
      bit highBer {
        position 5;
      }
      bit noBlockLock {
        position 6;
      }
      bit noAmLock {
        position 7;
      }
      bit duplicateLane {
        position 8;
      }
    }
    description
      "The TmnxPortEtherReportStatus is a bitmask that describes alarms that
       can be raised/cleared on an Ethernet Port.";
  }

  typedef TmnxPortEtherCrcMonReportValue {
    type enumeration {
      enum "noFault" {
        value 0;
      }
      enum "sdThresholdExceeded" {
        value 1;
      }
      enum "sfThresholdExceeded" {
        value 2;
      }
    }
    description
      "The TmnxPortEtherCrcMonReportValue is an enumerated integer that
       describes the values used to identify the reason an alarm has been
       raised for a fault in CRC Monitoring on an Ethernet Port.
       
       TmnxPortEtherCrcMonReportStatus defines the valid alarm values.";
  }

  typedef TmnxPortEtherCrcMonReportStatus {
    type bits {
      bit sdThresholdExceeded {
        position 0;
      }
      bit sfThresholdExceeded {
        position 1;
      }
    }
    description
      "The TmnxPortEtherCrcMonReportStatus is a bitmask that describes alarms
       that can be raised/cleared on an Ethernet Port used in CRC Monitoring.
       
       The possible values are:
          sdThresholdExceeded (0)-- Signal Degradation exceeded the threshold.
          sfThresholdExceeded (1)-- Signal Failure exceeded the threshold.";
  }

  typedef TmnxPortEtherOperPhyTxClock {
    type enumeration {
      enum "notApplicable" {
        value 0;
      }
      enum "master" {
        value 1;
      }
      enum "slave" {
        value 2;
      }
    }
    description
      "The TmnxPortEtherOperPhyTxClock data type is an enumerated integer that
       indicates the result of the master/slave resolution on copper based
       Ethernet ports running at 1 Gbps.
       
       - The value of 'notApplicable' indicates that this object is not
         applicable to this port.
       - The value of 'master' indicates that the port is the timing master
         for the link partner.
       - The value of 'slave' indicates that the port is timing slave 
         to the link partner.";
  }

  typedef TmnxPortClass {
    type enumeration {
      enum "none" {
        value 1;
      }
      enum "faste" {
        value 2;
      }
      enum "gige" {
        value 3;
      }
      enum "xgige" {
        value 4;
      }
      enum "sonet" {
        value 5;
      }
      enum "vport" {
        value 6;
      }
      enum "unused" {
        value 7;
      }
      enum "xcme" {
        value 8;
      }
      enum "tdm" {
        value 9;
      }
      enum "xlgige" {
        value 10;
      }
      enum "cgige" {
        value 11;
      }
      enum "vsme" {
        value 12;
      }
    }
    description
      "The TmnxPortClass data type is an enumerated integer that
       describes the values used to identify the class of interface
       provided by this port.";
  }

  typedef TmnxPortConnectorType {
    type uint32;
    description
      "The TmnxPortConnectorType data type is an enumerated integer that
       describes the values used to identify the connector type used on
       a port.  A TmnxPortConnectorType value specifies the index value
       for the entry in the tmnxPortConnectTypeTable used to identify a
       specific type of port connector.  Some example port connector types
       are: 'unknown', 'rj45', 'bncCoax', 'mtrj', 'scDuplex', 'sffp',
       'lcDuplex'.";
  }

  typedef TmnxPortState {
    type enumeration {
      enum "none" {
        value 1;
      }
      enum "ghost" {
        value 2;
      }
      enum "linkDown" {
        value 3;
      }
      enum "linkUp" {
        value 4;
      }
      enum "up" {
        value 5;
      }
      enum "diagnose" {
        value 6;
      }
    }
    description
      "The state level of this port.  A value of 'none' indicates the
       port is either in its initial creation state or is just about to
       be deleted.  A value of 'ghost' represents a port that is not
       physically present.  This state may represent a pre-provisioned
       port.  A value of 'linkDown' represents a port that is physically
       present but does not have a link.  The 'linkUp' state represents a
       port that is physically present and has physical link present.
       A port in 'up' state is ready to pass some kinds of traffic.
       The tmnxPortUpProtocols variable indicates the actual type(s) of
       traffic that can be passed on this 'up' link. The 'diagnose' state
       represents the port undergoing diagnostic test.";
  }

  typedef TmnxPortType {
    type uint32;
    description
      "The TmnxPortType data type is an enumerated integer that describes
       the values used to identify the specific type of hardware port.
       A TmnxPortType value specifies the index value for the entry in the
       tmnxPortTypeTable used to identify a specific type of port.
       Some example port types are:
          -- unknown            - no port installed or unidentified
          -- portType100Tx      - 10/100 base copper
          -- portType100F       - 10/100 base fiber
          -- portType1000Tx     - 1000 base copper
          -- portType1000F      - 1000 base fiber
          -- portType1000dF     - 1000 base dual fiber
          -- portTypeOC3sonet   - OC-3
          -- portTypeOC12sonet  - OC-12
          -- portTypeOC48sonet  - OC-48
          -- portTypeOC192sonet - OC-192
          -- portType10000F     - 10 Gig Ethernet LAN
          -- portTypeXgigWan    - 10 Gig Ethernet WAN
          -- portTypeVport      - Virtual port
          -- portTypeDS3E3      - DS3/E3 port
          -- portTypeDS1E1      - DS1/E1 port
          -- portTypeXcmeTx     - 10/100/1000 base copper";
  }

  typedef TmnxPortEncapType {
    type enumeration {
      enum "unknown" {
        value 0;
      }
      enum "nullEncap" {
        value 1;
      }
      enum "qEncap" {
        value 2;
      }
      enum "mplsEncap" {
        value 3;
      }
      enum "bcpNullEncap" {
        value 4;
      }
      enum "bcpDot1qEncap" {
        value 5;
      }
      enum "ipcpEncap" {
        value 6;
      }
      enum "frEncap" {
        value 7;
      }
      enum "pppAutoEncap" {
        value 8;
      }
      enum "atmEncap" {
        value 9;
      }
      enum "qinqEncap" {
        value 10;
      }
      enum "wanMirrorEncap" {
        value 11;
      }
      enum "ciscoHDLCEncap" {
        value 12;
      }
      enum "cemEncap" {
        value 13;
      }
    }
    description
      "The type of encapsulation protocol configured on a
       port's network interface.
       
       When the encap type has a value of 'nullEncap', 
       frames received will not carry any tags
       or labels and as a result only one service can be
       configured on this port.  Sometimes this is referred to
       as raw Ethernet packets.
       
       When the encap type has a value of 'qEncap', ingress frames
       carry 802.1q tags where each different tag can signify a
       different service. This is not a valid value if
       tmnxPortClass has a value of 'sonetPath'.
       
       When the encap type has a value of 'bcpNullEncap',
       BCP is used on the SONET path as the NCP control protocol.
       The BCP IEEE 802 Tagged Frame Configuration Option (type 8)
       is negotiated to 'enabled'.  VLAN tagged frames are
       allowed into the SONET path.  Only a single SAP can
       be associated with the SONET path.  'bcpNullEncap' is
       valid only if tmnxPortClass has a value of 'sonetPath'.
       
       When the encap type has a value of 'bcpDot1qEncap',
       BCP is used as the NCP control protocol.  The BCP IEEE 802
       Tagged Frame Configuration Option (type 8) is negotiated to
       'enabled'.  VLAN tagged frames are allowed on the SONET path.
       This encapsulation type is required when multiple SAPs are
       defined on the SONET path where each one is service
       delimited by a provisioned Dot1q tag.  When 'bcpDot1qEncap'
       is specified, BCP does not enter the 'open' state unless
       the far end peer also supports 'bcpDot1qEncap'.  This allows
       a LCP negotiation to transmit configuration request and
       confirmation messages to enable this feature.  'bcpDot1qEncap'
       is a valid value only if tmnxPortClass has a value of 'SONET'.
       
       When the encap type has a value of 'ipcpEncap',
       BCP will not be used on this SONET path.  IPCP NCP is used
       instead.  'ipcpEncap' is a valid only if tmnxPortClass has
       a value of 'sonetPath'.
       
       When the encap type has a value of 'frEncap', Frame Relay is
       the expected encapsulation.
       
       When the encap type has a value of 'pppAutoEncap', IPCP is
       automatically enabled. This encap type is only valid on
       ports/paths in network mode.
       
       When the encap type has a value of 'atmEncap', the encapsulation
       on the port is ATM. The 'atmEncap' is also used when mirroring
       ATM ports.
       
       When the encap type has a value of 'wanMirrorEncap', the
       port is used for mirroring of frame-relay and POS ports. On such
       ports no link management protocol would run.
       
       When the encap type has a value of 'ciscoHDLCEncap', the Cisco HDLC
       encapsulation is applied. This encap type is only valid if
       TmnxPortClass has a value of 'tdm' or 'sonet'.
       
       When the encap type has a value of 'cemEncap', encapsulation of
       frames will be circuit emulation.  This is used to support transparent
       transmission of frames.  This encap type is only valid
       if TmnxPortClass has a value of 'tdm' or 'sonet' in access mode.";
  }

  typedef TmnxDs0ChannelList {
    type binary {
      length "0..4";
    }
    description
      "A list of ds0 timeslots on a DS1 line.
       
       The list is specified as an OCTET STRING in which each ds0
       timeslot is represented by a single bit, where  timeslots 1
       through 8 are represented by the bits in the first octet,
       timeslots 9 through 16 by the bits in the second octet,
       etc.  In each octet, the lowest numbered timeslot is
       represented by the most significant bit, and the highest
       numbered timeslot by the least significant bit.  A timeslot
       is present in the list when its bit is 1, and absent
       when its bit is 0.
       
       If the OCTET STRING value has more bits than required to
       represent the timeslots on a DS1, then the extra bits
       are ignored.";
  }

  typedef TmnxBundleID {
    type uint32;
    description
      "A TmnxBundleID is an unique 32 bit number encoded as shown below.
       
       |32 30| 29 26 | 25 22 | 21 16 | 15     13 | 12   1|
       +-----+-------+-------+-------+-----------+-------+
       |001  |  slot |  mda  |   0   | bndl type | bndlid|
       +-----+-------+-------+-------+-----------+-------+
       
       The bundle id is unique for a MDA.  The bndlid must fall in one of
       the following ranges depending on MDA type:
       
       mda-type             range
       m4-choc3-as-sfp      1-256
       m1-choc12-as-sfp     1-256
       m12-chds3-as         1-256
       m4-chds3-as          1-112
       m4-chds3             1-56
       m12-chds3            1-56
       m1-choc12-sfp        1-56
       m4-choc3-sfp         1-56
       c8-chds1             1-56
       c8-atmds1            1-8
       
       A slot value of 15 (Invalid slot) and mda value of 0 (invalid mda)
       represents a bundle protection group.
       Otherwise, the bundle is considered associated with a valid slot
       and mda.
       
       The following bundle types are supported:
       
       bndl type     value
       MLPPP        000
       IMA          001
       MLFR         010";
  }

  typedef TmnxDSXBertPattern {
    type enumeration {
      enum "none" {
        value 0;
      }
      enum "ones" {
        value 1;
      }
      enum "zeros" {
        value 2;
      }
      enum "alternating" {
        value 3;
      }
      enum "twoexp3" {
        value 4;
      }
      enum "twoexp9" {
        value 5;
      }
      enum "twoexp15" {
        value 6;
      }
      enum "twoexp20" {
        value 7;
      }
      enum "twoexp11" {
        value 8;
      }
      enum "twoexp20q" {
        value 9;
      }
      enum "twoexp23" {
        value 10;
      }
    }
    description
      "The TmnxDSXBertPattern data type is an enumerated integer that
       indicates the pattern used for the Bit Error Rate Test (BERT).";
  }

  typedef TmnxDSXBertOperStatus {
    type enumeration {
      enum "none" {
        value 0;
      }
      enum "active" {
        value 1;
      }
      enum "idle" {
        value 2;
      }
      enum "noMdaResources" {
        value 3;
      }
    }
    description
      "The TmnxDSXBertOperStatus data type is an enumerated integer that
       indicates the status of Bit Error Rate Test (BERT).
       When BERT is activated, the status will be 'active'. Otherwise
       the status will be 'idle' or 'noMdaResources' if the last BERT test
       could not be executed because of an MDA concurrent BERT test limit.";
  }

  typedef TmnxDSXIdleCycleFlags {
    type enumeration {
      enum "none" {
        value 0;
      }
      enum "flags" {
        value 1;
      }
      enum "ones" {
        value 2;
      }
    }
    description
      "The TmnxDSXIdleCycleFlags data type is an enumerated integer that
       indicates the value that the DS3/DS1 port/channel or a DS0 channel
       group transmits during idle cycle.
       
       The value of 'none' is applicable to ATM and CEM ports/channels only,
       which transmit idle cells and not octets defined by the below values.
       
       If the value is set to 'flags', a value of 0x7E is used.
       If the value is set to 'ones', a value of 0xFF is used.";
  }

  typedef TmnxDSXIdleFillType {
    type enumeration {
      enum "notApplicable" {
        value 0;
      }
      enum "allOnes" {
        value 1;
      }
      enum "userDefinedPattern" {
        value 2;
      }
    }
    description
      "The TmnxDSXIdleFillType data type is an enumerated integer that
       indicates the type of data fill that a CEM DS3/DS1 channel or a DS0
       channel group plays out when the channel experiences underun.
       
       - The value of 'notApplicable' indicates that this object is not
         applicable to the channel.
       - The value of 'allOnes' indicates that all 1's will be played out.
       - The value of 'userDefinedPattern' indicates that a user defined
         pattern will be played out.";
  }

  typedef TmnxDSXLoopback {
    type enumeration {
      enum "none" {
        value 0;
      }
      enum "line" {
        value 1;
      }
      enum "internal" {
        value 2;
      }
      enum "remote" {
        value 3;
      }
    }
    status obsolete;
    description
      "The TmnxDSXLoopback data type is an enumerated integer that
       indicates the type of loopback the DS3/DS1 port/channel
       currently is in.";
  }

  typedef TmnxDSXReportAlarm {
    type bits {
      bit notUsed {
        position 0;
      }
      bit ais {
        position 1;
      }
      bit los {
        position 2;
      }
      bit oof {
        position 3;
      }
      bit rai {
        position 4;
      }
      bit looped {
        position 5;
      }
      bit berSd {
        position 6;
      }
      bit berSf {
        position 7;
      }
    }
    description
      "The TmnxDSXReportAlarm data type indicates the type of TDM alarm:
       ais - alarm indication signal errors.
       los - loss of signal errors.
       oof - out-of-frame errors.
       rai - resource availability indicator events.
       looped - far end wants the read end to loopback
       berSd - DSX bit error signal degradation
       berSf - DSX bit error signal failure";
  }

  typedef TmnxDSXClockSource {
    type enumeration {
      enum "loopTimed" {
        value 1;
      }
      enum "nodeTimed" {
        value 2;
      }
      enum "adaptive" {
        value 3;
      }
      enum "differential" {
        value 4;
      }
    }
    description
      "The TmnxDSXClockSource data type is an enumerated type
       that indicates the clock for transmitted data on a DS3 or DS1 channel.
       loopTimed(1)     - The clock is recovered from the line's receive
                          data stream
       nodeTimed(2)     - The clock is internal
       adaptive(3)      - The clock is adaptively recovered from the rate at
                          which data is received and not from the physical
                          layer.
       differential(4)  - The clock is recovered from differential RTP
                          timestamp header.";
  }

  typedef TmnxDSXClockSyncState {
    type enumeration {
      enum "unknown" {
        value 0;
      }
      enum "normal" {
        value 1;
      }
      enum "holdOver" {
        value 2;
      }
      enum "freeRun" {
        value 3;
      }
    }
    description
      "The TmnxDSXClockSyncState data type is an enumeration type that
       indicates the clock synchronization state on a DS3 or DS1 channel.
       unknown(0)       - Unsupported or unknown state
       normal(1)        - Normal (locked) state
       holdOver(2)      - Synchronization with reference has been lost
       freeRun(3)       - Synchronized with internal reference";
  }

  typedef TmnxDS1Loopback {
    type enumeration {
      enum "none" {
        value 0;
      }
      enum "line" {
        value 1;
      }
      enum "internal" {
        value 2;
      }
      enum "fdlAnsi" {
        value 3;
      }
      enum "fdlBellcore" {
        value 4;
      }
      enum "payloadAnsi" {
        value 5;
      }
      enum "inbandAnsi" {
        value 6;
      }
      enum "inbandBellcore" {
        value 7;
      }
    }
    description
      "The TmnxDS1Loopback data type is an enumerated integer that
       indicates the type of loopback the DS1 port/channel
       currently is in.
       A 'line' loopback loops frames received on this port back to the
       remote system.
       A 'internal' loopback loops frames from the local system back at
       the framer.
       A 'fdlAnsi' requests a line loopback of type FDL ANSI T1.403.
       A 'fdlBellcore' requests a line loopback of type FDL Bellcore
       TR-TSY-000312.
       A 'payloadAnsi' requests a payload loopback of type FDL ANSI T1.403.
       A 'inbandAnsi' requests a line loopback of type inband ANSI T1.403.
       A 'inbandBellcore' requests a line loopback of type inband Bellcore
       TR-TSY-000312.";
  }

  typedef TmnxDS3Loopback {
    type enumeration {
      enum "none" {
        value 0;
      }
      enum "line" {
        value 1;
      }
      enum "internal" {
        value 2;
      }
      enum "remote" {
        value 3;
      }
    }
    description
      "The TmnxDS3Loopback data type is an enumerated integer that
       indicates the type of loopback the DS3 port/channel
       currently is in.
       A 'line' loopback loops frames received on this port back to the
       remote system.
       A 'internal' loopback loops the frames from the local system back at
       the framer.
       When the value is set to 'remote', a signal is sent to the remote
       system to provide a line loopback.";
  }

  typedef TmnxImaGrpState {
    type enumeration {
      enum "invalid" {
        value 0;
      }
      enum "notConfigured" {
        value 1;
      }
      enum "startUp" {
        value 2;
      }
      enum "startUpAck" {
        value 3;
      }
      enum "configAbortUnsupportedM" {
        value 4;
      }
      enum "configAbortIncompatibleSymmetry" {
        value 5;
      }
      enum "configAbortOther" {
        value 6;
      }
      enum "insufficientLinks" {
        value 7;
      }
      enum "blocked" {
        value 8;
      }
      enum "operational" {
        value 9;
      }
      enum "configAbortUnsupportedImaVersion" {
        value 10;
      }
    }
    description
      "The TmnxImaGrpState indicates the current state
       of the IMA Group State Machine.";
  }

  typedef TmnxImaGrpFailState {
    type enumeration {
      enum "noFailure" {
        value 1;
      }
      enum "startUpNe" {
        value 2;
      }
      enum "startUpFe" {
        value 3;
      }
      enum "invalidMValueNe" {
        value 4;
      }
      enum "invalidMValueFe" {
        value 5;
      }
      enum "failedAssymetricNe" {
        value 6;
      }
      enum "failedAssymetricFe" {
        value 7;
      }
      enum "insufficientLinksNe" {
        value 8;
      }
      enum "insufficientLinksFe" {
        value 9;
      }
      enum "blockedNe" {
        value 10;
      }
      enum "blockedFe" {
        value 11;
      }
      enum "otherFailure" {
        value 12;
      }
      enum "invalidImaVersionNe" {
        value 13;
      }
      enum "invalidImaVersionFe" {
        value 14;
      }
    }
    description
      "The TmnxImaGrpFailState indcates the failure
       reason of an IMA group.";
  }

  typedef TmnxImaLnkState {
    type enumeration {
      enum "notInGroup" {
        value 1;
      }
      enum "unusableNoGivenReason" {
        value 2;
      }
      enum "unusableFault" {
        value 3;
      }
      enum "unusableMisconnected" {
        value 4;
      }
      enum "unusableInhibited" {
        value 5;
      }
      enum "unusableFailed" {
        value 6;
      }
      enum "usable" {
        value 7;
      }
      enum "active" {
        value 8;
      }
    }
    description
      "The TmnxImaLnkState indicates the current
       state of an IMA link.";
  }

  typedef TmnxImaLnkFailState {
    type enumeration {
      enum "noFailure" {
        value 1;
      }
      enum "imaLinkFailure" {
        value 2;
      }
      enum "lifFailure" {
        value 3;
      }
      enum "lodsFailure" {
        value 4;
      }
      enum "misConnected" {
        value 5;
      }
      enum "blocked" {
        value 6;
      }
      enum "fault" {
        value 7;
      }
      enum "farEndTxLinkUnusable" {
        value 8;
      }
      enum "farEndRxLinkUnusable" {
        value 9;
      }
    }
    description
      "The TmnxImaLnkFailState indicates the local failure
       status of a link belonging to an IMA group.";
  }

  typedef TmnxImaTestState {
    type enumeration {
      enum "disabled" {
        value 1;
      }
      enum "operating" {
        value 2;
      }
      enum "failed" {
        value 3;
      }
    }
    description
      "The TmnxImaTestState indicates the current state
       of the test pattern procedure.";
  }

  typedef TmnxImaGrpClockModes {
    type enumeration {
      enum "ctc" {
        value 1;
      }
      enum "itc" {
        value 2;
      }
    }
    description
      "The TmnxImaGrpClockModes lists the types of
       clock modes available to IMA Groups.";
  }

  typedef TmnxImaGrpVersion {
    type enumeration {
      enum "oneDotZero" {
        value 1;
      }
      enum "oneDotOne" {
        value 2;
      }
    }
    description
      "The TmnxImaGrpVersion lists the types of
       Ima versions available per IMA Groups.";
  }

  typedef TmnxMcMlpppClassIndex {
    type int32 {
      range "0..15";
    }
    description
      "The TmnxMcMlpppClassIndex indicates the class
       of a Multiclass MLPPP bundle.
       
       For Multiclass MLPPP bundles with a non-zero
       tmnxBundleMlpppClassCount of classes, class index takes
       valid values from 0 to (tmnxBundleMlpppClassCount - 1)
       inclusive. For example a 4-class MLPPP bundle has 4 classes
       with indices 0, 1, 2, and 3.";
  }

  typedef TmnxMlpppEndpointIdClass {
    type enumeration {
      enum "nullClass" {
        value 0;
      }
      enum "localAddress" {
        value 1;
      }
      enum "ipAddress" {
        value 2;
      }
      enum "ieee802dot1GlobalMacAddress" {
        value 3;
      }
      enum "pppMagicNumberBlock" {
        value 4;
      }
      enum "publicSwitchedNetworkDirNumber" {
        value 5;
      }
    }
    description
      "TmnxMlpppEndpointIdClass indicates the MLPPP Endpoint
       Discriminator Class Field Type.";
  }

  typedef TmnxMlfrLinkDownReason {
    type enumeration {
      enum "none" {
        value 0;
      }
      enum "outOfService" {
        value 1;
      }
      enum "redDiffDelayExceeded" {
        value 2;
      }
      enum "loopback" {
        value 3;
      }
      enum "negotiating" {
        value 4;
      }
      enum "noRxHelloAck" {
        value 5;
      }
      enum "rxCause" {
        value 7;
      }
      enum "txCause" {
        value 8;
      }
      enum "linkReset" {
        value 9;
      }
    }
    description
      "TmnxMlfrLinkDownReason indicates the reason code for marking
       a MLFR member link of a bundle to down.
           A 'none' down reason indicates that the link is active.
           An 'outOfService' down reason indicates that the link
           operational status is down.
           A 'redDiffDelayExceeded' down reason indicates that the
           differential delay of the link exceeded the configured
           value of red differential delay and the delay action was
           configured as 'down'.
           A 'loopback' down reason indicates that the link has been
           detected to be in a loopback condition.
           A 'negotiating' down reason indicates that the link has
           not successfully negotiated the link into a bundle.
           A 'noRxHelloAck' down reason indicates that the link has
           not received a hello ack response.
           A 'rxCause' down reason indicates that a peer failure has
           been detected on this link.
           A 'txCause' down reason indicates that a local failure has
           been detected on this link.
           A linkReset' down reason indicates that the link is being reset.";
  }

  typedef TmnxWaveTrackerAlarm {
    type bits {
      bit encFail {
        position 0;
      }
      bit encDegr {
        position 1;
      }
      bit pwrFail {
        position 2;
      }
      bit pwrDegr {
        position 3;
      }
      bit pwrHigh {
        position 4;
      }
      bit pwrLow {
        position 5;
      }
      bit missing {
        position 6;
      }
    }
    description
      "The TmnxWaveTrackerAlarm specifies the alarms which are enabled or
       outstanding against a Wave Tracker enabled interface.
       The valid alarms are as follows:
       
              - encFail       - Encoder Failure.
              - encDegr       - Encoder Degrade.
              - pwrFail       - Power Control Failure.
              - pwrDegr       - Power Control Degrade.
              - pwrHigh       - Power Control High limit reached.
              - pwrLow        - Power Control Low limit reached.
              - missing       - Missing pluggable VOA.";
  }

  typedef TmnxOpticalAmpAlarm {
    type bits {
      bit ampIld {
        position 0;
      }
      bit ampTmp {
        position 1;
      }
      bit ampMth {
        position 2;
      }
      bit ampMtl {
        position 3;
      }
      bit ampLos {
        position 4;
      }
      bit ampLop {
        position 5;
      }
      bit ampCom {
        position 6;
      }
    }
    description
      "The TmnxOpticalAmpAlarm specifies the alarms which are enabled
       or outstanding against an interface that is equipped with an
       optical amplifier.
       The valid alarms are as follows:
       
              - ampIld        - Amplifier Pump over-current.
              - ampTmp        - Amplifier Pump temperature.
              - ampMth        - Amplifier Module Case temperature high.
              - ampMtl        - Amplifier Module Case temperature low.
              - ampLos        - Amplifier Loss of input optical power.
              - ampLop        - Amplifier Loss of output power.
              - ampCom        - Amplifier Module communication failure.";
  }

  typedef TmnxOpticalTdcmAlarm {
    type bits {
      bit tdcmNotRdy {
        position 0;
      }
      bit tdcmMth {
        position 1;
      }
      bit tdcmMtl {
        position 2;
      }
      bit tdcmUnLck {
        position 3;
      }
      bit tdcmTmpLim {
        position 4;
      }
      bit tdcmEprInv {
        position 5;
      }
      bit tdcmCom {
        position 6;
      }
    }
    description
      "The TmnxOpticalTdcmAlarm specifies the alarms which are enabled
       or outstanding against an interface that is equipped with a
       tunable dispersion compensation module.
       The valid alarms are as follows:
       
              - tdcmNotRdy     - Tdcm not ready.
              - tdcmMth        - Tdcm module temperature high.
              - tdcmMtl        - Tdcm module temperature low.
              - tdcmUnLck      - Tdcm thermal control unlocked.
              - tdcmTmpLim     - Tdcm thermal control temperature limit.
              - tdcmEprInv     - Tdcm EEPROM invalid.
              - tdcmCom        - Tdcm module communication failure.";
  }

  typedef TmnxOpticalDispCtrlMode {
    type enumeration {
      enum "automatic" {
        value 0;
      }
      enum "manual" {
        value 1;
      }
    }
    description
      "The TmnxOpticalDispCtrlMode specifies the operational control mode
       of the dispersion compensation module. The valid modes are as follows:
              - automatic     - The software control loop automatically
                                determines the dispersion using a FEC
                                feedback algorithm to find the best
                                operational dispersion compensation point
              - manual        - The software control loop is disabled and
                                the user manually configures the dispersion
                                compensation.";
  }

  typedef TmnxOpticalAmpCtrlState {
    type enumeration {
      enum "unknown" {
        value 0;
      }
      enum "lossOfsignal" {
        value 1;
      }
      enum "adjusting" {
        value 2;
      }
      enum "paused" {
        value 3;
      }
      enum "converged" {
        value 4;
      }
    }
    description
      "The TmnxOpticalAmpCtrlState specifies the state of the control loop
       that optimizes the receive optical power of to the MSA optics.";
  }

  typedef TmnxOpticalTdcmCtrlState {
    type enumeration {
      enum "unknown" {
        value 0;
      }
      enum "disabled" {
        value 1;
      }
      enum "waiting" {
        value 2;
      }
      enum "sweeping" {
        value 3;
      }
      enum "zoneIn" {
        value 4;
      }
      enum "fineTuning" {
        value 5;
      }
      enum "converged" {
        value 6;
      }
    }
    description
      "The TmnxOpticalTdcmCtrlState specifies the state of the control loop
       that optimizes the dispersion by tuning the dispersion compensation
       module to the set point at which the FEC corrected error rate is the
       lowest.";
  }

  typedef TmnxOpticalDwdmChannel {
    type uint32 {
      range "0|17..61|170..610";
    }
    description
      "TmnxOpticalDwdmChannel is the DWDM ITU channel associated with an
       optical interface. It is expressed in a form that is derived from the
       laser's operational frequency. For example 193.40 THz corresponds to
       DWDM ITU channel 34 in the 100 GHz grid and 193.45 THz corresponds to
       DWDM ITU channel 345 in the 50 GHz grid.
       
           Range    ITU Grid
           -------- ----------------------
           17-61    100 GHz Grid
           170-610  50 GHz Grid
       
       For configurable attributes, the value 0 represents no channel. For
       read-only attributes, the value 0 represents no channel transmitted or
       the interface is not equipped with a laser.";
  }

  typedef TmnxDigitalDiagnosticFailureBits {
    type bits {
      bit unknown {
        position 0;
      }
      bit temperature-low-warning {
        position 1;
      }
      bit temperature-low-alarm {
        position 2;
      }
      bit temperature-high-warning {
        position 3;
      }
      bit temperature-high-alarm {
        position 4;
      }
      bit supplyVoltage-low-warning {
        position 5;
      }
      bit supplyVoltage-low-alarm {
        position 6;
      }
      bit supplyVoltage-high-warning {
        position 7;
      }
      bit supplyVoltage-high-alarm {
        position 8;
      }
      bit txBiasCurrent-low-warning {
        position 9;
      }
      bit txBiasCurrent-low-alarm {
        position 10;
      }
      bit txBiasCurrent-high-warning {
        position 11;
      }
      bit txBiasCurrent-high-alarm {
        position 12;
      }
      bit txOutputPower-low-warning {
        position 13;
      }
      bit txOutputPower-low-alarm {
        position 14;
      }
      bit txOutputPower-high-warning {
        position 15;
      }
      bit txOutputPower-high-alarm {
        position 16;
      }
      bit rxOpticalPower-low-warning {
        position 17;
      }
      bit rxOpticalPower-low-alarm {
        position 18;
      }
      bit rxOpticalPower-high-warning {
        position 19;
      }
      bit rxOpticalPower-high-alarm {
        position 20;
      }
      bit aux1-low-warning {
        position 21;
      }
      bit aux1-low-alarm {
        position 22;
      }
      bit aux1-high-warning {
        position 23;
      }
      bit aux1-high-alarm {
        position 24;
      }
      bit aux2-low-warning {
        position 25;
      }
      bit aux2-low-alarm {
        position 26;
      }
      bit aux2-high-warning {
        position 27;
      }
      bit aux2-high-alarm {
        position 28;
      }
    }
    description
      "The TmnxDigitalDiagnosticFailureBits specifies the state of the Digital
       Diagnostic Monitoring (DDM) SFF thresholds. For each monitored
       attribute a low-warning, low-alarm, high-warning, and high-alarm are
       recorded.
       
       A set bit indicates the object is in a failed state, a cleared bit
       indicates the object has not exceeded the threshold.";
  }

  typedef TmnxCoherentOpticalDefectPoint {
    type bits {
      bit overTemp {
        position 0;
      }
      bit hwPost {
        position 1;
      }
      bit pldFlashInit {
        position 2;
      }
      bit powerSupply {
        position 3;
      }
      bit chkSum {
        position 4;
      }
      bit refClkIn {
        position 5;
      }
      bit txJitPllLol {
        position 6;
      }
      bit txCmuLol {
        position 7;
      }
      bit txLossFunc {
        position 8;
      }
      bit hostTxLol {
        position 9;
      }
      bit netRxLol {
        position 10;
      }
      bit hostTxSkewHigh {
        position 11;
      }
      bit netTxTec {
        position 12;
      }
      bit netTxWaveUnlk {
        position 13;
      }
      bit netTxLosf {
        position 14;
      }
      bit netRxLos {
        position 15;
      }
      bit netRxFifoErr {
        position 16;
      }
      bit netRxTec {
        position 17;
      }
      bit netTxOutOfAlign {
        position 18;
      }
      bit netTxCmuLock {
        position 19;
      }
      bit netTxRefClk {
        position 20;
      }
      bit netRxModemSyncDet {
        position 21;
      }
      bit netRxModemLock {
        position 22;
      }
      bit hostTxLaneFifoErr {
        position 23;
      }
      bit hostTxDeskew {
        position 24;
      }
    }
    description
      "The TmnxCoherentOpticalDefectPoint specifies the type of coherent
       optical defects currently active on the port.
                  
           overTemp           - Module over safe operating temperature.
           hwPost             - Hardware fault detected during power-on 
                                self-test.
           pldFlashInit       - PLD (Programmable Logic Device), CPLD
                                (Complex Programmable Logic Device), or FPGA
                                (Field Programmable Gate Array)
                                initialization fault.
           powerSupply        - Power supply is out of range.
           chkSum             - CFP (C Form factor Pluggable) table checksum
                                fault.
           refClkIn           - Loss of reference clock.
           txJitPllLol        - TX jitter PLL (Phase-Locked Loop) loss of
                                lock.
           txCmuLol           - TX CMU (Clock Multiplier Unit) loss of lock.
           txLossFunc         - TX loss of signal functionality.
           hostTxLol          - TX IC (Integrated Circuit) lock indicator.
           netRxLol           - RX IC lock indicator.
           hostTxSkewHigh     - Host lane skew out of alignment.
           netTxTec           - Lane TX thermo-electric cooler fault.
           netTxWaveUnlk      - Lane wavelength unlocked.
           netTxLosf          - Lane TX loss of signal functionality
           netRxLos           - Lane RX loss of signal.
           netRxFifoErr       - Lane RX FIFO error.
           netRxTec           - Lane RX thermo-electric cooler fault.
           netTxOutOfAlign    - Out of alignment.
           netTxCmuLock       - CMU lock fault.
           netTxRefClk        - Reference clock fault.
           netRxModemSyncDet  - Modem sync detect fault.
           netRxModemLock     - Modem lock fault.
           hostTxLaneFifoErr  - Lane TX FIFO error.
           hostTxDeskew       - Deskew lock fault.";
  }

  typedef TmnxCoherentOpticalAlarm {
    type bits {
      bit moduleFault {
        position 0;
      }
      bit module {
        position 1;
      }
      bit netRx {
        position 2;
      }
      bit netTx {
        position 3;
      }
      bit hostTx {
        position 4;
      }
    }
    description
      "The TmnxCoherentOpticalAlarm specifies the type of coherent optical
       alarm currently active on the port. The values are logical ORs of
       TmnxCoherentOpticalDefectPoint.
                 
       moduleFault  - logical OR of defect points 'overTemp(1)',
                      'hwPost(2)', 'pldFlashInit(3)', 'powerSupply(4)',
                      'chkSum(5)'
       
       module       - logical OR of defect points 'refClkIn(6)',
                      'txJitPllLol(7)', 'txCmuLol(8)', 'txLossFunc(9)'
       
       netRx        - logical OR of defect points 'netRxLol(11)',
                      'netRxLos(16)', 'netRxFifoErr(17)', 'netRxTec(18)',
                      'netRxModemSyncDet(22)', 'netRxModemLock(23)'
       
       netTx        - logical OR of defect points 'netTxTec(13)',
                      'netTxWaveUnlk(14)', 'netTxLosf(15)',
                      'netTxOutOfAlign(19)', 'netTxCmuLock(20)',
                      'netTxRefClk(21)'
       
       hostTx       - logical OR of defect points 'hostTxLol(10)',
                      'hostTxSkewHigh(12)', 'hostTxLaneFifoErr(24)',
                      'hostTxDeskew(25)'";
  }

  typedef TmnxPortLosReaction {
    type enumeration {
      enum "none" {
        value 0;
      }
      enum "squelch" {
        value 1;
      }
    }
    description
      "The TmnxPortLosReaction specifies the type of action that is taken in
       the event of a Loss Of Signal (LOS). The valid modes are as follows:
       
              - none     - Specifies that the interface not be taken down on
                           crossing the optical LOS threshold.
              - squelch  - Specifies that the interface be taken down on
                           crossing the optical LOS threshold.";
  }

  container TIMETRA-PORT-MIB {
    container tmnxPortObjs {
      smiv2:oid "1.3.6.1.4.1.6527.3.1.2.2.4";
      leaf tmnxPortTableLastChange {
        type yang:timestamp;
        description
          "The value of sysUpTime when the tmnxPortTable was last changed.";
        smiv2:max-access "read-only";
        smiv2:oid "1.3.6.1.4.1.6527.3.1.2.2.4.1";
      }
      leaf tmnxHsmdaPortSchOvrTblLastChngd {
        type yang:timestamp;
        description
          "The value of tmnxHsmdaPortSchOvrTblLastChngd indicates the sysUpTime
           at the time of the last modification of tmnxHsmdaPortSchOvrTable.
           
           If no changes were made to the table since the last
           re-initialization of the local network management subsystem,
           then this object contains a zero value.";
        smiv2:max-access "read-only";
        smiv2:oid "1.3.6.1.4.1.6527.3.1.2.2.4.27";
      }
      leaf tmnxPortEgrShaperTblLastChanged {
        type yang:timestamp;
        status obsolete;
        description
          "The value of tmnxPortEgrShaperTblLastChanged indicates the sysUpTime
           at the time of the last modification of tmnxPortEgrShaperTable.
           
           If no changes were made to the table since the last
           re-initialization of the local network management subsystem,
           then this object contains a zero value.
           
           This object is obsoleted in 10.0 Release.";
        smiv2:max-access "read-only";
        smiv2:oid "1.3.6.1.4.1.6527.3.1.2.2.4.29";
      }
      leaf tPortAccIngQGrpTableLastChgd {
        type yang:timestamp;
        description
          "The value of tPortAccIngQGrpTableLastChgd indicates the
           timestamp of last change to the tPortAccIngQGrpTable.";
        smiv2:max-access "read-only";
        smiv2:oid "1.3.6.1.4.1.6527.3.1.2.2.4.32";
      }
      leaf tPortAccIngQOverTableLastChgd {
        type yang:timestamp;
        description
          "The value of tPortAccIngQOverTableLastChgd indicates the
           timestamp of last change to the tPortAccIngQOverTable.";
        smiv2:max-access "read-only";
        smiv2:oid "1.3.6.1.4.1.6527.3.1.2.2.4.34";
      }
      leaf tPortAccEgrQGrpTableLastChgd {
        type yang:timestamp;
        description
          "The value of tPortAccEgrQGrpTableLastChgd indicates the
           timestamp of last change to the tPortAccEgrQGrpTable.";
        smiv2:max-access "read-only";
        smiv2:oid "1.3.6.1.4.1.6527.3.1.2.2.4.36";
      }
      leaf tPortAccEgrQOverTableLastChgd {
        type yang:timestamp;
        description
          "The value of tPortAccEgrQOverTableLastChgd indicates the timestamp
           of last change to the tPortAccEgrQOverTable.";
        smiv2:max-access "read-only";
        smiv2:oid "1.3.6.1.4.1.6527.3.1.2.2.4.38";
      }
      leaf tPortNetEgrQGrpTableLastChgd {
        type yang:timestamp;
        description
          "The value of tPortNetEgrQGrpTableLastChgd indicates the
           timestamp of last change to the tPortNetEgrQGrpTable.";
        smiv2:max-access "read-only";
        smiv2:oid "1.3.6.1.4.1.6527.3.1.2.2.4.40";
      }
      leaf tPortNetEgrQOverTableLastChgd {
        type yang:timestamp;
        description
          "The value of tPortNetEgrQOverTableLastChgd indicates the timestamp
           of last change to the tPortNetEgrQOverTable.";
        smiv2:max-access "read-only";
        smiv2:oid "1.3.6.1.4.1.6527.3.1.2.2.4.42";
      }
      leaf tPortAccEgrQGrpHMTableLastChgd {
        type yang:timestamp;
        description
          "The value of tPortAccEgrQGrpHMTableLastChgd indicates the
           timestamp of last change to the tPortAccEgrQGrpHostMatchTable.";
        smiv2:max-access "read-only";
        smiv2:oid "1.3.6.1.4.1.6527.3.1.2.2.4.49";
      }
      leaf tPortEgrVPortTableLastChgd {
        type yang:timestamp;
        description
          "The value of tPortEgrVPortTableLastChgd indicates the
           timestamp of last change to the tPortEgrVPortTable.";
        smiv2:max-access "read-only";
        smiv2:oid "1.3.6.1.4.1.6527.3.1.2.2.4.54";
      }
      leaf tPortEgrVPortHMTableLastChgd {
        type yang:timestamp;
        description
          "The value of tPortEgrVPortHMTableLastChgd indicates the timestamp
           of last change to the tPortEgrVPortHostMatchTable.";
        smiv2:max-access "read-only";
        smiv2:oid "1.3.6.1.4.1.6527.3.1.2.2.4.56";
      }
      leaf tmnxPortEgrExpShaperTblLastChngd {
        type yang:timestamp;
        description
          "The value of tmnxPortEgrExpShaperTblLastChngd indicates the sysUpTime
           at the time of the last modification of tmnxPortEgrExpShaperTable.";
        smiv2:max-access "read-only";
        smiv2:oid "1.3.6.1.4.1.6527.3.1.2.2.4.60";
      }
      leaf tmnxPwPortTblLastChanged {
        type yang:timestamp;
        description
          "The value of tmnxPwPortTblLastChanged indicates the sysUpTime
           at the time of the last modification of tmnxPwPortTable.
           
           If no changes were made to the entry since the last re-initialization
           of the local network management subsystem, then this object contains a
           zero value.";
        smiv2:max-access "read-only";
        smiv2:oid "1.3.6.1.4.1.6527.3.1.2.2.4.69";
      }
      config false;
    }
    container tmnxPortScalarObjs {
      smiv2:oid "1.3.6.1.4.1.6527.3.1.2.2.4.19";
      leaf tmnxL4LoadBalancing {
        type boolean;
        description
          "The value of tmnxL4LoadBalancing specifies whether layer 4 information,
           src and dst ports, should be used in the LAG and ECMP hashing
           algorithm. This is the global system setting that all ports will
           inherit. When set to 'true', src and dst ports are used in the hashing
           algorithm. The per port setting of tmnxPortLoadBalanceAlgorithm can
           override tmnxL4LoadBalancing.";
        smiv2:defval "false";
        smiv2:max-access "read-write";
        smiv2:oid "1.3.6.1.4.1.6527.3.1.2.2.4.19.1";
        config true;
      }
      leaf tmnxLsrIpLoadBalancing {
        type enumeration {
          enum "label-only" {
            value 1;
          }
          enum "label-ip" {
            value 2;
          }
          enum "ip-only" {
            value 3;
          }
        }
        description
          "The value of tmnxLsrIpLoadBalancing specifies whether the IP Header is
           used in the LAG and ECMP LSR hashing algorithm. This is the global
           system setting that all ports will inherit. When set to 'label-ip (2)',
           the IP Header is included in the hashing algorithm. When set to
           'ip-only (3)' the IP Header is used exclusively in the hashing
           algorithm.";
        smiv2:defval "label-only";
        smiv2:max-access "read-write";
        smiv2:oid "1.3.6.1.4.1.6527.3.1.2.2.4.19.2";
        config true;
      }
      leaf tmnxIpLoadBalancing {
        type enumeration {
          enum "standard" {
            value 1;
          }
          enum "systemIp" {
            value 2;
          }
        }
        description
          "The value of tmnxIpLoadBalancing specifies whether or not this node's
           system IP address is used in the final stage of the load balancing
           (hashing) algorithm used to choose the LAG member or ECMP route for an
           outbound packet.
           
           If 'systemIp(2)' is selected, this node's system IP address (i.e.
           TIMETRA-VRTR-MIB::vRiaIpAddress.1.1.1) is used in the final stage of
           the LAG and ECMP load balancing algorithm.  This selection makes it
           more likely that different SROS nodes in a network will make different
           load balancing decisions.  'systemIp(2)' is supported on iom3-xp IOMs,
           equivalent IMMs, and newer IOM and IMM types.  When older IOMs/IMMs are
           present in a system which has 'systemIp(2)' configured, the older IOMs
           operate in 'standard(1)' mode.
           
           If 'standard(1)' is selected, this node's system IP address is not used
           in the final stage of the LAG and ECMP load balancing algorithm.
           'standard(1)' is supported on all IOM and IMM types.
           
           The earlier stages of the load balancing algorithm are controlled by
           tmnxL4LoadBalancing and tmnxLsrIpLoadBalancing (when applicable).";
        smiv2:defval "standard";
        smiv2:max-access "read-write";
        smiv2:oid "1.3.6.1.4.1.6527.3.1.2.2.4.19.3";
        config true;
      }
      leaf tmnxMulticastEnhLoadBalancing {
        type boolean;
        description
          "The value of tmnxMulticastEnhLoadBalancing specifies how the node
           distributes multicast traffic over LAG ports.
           
           The default value, 'false (1),' preserves the behaviour prior to
           the introduction of this object: multicast traffic hash uses internal
           system multicast identifiers.  This allows per multicast
           (S,G) channel (IP replication) or per LSP (MPLS replication) traffic
           distribution over LAG.
           
           The value of 'true (2)' introduces an enhanced multicast distribution
           over LAG: multicast traffic hash uses packet header information and
           configuration of other system-level hashing parameters like
           tmnxL4LoadBalancing, tmnxLsrIpLoadBalancing, or tmnxIpLoadBalancing.
           The functionality allows for a greater flexibility in defining how
           multicast is to be distributed over a LAG allowing, for example, per
           (S,G) channel distribution for both IP and MPLS replications.";
        smiv2:defval "false";
        smiv2:max-access "read-write";
        smiv2:oid "1.3.6.1.4.1.6527.3.1.2.2.4.19.4";
        config true;
      }
      config true;
    }
    container tmnxPortPlcyObjs {
      smiv2:oid "1.3.6.1.4.1.6527.3.1.2.2.4.67";
      leaf tmnxPortPlcyTableLastCh {
        type yang:timestamp;
        description
          "The value of the object tmnxPortPlcyTableLastCh indicates
           the value of sysUpTime at the time of the last modification of
           an entry in the tmnxPortPlcyTable.";
        smiv2:max-access "read-only";
        smiv2:oid "1.3.6.1.4.1.6527.3.1.2.2.4.67.1";
      }
      config false;
    }
    container tmnxATMObjs {
      smiv2:oid "1.3.6.1.4.1.6527.3.1.2.2.11";
      leaf tmnxPortATMVpShaperTblLastCh {
        type yang:timestamp;
        description
          "The value of tmnxPortATMVpShaperTblLastCh indicates the sysUpTime
           at the time of the last modification of tmnxPortATMVpShaperTable.
           
           If no changes were made to the table since the last
           re-initialization of the local network management subsystem,
           then this object contains a zero value.";
        smiv2:max-access "read-only";
        smiv2:oid "1.3.6.1.4.1.6527.3.1.2.2.11.2";
      }
      config false;
    }
    container tmnxPortTable {
      description
        "The port table has an entry for each port on each IOM card in each
         chassis in the TMNX system.";
      smiv2:oid "1.3.6.1.4.1.6527.3.1.2.2.4.2";
      list tmnxPortEntry {
        key "tmnxChassisIndex tmnxPortPortID";
        description
          "Each row entry represents a port on a IOM card in a chassis in the
           system.  Entries cannot be created and deleted via SNMP SET
           operations.  Before an IOM tmnxMDAEntry can be deleted from the
           tmnxMDATable, its supported tmnxPortEntry rows must be in the proper
           state for removal.";
        smiv2:oid "1.3.6.1.4.1.6527.3.1.2.2.4.2.1";
        leaf tmnxChassisIndex {
          type leafref {
            path "/timetra-chassis:TIMETRA-CHASSIS-MIB/timetra-chassis:tmnxChassisTable/timetra-chassis:tmnxChassisEntry/timetra-chassis:tmnxChassisIndex";
          }
          config true;
        }
        leaf tmnxPortPortID {
          type timetra-tc:TmnxPortID;
          description
            "tmnxPortPortID is an index into this table. It maps this port to its
             entry in the mib-2 interfaces table.";
          smiv2:max-access "not-accessible";
          smiv2:oid "1.3.6.1.4.1.6527.3.1.2.2.4.2.1.1";
          config true;
        }
        leaf tmnxPortLastChangeTime {
          type yang:timestamp;
          description
            "The tmnxPortLastChangeTime variable contains the sysUpTime
             value of the most recently modified writable variable in the
             tmnxPortEntry row for this port.";
          smiv2:max-access "read-only";
          smiv2:oid "1.3.6.1.4.1.6527.3.1.2.2.4.2.1.2";
          config false;
        }
        leaf tmnxPortType {
          type timetra-port:TmnxPortType;
          description
            "The type of port or optical pack installed.";
          smiv2:max-access "read-only";
          smiv2:oid "1.3.6.1.4.1.6527.3.1.2.2.4.2.1.3";
          config false;
        }
        leaf tmnxPortClass {
          type timetra-port:TmnxPortClass;
          description
            "The class of port or optical pack installed.  This can be
             derived from tmnxPortType.";
          smiv2:max-access "read-only";
          smiv2:oid "1.3.6.1.4.1.6527.3.1.2.2.4.2.1.4";
          config false;
        }
        leaf tmnxPortDescription {
          type timetra-tc:TItemLongDescription;
          description
            "A textual string containing user supplied information about the
             interface.";
          smiv2:defval "";
          smiv2:max-access "read-write";
          smiv2:oid "1.3.6.1.4.1.6527.3.1.2.2.4.2.1.5";
          config true;
        }
        leaf tmnxPortName {
          type timetra-tc:TNamedItemOrEmpty;
          description
            "The textual name of the interface.  The value of this
             object should be the name of the interface as assigned by
             the local device and should be suitable for use in commands
             entered at the device's `console'.  This might be a text
             name, such as `le0' or 'sys171-2/1.";
          smiv2:max-access "read-only";
          smiv2:oid "1.3.6.1.4.1.6527.3.1.2.2.4.2.1.6";
          config false;
        }
        leaf tmnxPortAlias {
          type timetra-tc:TNamedItemOrEmpty;
          description
            "This object is an 'alias' name for the interface as
             specified by a network manager, and provides a non-volatile
             'handle' for the interface.
             
             On the first instantiation of an interface, the value of
             tmnxPortAlias associated with that interface is the zero-length
             string.  As and when a value is written into an instance of
             tmnxPortAlias through a network management set operation, then the
             agent must retain the supplied value in the tmnxPortAlias instance
             associated with the same interface for as long as that
             interface remains instantiated, including across all re-
             initializations/reboots of the network management system.";
          smiv2:defval "";
          smiv2:max-access "read-write";
          smiv2:oid "1.3.6.1.4.1.6527.3.1.2.2.4.2.1.7";
          config true;
        }
        leaf tmnxPortUserAssignedMac {
          type boolean;
          description
            "When tmnxPortUserAssignedMac has a value of 'true', the value of
             tmnxPortMacAddress has been explicitly assigned by a SNMP SET
             request.  When tmnxPortUserAssignedMac is set to 'false',
             tmnxPortMacAddress returns the system assigned MAC address.";
          smiv2:defval "false";
          smiv2:max-access "read-only";
          smiv2:oid "1.3.6.1.4.1.6527.3.1.2.2.4.2.1.8";
          config false;
        }
        leaf tmnxPortMacAddress {
          type yang:mac-address;
          description
            "When tmnxPortUserAssignedMac has a value of 'true',
             tmnxPortMacAddress has the value that has been explicitly
             assigned by a SNMP SET request.  When tmnxPortUserAssignedMac
             has a value of 'false', tmnxPortMacAddress returns the same
             value as tmnxPortMacAddress, the hardware or system assigned
             MAC address.  When tmnxPortMacAddress is modified by a SET
             request, the agent sets tmnxPortUserAssignedMac to 'true'.
             
             Setting tmnxPortMacAddress to all zeros causes the agent to
             revert to using the default tmnxPortHwMacAddress and also to
             return tmnxPortUserAssignedMac as 'false'.";
          smiv2:defval "'000000000000'H";
          smiv2:max-access "read-write";
          smiv2:oid "1.3.6.1.4.1.6527.3.1.2.2.4.2.1.9";
          config true;
        }
        leaf tmnxPortHwMacAddress {
          type yang:mac-address;
          description
            "The interface's hardware or system assigned MAC address at its
             protocol sub-layer.  When tmnxPortUserAssignedMac has a value of
             'true', the value of tmnxPortMacAddress is used instead of
             tmnxPortHwMacAddress.
             
             In the case of a pre-provisioned port that is not yet physically
             in the system, the MAC address may not be known.  In this case
             a MAC address of all zeros is returned.";
          smiv2:max-access "read-only";
          smiv2:oid "1.3.6.1.4.1.6527.3.1.2.2.4.2.1.10";
          config false;
        }
        leaf tmnxPortMode {
          type enumeration {
            enum "undefined" {
              value 0;
            }
            enum "access" {
              value 1;
            }
            enum "network" {
              value 2;
            }
            enum "hybrid" {
              value 3;
            }
          }
          description
            "The tmnxPortMode variable indicates if the interface on this port
             is configured as a service access port, a network port or a 
             hybrid port.  Once the port's mode has been configured for 'access', 
             'network' or 'hybrid' mode, multiple services may be configured 
             on the port.
             
             tmnxPortEncapType is defaulted based on MDA type and
             Port Mode according to the following table:
             
             MDA Type           Port Mode             tmnxPortEncapType
             ---------------------------------------------------------
             ATM                access                atmEncap
             
             CEM                access                cemEncap
             
             Ethernet           access                nullEncap
                                network               nullEncap
                                hybrid                qEncap
             
             ISA
               isa-aa           network               nullEncap
               isa-bb           access                qinqEncap
                                network               qEncap
               isa-ipsec        access                qEncap
               isa-video        access                qEncap
             
             Sonet/SDH          access                bcpNullEncap
                                network               pppAutoEncap
             
             TDM                access                bcpNullEncap
                                network               pppAutoEncap
             
             VSM
                vsm-cca         access                qEncap
                vsm-cca         network               qEncap";
          smiv2:max-access "read-write";
          smiv2:oid "1.3.6.1.4.1.6527.3.1.2.2.4.2.1.11";
          config true;
        }
        leaf tmnxPortEncapType {
          type timetra-port:TmnxPortEncapType;
          description
            "The value of tmnxPortEncapType specifies the type of encapsulation 
             protocol configured on this port's network interface.  
             
             tmnxPortEncapType is set to 'unknown' for physical SONET/SDH and
             TDM ports.
             
             If the port mode equals 'hybrid', tmnxPortEncapType can only
             be set to 'qEncap' or 'qinqEncap'.";
          smiv2:max-access "read-write";
          smiv2:oid "1.3.6.1.4.1.6527.3.1.2.2.4.2.1.12";
          config true;
        }
        leaf tmnxPortLagId {
          type uint32 {
            range "0..200";
          }
          description
            "The value of tmnxPortLagId indicates which LAG or multi-link trunk
             (MLT) this port is assigned to. If this port is not associated
             with any LAG, this value will be set to zero(0).
             
             The maximum value of this object is '64', when the value of
             TIMETRA-CHASSIS-MIB::tmnxChassisType is '5' (ESS-1/SR-1).";
          smiv2:defval "0";
          smiv2:max-access "read-write";
          smiv2:oid "1.3.6.1.4.1.6527.3.1.2.2.4.2.1.13";
          config true;
        }
        leaf tmnxPortHoldTimeUp {
          type uint32 {
            range "0..90000";
          }
          description
            "The value of tmnxPortHoldTimeUp is used to configure the
             hold-timer for link up event dampening. This guards against
             reporting excessive interface transitions. This is implemented
             by not advertising subsequent transitions of the interface to
             upper layer protocols until the configured timer has expired.
             A value of zero (0) indicates that an up transition is reported
             immediately.  The value of tmnxPortHoldTimeUp is not applicable
             when tmnxPortClass has a value of 'sonet (5)'. In that case,
             tmnxSonetHoldTimeUp is used instead.
             
             tmnxPortHoldTimeUp is measured in units as specified by
             tmnxPortHoldTimeUnits. The maximum hold-time for this object is
             15 minutes, regardless of the units specified. Attempts to change
             the maximum value to a hold-time longer than 15 minutes will result
             in an INCONSISTENT error.";
          smiv2:defval "0";
          smiv2:max-access "read-write";
          smiv2:oid "1.3.6.1.4.1.6527.3.1.2.2.4.2.1.14";
          config true;
        }
        leaf tmnxPortHoldTimeDown {
          type uint32 {
            range "0..90000";
          }
          description
            "The value of tmnxPortHoldTimeDown is used to configure the
             hold-timer for link down event dampening. This guards against
             reporting excessive interface transitions. This is implemented
             by not advertising subsequent transitions of the interface to
             upper layer protocols until the configured timer has expired.
             A value of zero (0) indicates that a down transition is reported
             immediately. The value of tmnxPortHoldTimeDown is not applicable
             when tmnxPortClass has a value of 'sonet (5)'. In that case,
             tmnxSonetHoldTimeDown is used instead.
             
             tmnxPortHoldTimeDown is measured in units as specified by
             tmnxPortHoldTimeUnits. The maximum hold-time for this object is
             15 minutes, regardless of the units specified. Attempts to change
             the maximum value to a hold-time longer than 15 minutes will result
             in an INCONSISTENT error.";
          smiv2:defval "0";
          smiv2:max-access "read-write";
          smiv2:oid "1.3.6.1.4.1.6527.3.1.2.2.4.2.1.15";
          config true;
        }
        leaf tmnxPortUpProtocols {
          type bits {
            bit portUpIpv4 {
              position 0;
            }
            bit portUpMpls {
              position 1;
            }
            bit portUpBcp {
              position 2;
            }
            bit portUpIso {
              position 3;
            }
            bit portUpFr {
              position 4;
            }
            bit portUpAtm {
              position 5;
            }
            bit portUpChdlc {
              position 6;
            }
            bit portUpIma {
              position 7;
            }
            bit portUpIpv6 {
              position 8;
            }
          }
          description
            "The tmnxPortUpProtocols variable is a bitmap that indicates what
             protocols can be used on this port type.";
          smiv2:max-access "read-only";
          smiv2:oid "1.3.6.1.4.1.6527.3.1.2.2.4.2.1.16";
          config false;
        }
        leaf tmnxPortConnectorType {
          type timetra-port:TmnxPortConnectorType;
          description
            "The type of connector installed on this port.";
          smiv2:max-access "read-only";
          smiv2:oid "1.3.6.1.4.1.6527.3.1.2.2.4.2.1.17";
          config false;
        }
        leaf tmnxPortTransceiverType {
          type enumeration {
            enum "unknown" {
              value 0;
            }
            enum "gbic" {
              value 1;
            }
            enum "moduleConnectorSolderedToMotherboard" {
              value 2;
            }
            enum "sfpTransceiver" {
              value 3;
            }
            enum "xbiTransceiver" {
              value 4;
            }
            enum "xenpakTransceiver" {
              value 5;
            }
            enum "xfpTransceiver" {
              value 6;
            }
            enum "xffTransceiver" {
              value 7;
            }
            enum "xfpeTransceiver" {
              value 8;
            }
            enum "xpakTransceiver" {
              value 9;
            }
            enum "x2Transceiver" {
              value 10;
            }
            enum "dwdmSfpTransceiver" {
              value 11;
            }
            enum "qsfpTransceiver" {
              value 12;
            }
            enum "qsfpPlusTransceiver" {
              value 13;
            }
            enum "cfpTransceiver" {
              value 14;
            }
            enum "cxpTransceiver" {
              value 15;
            }
            enum "oifMsa100gLh" {
              value 16;
            }
          }
          description
            "Type of the transceiver.";
          smiv2:max-access "read-only";
          smiv2:oid "1.3.6.1.4.1.6527.3.1.2.2.4.2.1.25";
          config false;
        }
        leaf tmnxPortTransceiverCode {
          type bits {
            bit unknown {
              position 0;
            }
            bit oc48-longreach {
              position 1;
            }
            bit oc48-intermediatereach {
              position 2;
            }
            bit oc48-shortreach {
              position 3;
            }
            bit oc12-singlemodelongreach {
              position 4;
            }
            bit oc12-singlemodeinterreach {
              position 5;
            }
            bit oc12-multimodeshortreach {
              position 6;
            }
            bit oc3-singlemodelongreach {
              position 7;
            }
            bit oc3-singlemodeinterreach {
              position 8;
            }
            bit oc3-multi-modeshortreach {
              position 9;
            }
            bit gige-1000base-t {
              position 10;
            }
            bit gige-1000base-cx {
              position 11;
            }
            bit gige-1000base-lx {
              position 12;
            }
            bit gige-1000base-sx {
              position 13;
            }
            bit faste-100base-mm-fx {
              position 14;
            }
            bit faste-100base-sm-fx {
              position 15;
            }
            bit xgige-10gbase-sr {
              position 16;
            }
            bit xgige-10gbase-lr {
              position 17;
            }
            bit xgige-10gbase-er {
              position 18;
            }
            bit xgige-10gbase-sw {
              position 19;
            }
            bit xgige-10gbase-lw {
              position 20;
            }
            bit xgige-10gbase-ew {
              position 21;
            }
          }
          status obsolete;
          description
            "The code for the transmission media.
             
             tmnxPortOpticalCompliance is used instead of
             tmnxPortTransceiverCode.tmnxPortOpticalCompliance  contains the
             same information and is defined by an industry standard.";
          smiv2:max-access "read-only";
          smiv2:oid "1.3.6.1.4.1.6527.3.1.2.2.4.2.1.26";
          config false;
        }
        leaf tmnxPortTransceiverLaserWaveLen {
          type uint32;
          description
            "The light wavelength transmitted by the transceiver's laser.
             A value of zero indicates that the port is not equipped with
             the transceiver.
             
             A value in the range of 1 to 2000 indicates that the units are in
             nano-meters (nm). A value in the range of 850000 to 2000000
             indicates that the units are in pico-meters (pm).";
          smiv2:max-access "read-only";
          smiv2:oid "1.3.6.1.4.1.6527.3.1.2.2.4.2.1.27";
          config false;
        }
        leaf tmnxPortTransceiverDiagCapable {
          type enumeration {
            enum "notApplicable" {
              value 0;
            }
            enum "true" {
              value 1;
            }
            enum "false" {
              value 2;
            }
          }
          description
            "Indicates if the transceiver is capable of doing diagnostics.";
          smiv2:max-access "read-only";
          smiv2:oid "1.3.6.1.4.1.6527.3.1.2.2.4.2.1.28";
          config false;
        }
        leaf tmnxPortTransceiverModelNumber {
          type timetra-tc:TNamedItemOrEmpty;
          description
            "The value of tmnxPortTransceiverModelNumber indicates the model
             information for the transceiver, as read from the transceiver
             EEPROM.  For example, the string may contain the Alcatel-Lucent
             part number and CLEI for the transceiver.
             
             The string is expected to contain printable ASCII characters, but
             unprintable ASCII characters read from the EEPROM are not
             filtered out.";
          smiv2:max-access "read-only";
          smiv2:oid "1.3.6.1.4.1.6527.3.1.2.2.4.2.1.29";
          config false;
        }
        leaf tmnxPortSFPConnectorCode {
          type enumeration {
            enum "unknown" {
              value 0;
            }
            enum "sc" {
              value 1;
            }
            enum "fiberChannel-Style1-CopperConnector" {
              value 2;
            }
            enum "fiberChannel-Style2-CopperConnector" {
              value 3;
            }
            enum "bncortnc" {
              value 4;
            }
            enum "fiberChannelCoaxialHeaders" {
              value 5;
            }
            enum "fiberJack" {
              value 6;
            }
            enum "lc" {
              value 7;
            }
            enum "mt-rj" {
              value 8;
            }
            enum "mu" {
              value 9;
            }
            enum "sg" {
              value 10;
            }
            enum "opticalPigtail" {
              value 11;
            }
            enum "hssdcII" {
              value 32;
            }
            enum "copperPigtail" {
              value 33;
            }
            enum "opticalTransceiver" {
              value 51;
            }
            enum "copperGigE" {
              value 128;
            }
          }
          description
            "The external connector provided on the interface.";
          smiv2:max-access "read-only";
          smiv2:oid "1.3.6.1.4.1.6527.3.1.2.2.4.2.1.30";
          config false;
        }
        leaf tmnxPortSFPVendorOUI {
          type uint32;
          description
            "The vendor organizationally unique identifier field (OUI)
             contains the IEEE company identifier for the vendor.
             A value of all zero indicates that the vendor OUI
             is unspecified.";
          smiv2:max-access "read-only";
          smiv2:oid "1.3.6.1.4.1.6527.3.1.2.2.4.2.1.31";
          config false;
        }
        leaf tmnxPortSFPVendorManufactureDate {
          type snmpv2-tc:DateAndTime;
          description
            "The vendor's date code.";
          smiv2:max-access "read-only";
          smiv2:oid "1.3.6.1.4.1.6527.3.1.2.2.4.2.1.32";
          config false;
        }
        leaf tmnxPortSFPMedia {
          type enumeration {
            enum "notApplicable" {
              value 0;
            }
            enum "ethernet" {
              value 1;
            }
            enum "sonetsdh" {
              value 2;
            }
          }
          description
            "The value of tmnxPortSFPMedia indicates the media supported for the
             SFF (Small Form-Factor).";
          smiv2:max-access "read-only";
          smiv2:oid "1.3.6.1.4.1.6527.3.1.2.2.4.2.1.33";
          config false;
        }
        leaf tmnxPortSFPEquipped {
          type boolean;
          description
            "The value of tmnxPortSFPEquipped indicates if the SFF is equipped.";
          smiv2:max-access "read-only";
          smiv2:oid "1.3.6.1.4.1.6527.3.1.2.2.4.2.1.34";
          config false;
        }
        leaf tmnxPortEquipped {
          type boolean;
          description
            "Indicates if there is an optics pack installed in this
             port or not.";
          smiv2:max-access "read-only";
          smiv2:oid "1.3.6.1.4.1.6527.3.1.2.2.4.2.1.35";
          config false;
        }
        leaf tmnxPortLinkStatus {
          type boolean;
          description
            "Indicates whether or not the port has a physical link.";
          smiv2:max-access "read-only";
          smiv2:oid "1.3.6.1.4.1.6527.3.1.2.2.4.2.1.36";
          config false;
        }
        leaf tmnxPortAdminStatus {
          type timetra-chassis:TmnxPortAdminStatus;
          description
            "The desired administrative status of this port.
             
             When tmnxPortType references a row in the tmnxPortTypeTable
             where tmnxPortTypeName is the octet string 'Application 
             Assurance', an attempt to set tmnxPortAdminStatus to a 
             value other than 'inService' results in an 
             'inconsistentValue' error.";
          smiv2:defval "inService";
          smiv2:max-access "read-write";
          smiv2:oid "1.3.6.1.4.1.6527.3.1.2.2.4.2.1.37";
          config true;
        }
        leaf tmnxPortOperStatus {
          type timetra-port:TmnxPortOperStatus;
          description
            "The current operational status of this port.";
          smiv2:max-access "read-only";
          smiv2:oid "1.3.6.1.4.1.6527.3.1.2.2.4.2.1.38";
          config false;
        }
        leaf tmnxPortState {
          type timetra-port:TmnxPortState;
          description
            "The state level of this port.  A value of 'none' indicates
             the port is either in its initial creation state or is
             just about to be deleted.  A value of 'ghost' represents
             a port that is not physically present.  This state may
             represent a pre-provisioned port.  A value of 'linkDown'
             represents a port that is physically present but does
             not have a link.  The 'linkUp' state represents a port
             that is physically present and has physical link present.
             A port in 'up' state is ready to pass some kinds of traffic.
             The tmnxPortUpProtocols variable indicates the actual type(s)
             of traffic can be passed on this 'up' link.";
          smiv2:max-access "read-only";
          smiv2:oid "1.3.6.1.4.1.6527.3.1.2.2.4.2.1.39";
          config false;
        }
        leaf tmnxPortPrevState {
          type timetra-port:TmnxPortState;
          description
            "The tmnxPortPrevState indicates the state level that the port
             transitioned from into the current tmnxPortState level.";
          smiv2:max-access "read-only";
          smiv2:oid "1.3.6.1.4.1.6527.3.1.2.2.4.2.1.40";
          config false;
        }
        leaf tmnxPortNumAlarms {
          type uint32;
          description
            "The number of alarms currently outstanding on this port.";
          smiv2:max-access "read-only";
          smiv2:oid "1.3.6.1.4.1.6527.3.1.2.2.4.2.1.41";
          config false;
        }
        leaf tmnxPortAlarmState {
          type timetra-chassis:TmnxAlarmState;
          description
            "The value of tmnxPortAlarmState indicates the current alarm
             state for this port.";
          smiv2:max-access "read-only";
          smiv2:oid "1.3.6.1.4.1.6527.3.1.2.2.4.2.1.42";
          config false;
        }
        leaf tmnxPortLastAlarmEvent {
          type snmpv2-tc:RowPointer;
          description
            "The value of tmnxPortLastAlarmEvent indicates the object name
             and instance value that points to the row entry in the ALARM-MIB
             containing the most recent alarm associated with this port.  If
             tmnxPortAlarmState has a value of 'alarmCleared(2)', the
             most recent alarm event will be in the cleared alarm table.  If it has
             a value of 'alarmActive(1)', the most recent alarm event will be in
             the active alarm table.  If the value of tmnxPortLastAlarmEvent is
             '0.0', either no port alarm events have occurred since the system was
             last booted, or the last port alarm event has aged out and its entry
             is no longer available in the ALARM-MIB tables.";
          smiv2:max-access "read-only";
          smiv2:oid "1.3.6.1.4.1.6527.3.1.2.2.4.2.1.43";
          config false;
        }
        leaf tmnxPortClearAlarms {
          type timetra-tc:TmnxActionType;
          description
            "Setting this action variable causes all the alarms
             associated with this port to be moved from the current
             alarm log to the history alarm log. Primarily meant
             for use in development.  This object will most likely
             be removed from the MIB before product release.";
          smiv2:defval "notApplicable";
          smiv2:max-access "read-write";
          smiv2:oid "1.3.6.1.4.1.6527.3.1.2.2.4.2.1.44";
          config true;
        }
        leaf tmnxPortSFPVendorSerialNum {
          type timetra-tc:TNamedItemOrEmpty;
          description
            "The value of tmnxPortSFPVendorSerialNum indicates the
             transceiver's vendor serial number in ASCII characters,
             as read from the transceiver EEPROM.
             
             An empty string indicates the vendor serial number is
             unspecified.
             
             The string is expected to contain printable ASCII characters,
             but unprintable ASCII characters read from the EEPROM are not
             filtered out.";
          smiv2:max-access "read-only";
          smiv2:oid "1.3.6.1.4.1.6527.3.1.2.2.4.2.1.45";
          config false;
        }
        leaf tmnxPortSFPVendorPartNum {
          type timetra-tc:TNamedItemOrEmpty;
          description
            "The value of tmnxPortSFPVendorPartNum indicates the
             transceiver's vendor part number (or product name) in ASCII
             characters, as read from the transceiver EEPROM.
             
             An empty string indicates the vendor part number is
             unspecified.
             
             The string is expected to contain printable ASCII characters, but
             unprintable ASCII characters read from the EEPROM are not
             filtered out.";
          smiv2:max-access "read-only";
          smiv2:oid "1.3.6.1.4.1.6527.3.1.2.2.4.2.1.46";
          config false;
        }
        leaf tmnxPortLastStateChanged {
          type yang:timestamp;
          description
            "The tmnxPortLastStateChanged variable contains the
             value of the sysUpTime the last time the operational status
             of the port changed state.";
          smiv2:max-access "read-only";
          smiv2:oid "1.3.6.1.4.1.6527.3.1.2.2.4.2.1.48";
          config false;
        }
        leaf tmnxPortNumChannels {
          type uint32;
          description
            "For SONET/SDH paths or TDM channels, tmnxPortNumChannels
             contains the number of possible immediate children. For
             leaf paths or channels, the value of this object will be zero.
             For SONET/SDH or TDM physical ports, tmnxPortNumChannels
             contains the total number of channels on the physical port.
             For all other entries in the tmnxPortTable, the value of
             this object will be zero.";
          smiv2:max-access "read-only";
          smiv2:oid "1.3.6.1.4.1.6527.3.1.2.2.4.2.1.49";
          config false;
        }
        leaf tmnxPortNetworkEgrQueues {
          type timetra-tc:TNamedItemOrEmpty;
          description
            "tmnxPortNetworkEgrQueues contains the network egress queue policy
             if the tmnxPortMode is network. Otherwise this object has no
             significance.";
          smiv2:max-access "read-write";
          smiv2:oid "1.3.6.1.4.1.6527.3.1.2.2.4.2.1.50";
          config true;
        }
        leaf tmnxPortBundleNumber {
          type int32 {
            range "0..2000";
          }
          description
            "tmnxPortBundleNumber identifies the bundle for which this port is
             a member. If this port is not a member of any bundle, the value of
             tmnxPortBundleNumber will be zero.";
          smiv2:max-access "read-only";
          smiv2:oid "1.3.6.1.4.1.6527.3.1.2.2.4.2.1.51";
          config false;
        }
        leaf tmnxPortIsLeaf {
          type boolean;
          description
            "tmnxPortIsLeaf is applicable only when the 'isSonet' and/or 'isTDM'
             bits in TIMETRA-CHASSIS-MIB:tmnxMDACapabilities are set.
             When the value of this object is 'true', it indicates that the channel
             is capable of passing traffic.
             
             The value of this object is 'false' for:
             1. Physical ports on SONET/TDM MDA's
             2. Intermediate channels on a channelized MDA
             3. Leaf channels which belong to a bundle
             
             For ports on Ethernet MDA's or for LAG ports, the value of this object
             will be 'false'.";
          smiv2:max-access "read-only";
          smiv2:oid "1.3.6.1.4.1.6527.3.1.2.2.4.2.1.52";
          config false;
        }
        leaf tmnxPortChanType {
          type timetra-chassis:TmnxMDAChanType;
          description
            "tmnxPortChanType is applicable only when the 'isSonet' and/or 'isTDM'
             bits in TIMETRA-CHASSIS-MIB:tmnxMDACapabilities are set. It indicates
             the type of the channel.
             For ports on Ethernet MDA's, the value of this object will
             be 'unknown'.";
          smiv2:max-access "read-only";
          smiv2:oid "1.3.6.1.4.1.6527.3.1.2.2.4.2.1.53";
          config false;
        }
        leaf tmnxPortParentPortID {
          type timetra-tc:TmnxPortID;
          description
            "tmnxPortParentPortID  is applicable only when the 'isSonet'
             and/or 'isTDM' bits in TIMETRA-CHASSIS-MIB:tmnxMDACapabilities are set.
             For SONET or TDM channel, it indicates the port ID of its parent
             channel or port.";
          smiv2:max-access "read-only";
          smiv2:oid "1.3.6.1.4.1.6527.3.1.2.2.4.2.1.54";
          config false;
        }
        leaf tmnxPortOpticalCompliance {
          type binary {
            length "8";
          }
          description
            "tmnxPortOpticalCompliance is applicable only when the
             tmnxPortSFPEquipped is set to 'true'. The value of
             tmnxPortOpticalCompliance indicates the 8 bytes of optical compliance
             bits stored in SFF EEPROMs.";
          smiv2:max-access "read-only";
          smiv2:oid "1.3.6.1.4.1.6527.3.1.2.2.4.2.1.55";
          config false;
        }
        leaf tmnxPortLoadBalanceAlgorithm {
          type enumeration {
            enum "notApplicable" {
              value 0;
            }
            enum "default" {
              value 1;
            }
            enum "includeL4" {
              value 2;
            }
            enum "excludeL4" {
              value 3;
            }
          }
          description
            "The value of tmnxPortLoadBalanceAlgorithm specifies the load
             balancing algorithm to be used on this port. When the
             value is 'includeL4', the src and dst port are used in the
             hashing algorithm. When it's 'excludeL4', they are not included.
             When the value is 'default', the port inherits the global settings
             in tmnxL4LoadBalancing. The value is 'notApplicable' for ports that
             do not pass any traffic. An attempt to modify this object when it is
             set to 'notApplicable' will return an inconsistentValue error.";
          smiv2:defval "default";
          smiv2:max-access "read-write";
          smiv2:oid "1.3.6.1.4.1.6527.3.1.2.2.4.2.1.56";
          config true;
        }
        leaf tmnxPortEgrPortSchedPlcy {
          type timetra-tc:TNamedItemOrEmpty;
          description
            "The value of tmnxPortEgrPortSchedPlcy specifies the egress QoS
             port-scheduler policy for this port. This object must correspond
             to the index of a row in TIMETRA-QOS-MIB::tPortSchedulerPlcyTable.
             
             A non-empty value for tmnxPortEgrPortSchedPlcy is only valid when the
             tmnxMDAAssignedType is a non-HSMDA MDA Type. Attempting to set
             tmnxPortEgrPortSchedPlcy to a non-empty string when the
             tmnxMDAAssignedType is a HSMDA MDA Type will return
             an 'inconsistentValue' error.";
          smiv2:defval "";
          smiv2:max-access "read-write";
          smiv2:oid "1.3.6.1.4.1.6527.3.1.2.2.4.2.1.57";
          config true;
        }
        leaf tmnxPortLastClearedTime {
          type yang:timestamp;
          description
            "The value of tmnxPortLastClearedTime indicates the sysUpTime
             when the counters in the IF-MIB:ifTable were last cleared.";
          smiv2:max-access "read-only";
          smiv2:oid "1.3.6.1.4.1.6527.3.1.2.2.4.2.1.58";
          config false;
        }
        leaf tmnxPortEgrHsmdaSchedPlcy {
          type timetra-tc:TNamedItemOrEmpty;
          description
            "The value of tmnxPortEgrHsmdaSchedPlcy specifies the egress QoS
             Hsmda-scheduler policy for this port. This object must correspond
             to the index of a row in TIMETRA-QOS-MIB::tHsmdaSchedulerPlcyTable,
             otherwise an 'inconsistentValue' error will be returned.
             
             When the tmnxMDAAssignedType is a non-HSMDA MDA Type, the value
             for tmnxPortEgrHsmdaSchedPlcy will be ignored. If the
             tmnxMDAAssignedType is a HSMDA MDA Type, the default for this
             object will be the string 'default'.";
          smiv2:defval "";
          smiv2:max-access "read-write";
          smiv2:oid "1.3.6.1.4.1.6527.3.1.2.2.4.2.1.59";
          config true;
        }
        leaf tmnxPortIngNamedPoolPlcy {
          type timetra-tc:TNamedItemOrEmpty;
          description
            "The value of tmnxPortIngNamedPoolPlcy specifies a named pool
             policy associated with an port ingress context. The policy
             governs the way named pools are created at the port level.";
          smiv2:defval "";
          smiv2:max-access "read-write";
          smiv2:oid "1.3.6.1.4.1.6527.3.1.2.2.4.2.1.60";
          config true;
        }
        leaf tmnxPortEgrNamedPoolPlcy {
          type timetra-tc:TNamedItemOrEmpty;
          description
            "The value of tmnxPortEgrNamedPoolPlcy specifies a named pool
             policy associated with an port egress context. The policy
             governs the way named pools are created at the port level.";
          smiv2:defval "";
          smiv2:max-access "read-write";
          smiv2:oid "1.3.6.1.4.1.6527.3.1.2.2.4.2.1.61";
          config true;
        }
        leaf tmnxPortIngPoolPercentRate {
          type uint32 {
            range "1..1000";
          }
          description
            "The value of tmnxPortIngPoolPercentRate specifies increment or
             decrement of the active bandwidth associated with the ingress port.
             This active bandwidth affects the amount of ingress buffer space
             managed by the port.";
          smiv2:defval "100";
          smiv2:max-access "read-write";
          smiv2:oid "1.3.6.1.4.1.6527.3.1.2.2.4.2.1.62";
          config true;
        }
        leaf tmnxPortEgrPoolPercentRate {
          type uint32 {
            range "1..1000";
          }
          description
            "The value of tmnxPortEgrPoolPercentRate specifies increment or
             decrement of the active bandwidth associated with the egress port.
             This active bandwidth affects the amount of egress buffer space
             managed by the port.
             
             The table below summarizes cases when the default value of 
             tmnxPortEgrPoolPercentRate differs from 100.
             
                 port behavior          default value
                 ------------------------------------
                 ISA-AA /to-sub                  1000
                 ISA-AA /fm-sub                   500";
          smiv2:defval "100";
          smiv2:max-access "read-write";
          smiv2:oid "1.3.6.1.4.1.6527.3.1.2.2.4.2.1.63";
          config true;
        }
        leaf tmnxPortDDMEventSuppression {
          type boolean;
          description
            "The value of tmnxPortDDMEventSuppression specifies whether or not an
             inserted SFF that supports Digital Diagnostic Monitoring
             raises traps and events (false) or suppresses all notifications
             (true).";
          smiv2:defval "false";
          smiv2:max-access "read-write";
          smiv2:oid "1.3.6.1.4.1.6527.3.1.2.2.4.2.1.64";
          config true;
        }
        leaf tmnxPortSFPStatus {
          type enumeration {
            enum "not-equipped" {
              value 0;
            }
            enum "operational" {
              value 1;
            }
            enum "read-error" {
              value 2;
            }
            enum "data-corrupt" {
              value 3;
            }
            enum "ddm-corrupt" {
              value 4;
            }
            enum "unsupported" {
              value 5;
            }
          }
          description
            "The value of tmnxPortSFPStatus indicates the operational status of
             the inserted SFF. If tmnxPortSFPEquipped is false, the
             tmnxPortSFPStatus will be 'not-equipped (0)', otherwise
             'operational (1)' if no failure is detected.
             
             A failure to read the SFF data will result in a 'read-error (2)',
             while corrupted information on the SFF will result in either
             'data-corrupt (3)', or 'ddm-corrupt (4)' if an SFF read results in
             invalid data or DDM information respectively.  An insertion of an
             unsupported SFF will result in 'unsupported (5)'.
             
             A trap will be raised if the value of tmnxPortSFPStatus indicates a
             failure; that is the tmnxPortSFPStatus is neither 'not-equipped (0)',
             nor 'operational (1)'.";
          smiv2:defval "not-equipped";
          smiv2:max-access "read-only";
          smiv2:oid "1.3.6.1.4.1.6527.3.1.2.2.4.2.1.65";
          config false;
        }
        leaf tmnxPortReasonDownFlags {
          type bits {
            bit unknown {
              position 0;
            }
            bit linklossFwd {
              position 1;
            }
            bit lagMemberPortStandby {
              position 2;
            }
            bit ethCfmFault {
              position 3;
            }
            bit opticalTuning {
              position 4;
            }
            bit channelOutOfRange {
              position 5;
            }
            bit channelNotConfigured {
              position 6;
            }
            bit crcError {
              position 7;
            }
            bit internalMacTxError {
              position 8;
            }
            bit efmOamDown {
              position 9;
            }
          }
          description
            "The tmnxPortReasonDownFlags indicates why a port may
             be in the operationally 'down' state. The following reasons are
             detected through this object:
                     unknown(0)              - Unspecified (or unknown)
                     linklossFwd(1)          - A sap using this port has an LLF
                                               operational status set to 'fault'
                     lagMemberPortStandby(2) - A lag using this port as a member
                                               port has set the member port to
                                               'standby' while configured to keep
                                               standby member ports down.
                     ethCfmFault(3)          - A facility MEP bound to this port
                                               has its dot1agCfmMepHighestPrDefect
                                               set to a value other than 'none (0)'.
                     opticalTuning(4)        - The DWDM optical receive signal is 
                                               undergoing tuning and analysis by
                                               control algorithms to find the
                                               optimal settings.
                     channelOutOfRange(5)    - The configured DWDM optical channel
                                               is out of range for the equipped
                                               tunable optical interface.
                     channelNotConfigured(6) - The DWDM optical channel is not
                                               configured for the equipped
                                               tunable optical interface.
                     crcError(7)             - CRC errors on the port exceeded the
                                               configured threshold.
                     internalMacTxError(8)   - An internal MAC tx error was detected
                                               on the port.
                     efmOamDown              - dot3OamOperStatus is not
                                               'operational'.";
          smiv2:max-access "read-only";
          smiv2:oid "1.3.6.1.4.1.6527.3.1.2.2.4.2.1.66";
          config false;
        }
        leaf tmnxPortSSMRxQualityLevel {
          type enumeration {
            enum "unknown" {
              value 0;
            }
            enum "prs" {
              value 1;
            }
            enum "stu" {
              value 2;
            }
            enum "st2" {
              value 3;
            }
            enum "tnc" {
              value 4;
            }
            enum "st3e" {
              value 5;
            }
            enum "st3" {
              value 6;
            }
            enum "smc" {
              value 7;
            }
            enum "st4" {
              value 8;
            }
            enum "dus" {
              value 9;
            }
            enum "prc" {
              value 10;
            }
            enum "ssua" {
              value 11;
            }
            enum "ssub" {
              value 12;
            }
            enum "sec" {
              value 13;
            }
            enum "dnu" {
              value 14;
            }
            enum "inv" {
              value 15;
            }
            enum "pno" {
              value 16;
            }
            enum "eec1" {
              value 17;
            }
            enum "eec2" {
              value 18;
            }
            enum "failed" {
              value 19;
            }
          }
          description
            "tmnxPortSSMRxQualityLevel indicates the SSM quality level
             of received SSM messages. On ports not supporting SSM, or not
             receiving SSM messages, the quality level will be 'unknown (0)'.
             
             The values 'prs (1)' through 'dus (9)' and 'pno (16)' correspond to
             quality levels defined in GR-253-CORE.  The values 'prc (10)' through
             'inv (15)' correspond to quality levels defined in G.781.
             The values 'eec1 (17)' and 'eec2 (18)' correspond to quality levels
             defines in G.8264.
             The value 'failed (19)' is used when there is a failure in the SSM 
             channel.";
          reference
            "Bellcore (Telcordia Technologies) GR-253-CORE, Issue 3, September 2000,
             5.4.2.
             ITU-T Recommendation G.781, June 1999.
             ITU-T Recommendation G.8264, October 2008.";
          smiv2:defval "unknown";
          smiv2:max-access "read-only";
          smiv2:oid "1.3.6.1.4.1.6527.3.1.2.2.4.2.1.67";
          config false;
        }
        leaf tmnxPortDwdmLaserChannel {
          type timetra-port:TmnxOpticalDwdmChannel;
          description
            "tmnxPortDwdmLaserChannel specifies the DWDM ITU channel at which a
             tunable optical interface will be configured to operate.
             
             A value of zero(0) can be specified only on an administratively
             disabled port or a port that is equipped with a non-tunable laser. To
             enable a port that is equipped with a tunable laser,
             tmnxPortDwdmLaserChannel must be changed to a valid DWDM ITU channel
             number in either the 50GHz, or 100GHz grid.";
          smiv2:defval "0";
          smiv2:max-access "read-write";
          smiv2:oid "1.3.6.1.4.1.6527.3.1.2.2.4.2.1.68";
          config true;
        }
        leaf tmnxPortOtuCapable {
          type boolean;
          description
            "The value of tmnxPortOtuCapable indicates whether or not the physical
             port supports the Optical Transport Unit (OTU) encapsulation.";
          smiv2:max-access "read-only";
          smiv2:oid "1.3.6.1.4.1.6527.3.1.2.2.4.2.1.69";
          config false;
        }
        leaf tmnxPortWaveTrackerCapable {
          type boolean;
          description
            "The value of tmnxPortWaveTrackerCapable indicates whether or not the
             physical port supports Wavelength Tracker.
             
             tmnxPortWaveTrackerCapable is equivalent to
             'tnWtEncodePortCapabilityPresent' of the 1696-Roadm MIBs.";
          smiv2:max-access "read-only";
          smiv2:oid "1.3.6.1.4.1.6527.3.1.2.2.4.2.1.70";
          config false;
        }
        leaf tmnxPortHybridIngAccessWeight {
          type uint32 {
            range "0..100";
          }
          description
            "The value of tmnxPortHybridIngAccessWeight specifies the increment or
             decrement of the ingress access weight associated with the port.
             This active weight affects the amount of ingress access buffer space
             managed by the port. This object only applies when tmnxPortMode is
             set to 'hybrid (3)'";
          smiv2:defval "50";
          smiv2:max-access "read-write";
          smiv2:oid "1.3.6.1.4.1.6527.3.1.2.2.4.2.1.71";
          config true;
        }
        leaf tmnxPortHybridIngNetworkWeight {
          type uint32 {
            range "0..100";
          }
          description
            "The value of tmnxPortHybridIngNetworkWeight specifies the increment or
             decrement of the ingress network weight associated with the port.
             This active weight affects the amount of ingress network buffer space
             managed by the port. This object only applies when tmnxPortMode is
             set to 'hybrid (3)'";
          smiv2:defval "50";
          smiv2:max-access "read-write";
          smiv2:oid "1.3.6.1.4.1.6527.3.1.2.2.4.2.1.72";
          config true;
        }
        leaf tmnxPortHybridEgrAccessWeight {
          type uint32 {
            range "0..100";
          }
          description
            "The value of tmnxPortHybridEgrAccessWeight specifies the increment or
             decrement of the egress access weight associated with the port.
             This active weight affects the amount of egress access buffer space
             managed by the port. This object only applies when tmnxPortMode is
             set to 'hybrid (3)'";
          smiv2:defval "50";
          smiv2:max-access "read-write";
          smiv2:oid "1.3.6.1.4.1.6527.3.1.2.2.4.2.1.73";
          config true;
        }
        leaf tmnxPortHybridEgrNetworkWeight {
          type uint32 {
            range "0..100";
          }
          description
            "The value of tmnxPortHybridEgrNetworkWeight specifies the increment or
             decrement of the egress network weight associated with the port.
             This active weight affects the amount of egress network buffer space
             managed by the port. This object only applies when tmnxPortMode is
             set to 'hybrid (3)'";
          smiv2:defval "50";
          smiv2:max-access "read-write";
          smiv2:oid "1.3.6.1.4.1.6527.3.1.2.2.4.2.1.74";
          config true;
        }
        leaf tmnxPortDwdmRxDtvAdjustEnable {
          type boolean;
          description
            "The value of tmnxPortDwdmRxDtvAdjustEnable specifies whether or not
             the Receive Decision threshold voltage adjustment feedback loop
             should be enabled.
             
             When this value is set to false, the optical receiver's default
             receive decision threshold voltage will be used.";
          smiv2:defval "true";
          smiv2:max-access "read-write";
          smiv2:oid "1.3.6.1.4.1.6527.3.1.2.2.4.2.1.75";
          config true;
        }
        leaf tmnxPortDwdmRxDtvDacPercent {
          type uint32 {
            range "0..10000";
          }
          units "Hundredths of a percent";
          description
            "The value of tmnxPortDwdmRxDtvDacPercent specifies the current
             relative adjustment of the receive decision threshold voltage
             in hundredths of a percent.
             
             50.00% is the optical receiver's default decision threshold
             voltage.";
          smiv2:defval "5000";
          smiv2:max-access "read-only";
          smiv2:oid "1.3.6.1.4.1.6527.3.1.2.2.4.2.1.76";
          config false;
        }
        leaf tmnxPortInterfaceGroupHandlerIdx {
          type uint32;
          description
            "The value of tmnxPortInterfaceGroupHandlerIdx indicates whether or not
             the physical port is a member of an Interface Group Handler.";
          smiv2:max-access "read-only";
          smiv2:oid "1.3.6.1.4.1.6527.3.1.2.2.4.2.1.77";
          config false;
        }
        leaf tmnxPortHoldTimeUnits {
          type enumeration {
            enum "seconds" {
              value 0;
            }
            enum "centiseconds" {
              value 1;
            }
          }
          description
            "The value of tmnxPortHoldTimeUnits specifies the measurable units of
             tmnxPortHoldTimeDown and tmnxPortHoldTimeUp.";
          smiv2:defval "seconds";
          smiv2:max-access "read-write";
          smiv2:oid "1.3.6.1.4.1.6527.3.1.2.2.4.2.1.78";
          config true;
        }
        leaf tmnxPortLinkLengthInfo {
          type binary {
            length "6";
          }
          description
            "The value of tmnxPortLinkLengthInfo indicates the link length info
             stored in SFF EEPROMs.
             
             tmnxPortLinkLengthInfo is applicable only when tmnxPortSFPEquipped is
             'true'; otherwise, all 6 bytes will have a value of '0'.
             
             See SFF Committee documents for details on the representation of
             the values in each byte. For SFP EEPROMs, the 6 bytes are bytes 14 to
             19 of the A0 bank inclusive, described in SFF Committee document
             SFF-8472. For XFP EEPROMs, the first 5 bytes are bytes 142 to 146 of
             the 01 bank inclusive, described in SFF Committee document INF-8077i.
             For XFP EEPROMs, byte 6 will have a value of '0'.";
          reference
            "SFF Committee, SFF-8472 Specification for Diagnostic Monitoring
             Interface for Optical Transceivers, Rev 11.0, September 14, 2010
             
             SFF Committee, INF-8077i 10 Gigabit Small Form Factor Pluggable
             Module, Rev 4.5, August 31, 2005";
          smiv2:max-access "read-only";
          smiv2:oid "1.3.6.1.4.1.6527.3.1.2.2.4.2.1.79";
          config false;
        }
        leaf tmnxPortSFPNumLanes {
          type uint32;
          description
            "The value of tmnxPortSFPNumLanes indicates the total number of lanes
             supported by the CSFP/QSFP.  If tmnxPortSFPEquipped is false, this
             object will have a value of '0'.";
          smiv2:max-access "read-only";
          smiv2:oid "1.3.6.1.4.1.6527.3.1.2.2.4.2.1.80";
          config false;
        }
        leaf tmnxPortPhysStateChangeCount {
          type yang:counter32;
          description
            "The value of tmnxPortPhysStateChangeCount indicates the number of times
             a physical port state has changed from 'linkDown (3)' to either
             'linkUp (4)' or 'up (5)' and from either 'linkUp (4)' or 'up (5)' to
             'linkDown (3)'.  The count does not include transitions between
             'linkUp (4)' and 'up (5)'.
             
             This counter is applicable to physical Ethernet ports only. All other
             ports maintain a count of 0.
             
             This object is automatically reset to zero, once the port enters the
             'ghost (2)' state.  To reset this object manually, one may use the
             tmnxClearTable entry whose tmnxClearName value is
             'clearPortPhysStateChangeCount' by specifying the tmnxClearParams value
             with 'port-id=<ifIndex>'.";
          smiv2:max-access "read-only";
          smiv2:oid "1.3.6.1.4.1.6527.3.1.2.2.4.2.1.81";
          config false;
        }
        config true;
      }
      config true;
    }
    container tmnxPortEtherTable {
      description
        "The tmnxPortEtherTable has an entry for each Ethernet
         (faste, gige, xcme or xgige) port on each IOM card in each chassis
         in the TMNX system.";
      smiv2:oid "1.3.6.1.4.1.6527.3.1.2.2.4.4";
      list tmnxPortEtherEntry {
        key "tmnxChassisIndex tmnxPortPortID";
        description
          "Each row entry represents an Ethernet port on a IOM card in a
           chassis in the system.  Entries cannot be created and
           deleted via SNMP SET operations.  Before an IOM card entry
           can be deleted from the tmnxMDATable, its supported
           tmnxPortEntry and tmnxPortEtherEntry rows must be in the proper
           state for removal.  The tmnxPortEtherEntry contains attributes
           that are unique to the Ethernet TmnxPortType.";
        smiv2:oid "1.3.6.1.4.1.6527.3.1.2.2.4.4.1";
        leaf tmnxChassisIndex {
          type leafref {
            path "/timetra-chassis:TIMETRA-CHASSIS-MIB/timetra-chassis:tmnxChassisTable/timetra-chassis:tmnxChassisEntry/timetra-chassis:tmnxChassisIndex";
          }
          config true;
        }
        leaf tmnxPortPortID {
          type leafref {
            path "/timetra-port:TIMETRA-PORT-MIB/timetra-port:tmnxPortTable/timetra-port:tmnxPortEntry/timetra-port:tmnxPortPortID";
          }
          config true;
        }
        leaf tmnxPortEtherMTU {
          type uint32 {
            range "0|512..9212";
          }
          units "bytes";
          description
            "The size of the largest packet which can be sent/received
             on the Ethernet physical interface, specified in octets.  For
             interfaces that are used for transmitting network datagrams,
             this is the size of the largest network datagram that can be
             sent on the interface.
             
             Setting tmnxPortEtherMTU to a value of zero (0), causes the agent
             to recalculate the default MTU size which can vary based on the
             current setting of tmnxPortMode and tmnxPortEncapType variables.
             Some typical default values are:
                    1514 with mode access and encap-type null
                    1518 with mode access and encap-type dot1q
                    1518 with mode access and encap-type mpls
                    9198 with mode network";
          smiv2:max-access "read-write";
          smiv2:oid "1.3.6.1.4.1.6527.3.1.2.2.4.4.1.1";
          config true;
        }
        leaf tmnxPortEtherDuplex {
          type enumeration {
            enum "notApplicable" {
              value 0;
            }
            enum "fullDuplex" {
              value 1;
            }
            enum "halfDuplex" {
              value 2;
            }
          }
          description
            "The tmnxPortEtherDuplex variable specifies the duplex mode used by
             the Ethernet interface if tmnxPortEtherAutoNegotiate has a value of
             'false' or 'limited'. If tmnxPortEtherAutoNegotiate has a value of
             'true', the link parameters are negotiated with the far end and
             the tmnxPortEtherDuplex variable is ignored. A value of 'fullDuplex'
             sets the link to full duplex mode.  A value of 'halfDuplex' sets
             the link to half duplex mode. tmnxPortEtherDuplex is only valid on
             Ethernet interfaces that support multiple duplex modes.";
          smiv2:defval "fullDuplex";
          smiv2:max-access "read-write";
          smiv2:oid "1.3.6.1.4.1.6527.3.1.2.2.4.4.1.2";
          config true;
        }
        leaf tmnxPortEtherSpeed {
          type enumeration {
            enum "notApplicable" {
              value 0;
            }
            enum "speed10" {
              value 1;
            }
            enum "speed100" {
              value 2;
            }
            enum "speed1000" {
              value 3;
            }
            enum "speed10000" {
              value 4;
            }
            enum "speed40000" {
              value 5;
            }
            enum "speed100000" {
              value 6;
            }
            enum "speed25000" {
              value 7;
            }
          }
          description
            "The tmnxPortEtherSpeed variable specifies the link speed of the
             Ethernet interface if tmnxPortEtherAutoNegotiate has a value of
             'false' or 'limited'.  If tmnxPortEtherAutoNegotiate has a value of
             'true', the link parameters are negotiated with the far end and
             the tmnxPortEtherSpeed variable is ignored. A value of 'speed10'
             sets the link to 10 mbps.  A value of 'speed100' sets the link to
             100 mbps.  A value of 'speed1000' sets the link to 1000 mbps (1 gbps).
             tmnxPortEtherSpeed is only valid on Ethernet interfaces that support
             multiple link speeds.";
          smiv2:max-access "read-write";
          smiv2:oid "1.3.6.1.4.1.6527.3.1.2.2.4.4.1.3";
          config true;
        }
        leaf tmnxPortEtherAutoNegotiate {
          type enumeration {
            enum "notApplicable" {
              value 0;
            }
            enum "true" {
              value 1;
            }
            enum "false" {
              value 2;
            }
            enum "limited" {
              value 3;
            }
          }
          description
            "When the value of tmnxPortEtherAutoNegotiate is 'true', the Ethernet
             interface will automatically negotiate link parameters with the far
             end (including speed and duplex), and will advertise all speeds and
             duplex modes supported by the interface. When the value of
             tmnxPortEtherAutoNegotiate is 'limited', the Ethernet interface will
             automatically negotiate link parameters with the far end, but will
             only advertise the speed and duplex mode specified by
             tmnxPortEtherSpeed and tmnxPortEtherDuplex. If
             tmnxPortEtherAutoNegotiate is 'false', the Ethernet interface will not
             negotiate link parameters with the far end and will instead force the
             speed and duplex mode to the values specified by tmnxPortEtherSpeed and
             tmnxPortEtherDuplex respectively.";
          smiv2:defval "true";
          smiv2:max-access "read-write";
          smiv2:oid "1.3.6.1.4.1.6527.3.1.2.2.4.4.1.4";
          config true;
        }
        leaf tmnxPortEtherOperDuplex {
          type enumeration {
            enum "notApplicable" {
              value 0;
            }
            enum "fullDuplex" {
              value 1;
            }
            enum "halfDuplex" {
              value 2;
            }
          }
          description
            "The tmnxPortEtherOperDuplex variable indicates the operational duplex
             mode of the Ethernet interface. A value of 'fullDuplex' indicates that
             the link is in full duplex mode.  A value of 'halfDuplex' indicates
             that the link is in half duplex mode. tmnxPortEtherOperDuplex is only
             valid if tmnxPortClass is 'faste' or 'xcme'.";
          smiv2:max-access "read-only";
          smiv2:oid "1.3.6.1.4.1.6527.3.1.2.2.4.4.1.5";
          config false;
        }
        leaf tmnxPortEtherOperSpeed {
          type uint32;
          units "mega-bits per second";
          description
            "The tmnxPortEtherOperSpeed variable indicates the operational speed
             of the Ethernet interface in mega-bits per second (mbps).  If the value
             of tmnxPortEtherAutoNegotiate is 'true', the link autonegotiates the
             link parameters with the far end side.  The value of
             tmnxPortEtherOperSpeed is only valid if tmnxPortClass is one of the
             Ethernet classes.";
          smiv2:max-access "read-only";
          smiv2:oid "1.3.6.1.4.1.6527.3.1.2.2.4.4.1.6";
          config false;
        }
        leaf tmnxPortEtherAcctPolicyId {
          type uint32 {
            range "0..99";
          }
          description
            "The value of the accounting policy must be defined prior to associating
             the policy with the ethernet port. Accounting policies can only be
             associated with network ports.
             A non-zero value indicates the tmnxLogApPolicyId index identifying the
             policy entry in the tmnxLogApTable from the TIMETRA-LOG-MIB which is
             associated with this port.  A zero value indicates that there is no
             accounting policy associated with this port";
          smiv2:defval "0";
          smiv2:max-access "read-write";
          smiv2:oid "1.3.6.1.4.1.6527.3.1.2.2.4.4.1.7";
          config true;
        }
        leaf tmnxPortEtherCollectStats {
          type boolean;
          description
            "Enable/disable the collection of accounting and statistical data
             for the network ethernet port. When applying accounting policies the
             data by default will be collected in the appropriate records and
             written to the designated billing file.
             When the value is set to false, the statistics are still accumulated
             by the IOM cards, however, the CPU will not obtain the results and
             write them to the billing file.";
          smiv2:defval "false";
          smiv2:max-access "read-write";
          smiv2:oid "1.3.6.1.4.1.6527.3.1.2.2.4.4.1.8";
          config true;
        }
        leaf tmnxPortEtherMDIMDIX {
          type enumeration {
            enum "unknown" {
              value 0;
            }
            enum "mdi" {
              value 1;
            }
            enum "mdix" {
              value 2;
            }
          }
          description
            "The tmnxPortEtherMDIMDIX variable indicates whether the Ethernet
             interface is of type 'mdi' (Media Dependent Interface) or
             'mdix' (Media Dependent Interface with crossover). If the agent
             cannot identify the type of Ethernet interface the value
             'unknown (0)' is indicated. tmnxPortEtherMDIMDIX is only valid if
             tmnxPortClass is 'faste' or 'xcme'.";
          smiv2:max-access "read-only";
          smiv2:oid "1.3.6.1.4.1.6527.3.1.2.2.4.4.1.9";
          config false;
        }
        leaf tmnxPortEtherXGigMode {
          type enumeration {
            enum "notApplicable" {
              value 0;
            }
            enum "lan" {
              value 1;
            }
            enum "wan" {
              value 2;
            }
          }
          description
            "The tmnxPortEtherXGigMode variable specifies whether the Ethernet
             interface is in LAN or WAN mode. tmnxPortEtherXGigMode must be
             'notApplicable' if tmnxPortClass is not 'xgige'.";
          smiv2:defval "lan";
          smiv2:max-access "read-write";
          smiv2:oid "1.3.6.1.4.1.6527.3.1.2.2.4.4.1.10";
          config true;
        }
        leaf tmnxPortEtherEgressRate {
          type int32 {
            range "-1|1..100000000";
          }
          units "kilo-bits per second";
          description
            "The tmnxPortEtherEgressRate variable specifies the maximum egress
             bandwidth (in kilo-bits per second) that the Ethernet interface
             can generate. A value of -1 means that the limit is the actual
             physical limit. If the provisioned sub-rate bandwidth is larger than
             the actual physical bandwidth of the interface, the latter applies.";
          smiv2:defval "-1";
          smiv2:max-access "read-write";
          smiv2:oid "1.3.6.1.4.1.6527.3.1.2.2.4.4.1.11";
          config true;
        }
        leaf tmnxPortEtherDot1qEtype {
          type uint32 {
            range "1536..65535";
          }
          description
            "The tmnxPortEtherDot1qEtype variable indicates the ethertype expected
             when the port's encapsulation type is dot1qEncap.";
          smiv2:defval "33024";
          smiv2:max-access "read-write";
          smiv2:oid "1.3.6.1.4.1.6527.3.1.2.2.4.4.1.12";
          config true;
        }
        leaf tmnxPortEtherQinqEtype {
          type uint32 {
            range "1536..65535";
          }
          description
            "The tmnxPortEtherQinqEtype variable indicates the ethertype expected
             when the port's encapsulation type is qinqEncap.";
          smiv2:defval "33024";
          smiv2:max-access "read-write";
          smiv2:oid "1.3.6.1.4.1.6527.3.1.2.2.4.4.1.13";
          config true;
        }
        leaf tmnxPortEtherIngressRate {
          type int32 {
            range "-1|1..100000";
          }
          units "mega-bits per second";
          description
            "The tmnxPortEtherIngressRate variable specifies the maximum ingress
             bandwidth (in mega-bits per second) that the Ethernet interface
             can receive. A value of -1 means that the limit is the actual
             physical limit. If the provisioned sub-rate bandwidth is larger than
             the actual physical bandwidth of the interface, the latter applies.
             
             For interfaces that support more than 10Gbps, the configured value
             must be specified as a multiple of 10Mbps; otherwise, the
             configuration will be rejected with an inconsistentValue error.";
          smiv2:defval "-1";
          smiv2:max-access "read-write";
          smiv2:oid "1.3.6.1.4.1.6527.3.1.2.2.4.4.1.14";
          config true;
        }
        leaf tmnxPortEtherReportAlarm {
          type timetra-port:TmnxPortEtherReportStatus;
          description
            "The value of tmnxPortEtherReportAlarm determines when and if to
             generate tmnxEqPortEtherAlarm and tmnxEqPortEtherAlarmClear.";
          smiv2:defval "{remoteFault, localFault}";
          smiv2:max-access "read-write";
          smiv2:oid "1.3.6.1.4.1.6527.3.1.2.2.4.4.1.15";
          config true;
        }
        leaf tmnxPortEtherReportAlarmStatus {
          type timetra-port:TmnxPortEtherReportStatus;
          description
            "The value of tmnxPortEtherReportAlarmStatus indicates the alarms on
             this port.";
          smiv2:max-access "read-only";
          smiv2:oid "1.3.6.1.4.1.6527.3.1.2.2.4.4.1.16";
          config false;
        }
        leaf tmnxPortEtherPkts1519toMax {
          type yang:counter32;
          units "Packets";
          description
            "The total number of packets received that were longer than 1518 octets
             but less than the maximum frame size for the particular medium, usually
             12287 octets (excluding framing bits, but including FCS octets) and
             were otherwise well formed.";
          smiv2:max-access "read-only";
          smiv2:oid "1.3.6.1.4.1.6527.3.1.2.2.4.4.1.17";
          config false;
        }
        leaf tmnxPortEtherHCOverPkts1519toMax {
          type yang:counter32;
          units "Packets";
          description
            "The number of times the associated tmnxPortEtherPkts1519toMax
             counter has overflowed.";
          smiv2:max-access "read-only";
          smiv2:oid "1.3.6.1.4.1.6527.3.1.2.2.4.4.1.18";
          config false;
        }
        leaf tmnxPortEtherHCPkts1519toMax {
          type yang:counter64;
          units "Packets";
          description
            "The total number of packets (including bad packets) received that were
             between 1519 octets in length and the maximum frame size, usually 12287
             octets inclusive (excluding framing bits but including FCS octets).
             
             The lower 32-bits of this 64-bit counter will equal the value of
             tmnxPortEtherHCPkts1519toMax.  The high 32-bits of this counter will
             equal the value of tmnxPortEtherHCOverPkts1519toMax.";
          smiv2:max-access "read-only";
          smiv2:oid "1.3.6.1.4.1.6527.3.1.2.2.4.4.1.19";
          config false;
        }
        leaf tmnxPortEtherLacpTunnel {
          type boolean;
          description
            "The value of tmnxPortEtherLacpTunnel specifies whether the LACP
             packet tunneling for the ethernet port is enabled or disabled.
             When tunneling is enabled, the port will not process any LACP
             packets but will tunnel them through instead. Also, the port
             cannot be added as a member to a LAG group, and vice versa.";
          smiv2:defval "false";
          smiv2:max-access "read-write";
          smiv2:oid "1.3.6.1.4.1.6527.3.1.2.2.4.4.1.20";
          config true;
        }
        leaf tmnxPortEtherDownWhenLoopedEnabled {
          type boolean;
          description
            "The value of tmnxPortEtherDownWhenLoopedEnabled specifies whether
             physical loop detection for the Ethernet port is enabled or
             disabled.  When enabled, the port will periodically send out
             keep-alive PDUs with an EtherType of 0x9000.  If the port
             receives a keep-alive that it transmitted, tmnxPortState will be
             set to 'linkUp' if it was previously 'up'. The port will not move
             back to tmnxPortState 'up' for a period of time defined by
             tmnxPortEtherDownWhenLoopedRetry, but will continue to periodically
             send out keep-alive PDUs.  Every time the port receives a keep alive
             it sent while a loop has been detected, it will reset the time
             period that it will remain down as defined by
             tmnxPortEtherDownWhenLoopedRetry.";
          smiv2:defval "false";
          smiv2:max-access "read-write";
          smiv2:oid "1.3.6.1.4.1.6527.3.1.2.2.4.4.1.21";
          config true;
        }
        leaf tmnxPortEtherDownWhenLoopedKeepAlive {
          type uint32 {
            range "1..120";
          }
          units "seconds";
          description
            "The tmnxPortEtherDownWhenLoopedKeepAlive variable specifies the
             number of seconds between each keep alive PDU transmission.";
          smiv2:defval "10";
          smiv2:max-access "read-write";
          smiv2:oid "1.3.6.1.4.1.6527.3.1.2.2.4.4.1.22";
          config true;
        }
        leaf tmnxPortEtherDownWhenLoopedRetry {
          type uint32 {
            range "0|10..160";
          }
          units "seconds";
          description
            "The tmnxPortEtherDownWhenLoopedRetry variable specifies the minimum
             number of seconds the port should wait after detecting a loop before
             tmnxPortState can be set to 'up'.  A value of 0 specifies the the
             port should not set tmnxPortState to 'up' until the user
             administratively disables and re-enables the port by setting
             tmnxPortAdminStatus to 'outOfService' and then to 'inService'.";
          smiv2:defval "120";
          smiv2:max-access "read-write";
          smiv2:oid "1.3.6.1.4.1.6527.3.1.2.2.4.4.1.23";
          config true;
        }
        leaf tmnxPortEtherDownWhenLoopedState {
          type enumeration {
            enum "noLoopDetected" {
              value 1;
            }
            enum "loopDetected" {
              value 2;
            }
          }
          description
            "The value of tmnxPortEtherDownWhenLoopedState indicates whether
             a physical loop has been detected on the port or not.  If
             tmnxPortEtherDownWhenLoopedEnabled is set to 'false', this value
             will be 'noLoopDetected'.";
          smiv2:max-access "read-only";
          smiv2:oid "1.3.6.1.4.1.6527.3.1.2.2.4.4.1.24";
          config false;
        }
        leaf tmnxPortEtherPBBEtype {
          type uint32 {
            range "1536..65535";
          }
          description
            "The tmnxPortEtherPBBEtype variable indicates the Ethertype expected
             for Provider Backbone Bridging Frames.";
          smiv2:defval "35047";
          smiv2:max-access "read-write";
          smiv2:oid "1.3.6.1.4.1.6527.3.1.2.2.4.4.1.25";
          config true;
        }
        leaf tmnxPortEtherReasonDownFlags {
          type bits {
            bit unknown {
              position 0;
            }
            bit linklossFwd {
              position 1;
            }
            bit lagMemberPortStandby {
              position 2;
            }
          }
          status obsolete;
          description
            "The tmnxPortEtherReasonDownFlags indicates why an ethernet port may
             be in the operationally 'down' state. The following reasons are
             detected through this object:
                     unknown(0)              - Unspecified (or unknown)
                     linklossFwd(1)          - A sap using this port has the object
                                               'sapEthernetLLFOperStatus' set to
                                               'fault'
                     lagMemberPortStandby(2) - A lag using this port as a member
                                               port has set the member port to
                                               'standby' while configured to keep
                                               standby member ports down.";
          smiv2:max-access "read-only";
          smiv2:oid "1.3.6.1.4.1.6527.3.1.2.2.4.4.1.26";
          config false;
        }
        leaf tmnxPortEtherSingleFiber {
          type boolean;
          description
            "tmnxPortEtherSingleFiber is used to enable/disable packet gathering and
             redirection of IP packets from a single fiber on RX port of the
             Ethernet interface and redistribute packets to other interfaces
             through either state routes or policy-based forwarding.";
          smiv2:defval "false";
          smiv2:max-access "read-write";
          smiv2:oid "1.3.6.1.4.1.6527.3.1.2.2.4.4.1.27";
          config true;
        }
        leaf tmnxPortEtherSSM {
          type boolean;
          description
            "tmnxPortEtherSSM specifies whether or not synchronous
             status messages (SSM) are enabled on the ethernet port.";
          smiv2:defval "false";
          smiv2:max-access "read-write";
          smiv2:oid "1.3.6.1.4.1.6527.3.1.2.2.4.4.1.28";
          config true;
        }
        leaf tmnxPortEtherDWLUseBroadcastAddr {
          type boolean;
          description
            "tmnxPortEtherDWLUseBroadcastAddr specifies whether or not the
             Down When Looped destination MAC address is the broadcast address,
             'true (1)', or the local port mac address, as specified in
             tmnxPortMacAddress, 'false (2)'.";
          smiv2:defval "false";
          smiv2:max-access "read-write";
          smiv2:oid "1.3.6.1.4.1.6527.3.1.2.2.4.4.1.29";
          config true;
        }
        leaf tmnxPortEtherSSMCodeType {
          type enumeration {
            enum "unknown" {
              value 1;
            }
            enum "sonet" {
              value 2;
            }
            enum "sdh" {
              value 3;
            }
          }
          description
            "The value of tmnxPortEtherSSMCodeType specifies the code-type
             used by the Synchronous Status Message (SSM) channel.";
          smiv2:defval "sdh";
          smiv2:max-access "read-write";
          smiv2:oid "1.3.6.1.4.1.6527.3.1.2.2.4.4.1.30";
          config true;
        }
        leaf tmnxPortEtherSSMTxDus {
          type boolean;
          description
            "The value of tmnxPortEtherSSMTxDus specifies whether or not the
             value 0xF (dus/dnu) is forced in the Synchronous Status Message (SSM)
             channel.";
          smiv2:defval "false";
          smiv2:max-access "read-write";
          smiv2:oid "1.3.6.1.4.1.6527.3.1.2.2.4.4.1.31";
          config true;
        }
        leaf tmnxPortEtherSSMRxEsmc {
          type uint32 {
            range "0..255";
          }
          description
            "The value of tmnxPortEtherSSMRxEsmc indicates the SSM code received on
             the Ethernet Synchronization Messaging Channel of the Ethernet port.
             
             The value returned for this object is only meaningful if
             tmnxPortEtherSSM is 'true', and tmnxPortSSMRxQualityLevel is not
             'failed'.";
          reference "ITU-T Recommendation G.8264, October 2008.";
          smiv2:max-access "read-only";
          smiv2:oid "1.3.6.1.4.1.6527.3.1.2.2.4.4.1.32";
          config false;
        }
        leaf tmnxPortEtherSSMTxQualityLevel {
          type enumeration {
            enum "reserved0" {
              value 0;
            }
            enum "prs" {
              value 1;
            }
            enum "stu" {
              value 2;
            }
            enum "st2" {
              value 3;
            }
            enum "tnc" {
              value 4;
            }
            enum "st3e" {
              value 5;
            }
            enum "reserved6" {
              value 6;
            }
            enum "smc" {
              value 7;
            }
            enum "reserved8" {
              value 8;
            }
            enum "dus" {
              value 9;
            }
            enum "prc" {
              value 10;
            }
            enum "ssua" {
              value 11;
            }
            enum "ssub" {
              value 12;
            }
            enum "reserved13" {
              value 13;
            }
            enum "dnu" {
              value 14;
            }
            enum "reserved15" {
              value 15;
            }
            enum "pno" {
              value 16;
            }
            enum "eec1" {
              value 17;
            }
            enum "eec2" {
              value 18;
            }
            enum "reserved19" {
              value 19;
            }
          }
          description
            "The value of tmnxPortEtherSSMTxQualityLevel indicates the quality
             level transmitted in the Ethernet Synchronization Messaging Channel.";
          reference "ITU-T Recommendation G.8264, October 2008.";
          smiv2:max-access "read-only";
          smiv2:oid "1.3.6.1.4.1.6527.3.1.2.2.4.4.1.33";
          config false;
        }
        leaf tmnxPortEtherCrcMonSdThreshold {
          type uint32 {
            range "0..9";
          }
          description
            "The value of tmnxPortEtherCrcMonSdThreshold specifies a packet error
             rate threshold used to determine when to send a tmnxEqPortEtherCrcAlarm
             notification for a CRC Signal Degradation (SD) failure and
             tmnxEqPortEtherCrcAlarmClear notification for a CRC SD failure clear.
             
             tmnxPortEtherCrcMonSdThreshold is the absolute value of the exponent of
             the rate expressed as 10e-n.
             
             The CRC SD error rate threshold is calculated as:
             tmnxPortEtherCrcMonSdTMultiplier * 10e-tmnxPortEtherCrcMonSdThreshold.
             
             A value of 0 disables CRC SD monitioring.";
          smiv2:defval "0";
          smiv2:max-access "read-write";
          smiv2:oid "1.3.6.1.4.1.6527.3.1.2.2.4.4.1.34";
          config true;
        }
        leaf tmnxPortEtherCrcMonSdTMultiplier {
          type uint32 {
            range "1..9";
          }
          description
            "The value of tmnxPortEtherCrcMonSdTMultiplier specifies the
             tmnxPortEtherCrcMonSdThreshold multiplier value.
             
             The CRC SD error rate threshold is calculated as:
             tmnxPortEtherCrcMonSdTMultiplier * 10e-tmnxPortEtherCrcMonSdThreshold.";
          smiv2:defval "1";
          smiv2:max-access "read-write";
          smiv2:oid "1.3.6.1.4.1.6527.3.1.2.2.4.4.1.35";
          config true;
        }
        leaf tmnxPortEtherCrcMonSfThreshold {
          type uint32 {
            range "0..9";
          }
          description
            "The value of tmnxPortEtherCrcMonSfThreshold specifies a packet error
             rate threshold used to determine when to send a tmnxEqPortEtherCrcAlarm
             notification for a CRC Signal Failure (SF) failure.
             
             Crossing the tmnxPortEtherCrcMonSfThreshold will result in the
             tmnxPortOperStatus being set to 'outOfService'.
             
             tmnxPortEtherCrcMonSfThreshold is the absolute value of the exponent of
             the rate expressed as 10e-n.
             
             The CRC SF error rate threshold is calculated as:
             tmnxPortEtherCrcMonSfTMultiplier * 10e-tmnxPortEtherCrcMonSfThreshold.
             
             A value of 0 disables CRC SF montioring.";
          smiv2:defval "0";
          smiv2:max-access "read-write";
          smiv2:oid "1.3.6.1.4.1.6527.3.1.2.2.4.4.1.36";
          config true;
        }
        leaf tmnxPortEtherCrcMonSfTMultiplier {
          type uint32 {
            range "1..9";
          }
          description
            "The value of tmnxPortEtherCrcMonSfTMultiplier specifies the
             tmnxPortEtherCrcMonSfThreshold multiplier value.
             
             The CRC SF error rate threshold is calculated as:
             tmnxPortEtherCrcMonSfTMultiplier * 10e-tmnxPortEtherCrcMonSfThreshold.";
          smiv2:defval "1";
          smiv2:max-access "read-write";
          smiv2:oid "1.3.6.1.4.1.6527.3.1.2.2.4.4.1.37";
          config true;
        }
        leaf tmnxPortEtherCrcMonWindowSize {
          type uint32 {
            range "5..60";
          }
          units "seconds";
          description
            "The value of tmnxPortEtherCrcMonWindowSize specifies the size of the
             sliding window in seconds over which the tmnxPortEtherCrcMonSdThreshold
             and tmnxPortEtherCrcMonSfThreshold are applied.";
          smiv2:defval "10";
          smiv2:max-access "read-write";
          smiv2:oid "1.3.6.1.4.1.6527.3.1.2.2.4.4.1.38";
          config true;
        }
        leaf tmnxPortEtherCrcAlarmReason {
          type timetra-port:TmnxPortEtherCrcMonReportStatus;
          description
            "The value of tmnxPortEtherCrcAlarmReason indicates the current
             status of the Ethernet CRC Monitored alarms on the port.";
          smiv2:max-access "read-only";
          smiv2:oid "1.3.6.1.4.1.6527.3.1.2.2.4.4.1.39";
          config false;
        }
        leaf tmnxPortEtherDownOnInternalError {
          type boolean;
          description
            "The value of tmnxPortEtherDownOnInternalError specifies whether
             or not the port is monitored for excessive internal MAC tx errors.
             
             When enabled, excess Internal MAC tx errors results in the
             tmnxPortOperStatus being set to 'outOfService (3)' and a
             tmnxEqPortEtherInternalAlarm notification trap.";
          smiv2:defval "false";
          smiv2:max-access "read-write";
          smiv2:oid "1.3.6.1.4.1.6527.3.1.2.2.4.4.1.40";
          config true;
        }
        leaf tmnxPortEtherMinFrameLength {
          type uint32 {
            range "64|68";
          }
          units "Bytes";
          description
            "The value of tmnxPortEtherMinFrameLength specifies the minimum length
             of any frame transmitted out of the port.";
          smiv2:defval "64";
          smiv2:max-access "read-write";
          smiv2:oid "1.3.6.1.4.1.6527.3.1.2.2.4.4.1.41";
          config true;
        }
        leaf tmnxPortEtherPhysAcctPolicyId {
          type uint32 {
            range "0..99";
          }
          description
            "The value of tmnxPortEtherPhysAcctPolicyId specifies the
             TIMETRA-LOG-MIB::tmnxLogApPolicyId that identifies the policy entry in
             TIMETRA-LOG-MIB::tmnxLogApTable which is associated with this ethernet
             port for the purpose of collecting physical layer ethernet statistics.
             
             A zero value indicates that there is no accounting policy associated
             with this ethernet port.";
          smiv2:defval "0";
          smiv2:max-access "read-write";
          smiv2:oid "1.3.6.1.4.1.6527.3.1.2.2.4.4.1.42";
          config true;
        }
        leaf tmnxPortEtherPhysCollectStats {
          type boolean;
          description
            "The value of tmnxPortEtherPhysCollectStats specifies whether or not
             the collection of physical layer ethernet accounting and statistical
             data for the ethernet port is enabled.
             
             When a non-zero value is specified for tmnxPortEtherPhysAcctPolicyId
             and tmnxPortEtherPhysCollectStats is set to true, data will be
             collected in the appropriate records and written to the designated
             billing file.
             
             When a non-zero value is specified for tmnxPortEtherPhysAcctPolicyId
             and tmnxPortEtherPhysCollectStats is set to false, the statistics are
             still accumulated by the IOM cards; however, the CPM will not obtain
             the results and write them to the billing file.";
          smiv2:defval "false";
          smiv2:max-access "read-write";
          smiv2:oid "1.3.6.1.4.1.6527.3.1.2.2.4.4.1.43";
          config true;
        }
        leaf tmnxPortEtherOperPhyTxClock {
          type timetra-port:TmnxPortEtherOperPhyTxClock;
          description
            "The value of tmnxPortEtherOperPhyTxClock indicates the result
             of Master/Slave resolution on copper based Ethernet ports.
             tmnxPortEtherOperPhyTxClock is 'notApplicable' if tmnxPortClass
             is not 'xcme' and tmnxPortType is not 'portTypeXcmeTx' and
             'tmnxPortEtherOperSpeed' is not 1000.";
          smiv2:max-access "read-only";
          smiv2:oid "1.3.6.1.4.1.6527.3.1.2.2.4.4.1.44";
          config false;
        }
        config true;
      }
      config true;
    }
    container tmnxSonetTable {
      description
        "The tmnxSonetTable has an entry for each packet over Sonet
         port on each IOM card in each chassis in the TMNX system.";
      smiv2:oid "1.3.6.1.4.1.6527.3.1.2.2.4.5";
      list tmnxSonetEntry {
        key "tmnxChassisIndex tmnxPortPortID";
        description
          "Each row entry represents a packet over Sonet port on a
           IOM card in a chassis in the system.  Entries cannot be
           created and deleted via SNMP SET operations.  Before an IOM
           tmnxMDAEntry can be deleted from the tmnxMDATable, its
           supported tmnxPortEntry rows must be in the proper state for
           removal.  The tmnxSonetEntry contains attributes that are
           unique to the 'sonet' TmnxPortType.  It also contains attributes
           that are common to all sonet paths configured on a sonet port.
           The tmnxPortPortID for a sonet port includes a sonet path number
           in the lower bits.   If the sonet path number is zero, '0', it
           represents a single (clear) sonet path on the port that uses
           the full bandwidth of the sonet port.  All entries in this table
           have the sonet path number part of their tmnxPortPortID index
           value set to zero.";
        smiv2:oid "1.3.6.1.4.1.6527.3.1.2.2.4.5.1";
        leaf tmnxChassisIndex {
          type leafref {
            path "/timetra-chassis:TIMETRA-CHASSIS-MIB/timetra-chassis:tmnxChassisTable/timetra-chassis:tmnxChassisEntry/timetra-chassis:tmnxChassisIndex";
          }
          config true;
        }
        leaf tmnxPortPortID {
          type leafref {
            path "/timetra-port:TIMETRA-PORT-MIB/timetra-port:tmnxPortTable/timetra-port:tmnxPortEntry/timetra-port:tmnxPortPortID";
          }
          config true;
        }
        leaf tmnxSonetSpeed {
          type enumeration {
            enum "oc3" {
              value 1;
            }
            enum "oc12" {
              value 2;
            }
            enum "oc48" {
              value 3;
            }
            enum "oc192" {
              value 4;
            }
            enum "oc768" {
              value 5;
            }
            enum "oc1" {
              value 6;
            }
          }
          description
            "The rate of this optical facility.";
          smiv2:max-access "read-write";
          smiv2:oid "1.3.6.1.4.1.6527.3.1.2.2.4.5.1.1";
          config true;
        }
        leaf tmnxSonetClockSource {
          type enumeration {
            enum "loopTimed" {
              value 1;
            }
            enum "nodeTimed" {
              value 2;
            }
          }
          description
            "tmnxSonetClockSource configures the clock for transmitted data from
             either the internal clock ('nodeTimed') or from a clock recovered
             from the line's receive data stream ('loopTimed').";
          smiv2:defval "loopTimed";
          smiv2:max-access "read-write";
          smiv2:oid "1.3.6.1.4.1.6527.3.1.2.2.4.5.1.2";
          config true;
        }
        leaf tmnxSonetFraming {
          type enumeration {
            enum "unknown" {
              value 1;
            }
            enum "sonet" {
              value 2;
            }
            enum "sdh" {
              value 3;
            }
          }
          description
            "The value of tmnxSonetFraming indicates the type of framing used
             on this interface.";
          smiv2:defval "sonet";
          smiv2:max-access "read-write";
          smiv2:oid "1.3.6.1.4.1.6527.3.1.2.2.4.5.1.3";
          config true;
        }
        leaf tmnxSonetReportAlarm {
          type bits {
            bit notUsed {
              position 0;
            }
            bit loc {
              position 1;
            }
            bit lais {
              position 2;
            }
            bit lrdi {
              position 3;
            }
            bit ss1f {
              position 4;
            }
            bit sb1err {
              position 5;
            }
            bit lb2erSd {
              position 6;
            }
            bit lb2erSf {
              position 7;
            }
            bit slof {
              position 8;
            }
            bit slos {
              position 9;
            }
            bit stxptr {
              position 10;
            }
            bit srxptr {
              position 11;
            }
            bit lrei {
              position 12;
            }
          }
          description
            "The value of tmnxSonetReportAlarm determines when and if to
             generate tmnxEqPortSonetAlarm and tmnxEqPortSonetAlarmClear
             notifications for this port:
                loc(1)      Reports a loss of clock which causes the operational
                            state of the port to be downed.  Set by default.
                lais(2)     Reports line alarm indication signal errors. Not set
                            by default.
                lrdi(3)     Reports line remote defect initiation errors.  LRDIs
                            are caused by remote LOF, LOC, and LOS.  Set by default.
                ss1f(4)     Reports section synchronization failure as reported by
                            the S1 byte.  Not set by default.
                sb1err(5)   Reports section B1 errors.  Not set by default.
                lb2erSd(6)  Reports line signal degradation BER errors.  Not set
                            by default.
                lb2erSf(7)  Reports line signal failure BER errors.  Set by default.
                slof(8)     Reports section loss of frame errors.  Set by default
                slos(9)     Reports section loss of signal errors. Set by default.
                stxptr(10)  Reports a section synchronization error on the transmit
                            side.  Indicates if there is a positive or negative
                            justification count per channel.  Not set by default.
                srxptr(11)  Reports a section synchronization error on the receive
                            side.  Indicates if there is a positive or negative
                            justification count per path.  Not set by default.
                lrei(12)    Reports a line error condition raised by the remote
                            as a result of B1 errors received from this node.
                            Not set by default.";
          smiv2:defval "{loc, lrdi, lb2erSf, slof, slos}";
          smiv2:max-access "read-write";
          smiv2:oid "1.3.6.1.4.1.6527.3.1.2.2.4.5.1.4";
          config true;
        }
        leaf tmnxSonetBerSdThreshold {
          type uint32 {
            range "3..9";
          }
          description
            "The value of tmnxSonetBerSdThreshold specifies a bit error rate (BER)
             threshold used to determine when to send a tmnxEqPortSonetAlarm
             notification for a BER SD failure and tmnxEqPortSonetAlarmClear
             notification for a BER SD failure clear.  tmnxSonetBerSdThreshold is
             the absolute value of the exponent of the rate expressed as 10e-n.";
          smiv2:defval "6";
          smiv2:max-access "read-write";
          smiv2:oid "1.3.6.1.4.1.6527.3.1.2.2.4.5.1.5";
          config true;
        }
        leaf tmnxSonetBerSfThreshold {
          type uint32 {
            range "3..6";
          }
          description
            "The value of tmnxSonetBerSfThreshold specifies a bit error rate (BER)
             threshold used to determine when to send a tmnxEqPortSonetAlarm
             notification for a BER SF failure and tmnxEqPortSonetAlarmClear
             notification for a BER SF failure clear.  tmnxSonetBerSdThreshold is
             the absolute value of the exponent of the rate expressed as 10e-n.";
          smiv2:defval "3";
          smiv2:max-access "read-write";
          smiv2:oid "1.3.6.1.4.1.6527.3.1.2.2.4.5.1.6";
          config true;
        }
        leaf tmnxSonetAps {
          type boolean;
          status obsolete;
          description
            "Automatic Protection Switching (APS) is supported on 7x50 systems
             by the APS-MIB and TIMETRA-APS-MIB.";
          smiv2:defval "false";
          smiv2:max-access "read-write";
          smiv2:oid "1.3.6.1.4.1.6527.3.1.2.2.4.5.1.7";
          config true;
        }
        leaf tmnxSonetApsAdminStatus {
          type timetra-chassis:TmnxPortAdminStatus;
          status obsolete;
          description
            "Automatic Protection Switching (APS) is supported on 7x50 systems
             by the APS-MIB and TIMETRA-APS-MIB.";
          smiv2:defval "inService";
          smiv2:max-access "read-write";
          smiv2:oid "1.3.6.1.4.1.6527.3.1.2.2.4.5.1.8";
          config true;
        }
        leaf tmnxSonetApsOperStatus {
          type timetra-port:TmnxPortOperStatus;
          status obsolete;
          description
            "Automatic Protection Switching (APS) is supported on 7x50 systems
             by the APS-MIB and TIMETRA-APS-MIB.";
          smiv2:max-access "read-only";
          smiv2:oid "1.3.6.1.4.1.6527.3.1.2.2.4.5.1.9";
          config false;
        }
        leaf tmnxSonetApsAuthKey {
          type binary {
            length "0..256";
          }
          status obsolete;
          description
            "Automatic Protection Switching (APS) is supported on 7x50 systems
             by the APS-MIB and TIMETRA-APS-MIB.";
          smiv2:defval "'0000000000000000'H";
          smiv2:max-access "read-write";
          smiv2:oid "1.3.6.1.4.1.6527.3.1.2.2.4.5.1.10";
          config true;
        }
        leaf tmnxSonetApsNeighborAddr {
          type inet:ipv4-address;
          status obsolete;
          description
            "Automatic Protection Switching (APS) is supported on 7x50 systems
             by the APS-MIB and TIMETRA-APS-MIB.";
          smiv2:defval "'00000000'H";
          smiv2:max-access "read-write";
          smiv2:oid "1.3.6.1.4.1.6527.3.1.2.2.4.5.1.11";
          config true;
        }
        leaf tmnxSonetApsAdvertiseInterval {
          type snmpv2-tc:TimeInterval;
          units "milliseconds";
          status obsolete;
          description
            "Automatic Protection Switching (APS) is supported on 7x50 systems
             by the APS-MIB and TIMETRA-APS-MIB.";
          smiv2:defval "1000";
          smiv2:max-access "read-write";
          smiv2:oid "1.3.6.1.4.1.6527.3.1.2.2.4.5.1.12";
          config true;
        }
        leaf tmnxSonetApsAdvertiseTimeLeft {
          type snmpv2-tc:TimeInterval;
          units "milliseconds";
          status obsolete;
          description
            "Automatic Protection Switching (APS) is supported on 7x50 systems
             by the APS-MIB and TIMETRA-APS-MIB.";
          smiv2:max-access "read-only";
          smiv2:oid "1.3.6.1.4.1.6527.3.1.2.2.4.5.1.13";
          config false;
        }
        leaf tmnxSonetApsHoldTime {
          type snmpv2-tc:TimeInterval;
          units "milliseconds";
          status obsolete;
          description
            "Automatic Protection Switching (APS) is supported on 7x50 systems
             by the APS-MIB and TIMETRA-APS-MIB.";
          smiv2:defval "3000";
          smiv2:max-access "read-write";
          smiv2:oid "1.3.6.1.4.1.6527.3.1.2.2.4.5.1.14";
          config true;
        }
        leaf tmnxSonetApsHoldTimeLeft {
          type snmpv2-tc:TimeInterval;
          units "milliseconds";
          status obsolete;
          description
            "Automatic Protection Switching (APS) is supported on 7x50 systems
             by the APS-MIB and TIMETRA-APS-MIB.";
          smiv2:max-access "read-only";
          smiv2:oid "1.3.6.1.4.1.6527.3.1.2.2.4.5.1.15";
          config false;
        }
        leaf tmnxSonetLoopback {
          type enumeration {
            enum "none" {
              value 0;
            }
            enum "line" {
              value 1;
            }
            enum "internal" {
              value 2;
            }
          }
          description
            "Activate a loopback on the SONET port. The SONET port must be in a
             shutdown state to activate any type of loopback.";
          smiv2:max-access "read-write";
          smiv2:oid "1.3.6.1.4.1.6527.3.1.2.2.4.5.1.16";
          config true;
        }
        leaf tmnxSonetReportAlarmStatus {
          type bits {
            bit notUsed {
              position 0;
            }
            bit loc {
              position 1;
            }
            bit lais {
              position 2;
            }
            bit lrdi {
              position 3;
            }
            bit ss1f {
              position 4;
            }
            bit sb1err {
              position 5;
            }
            bit lb2erSd {
              position 6;
            }
            bit lb2erSf {
              position 7;
            }
            bit slof {
              position 8;
            }
            bit slos {
              position 9;
            }
            bit stxptr {
              position 10;
            }
            bit srxptr {
              position 11;
            }
            bit lrei {
              position 12;
            }
          }
          description
            "The bits in this object are used for indicating the alarms. The bits
             are explained as follows:
                loc(1)      Indicates a loss of clock which causes the operational
                            state of the port to be downed.
                lais(2)     Indicates line alarm indication signal errors.
                lrdi(3)     Indicates line remote defect indication errors.  LRDIs
                            are caused by remote LOF, LOC, and LOS.
                ss1f(4)     Indicates section synchronization failure as reported by
                            the S1 byte.
                sb1err(5)   Indicates section B1 errors.
                lb2erSd(6)  Indicates line signal degradation BER errors.
                lb2erSf(7)  Indicates line signal failure BER errors.
                slof(8)     Indicates section loss of frame errors.
                slos(9)     Indicates section loss of signal errors.
                stxptr(10)  Indicates a section synchronization error on the
                            transmit side. Indicates if there is a positive or
                            negative justification count per channel.
                srxptr(11)  Indicates a section synchronization error on the receive
                            side.  Indicates if there is a positive or negative
                            justification count per sonet path.
                lrei(12)    Indicates a line error condition raised by the remote
                            as a result of B1 errors received from this node.";
          smiv2:max-access "read-only";
          smiv2:oid "1.3.6.1.4.1.6527.3.1.2.2.4.5.1.17";
          config false;
        }
        leaf tmnxSonetSectionTraceMode {
          type enumeration {
            enum "increment-z0" {
              value 1;
            }
            enum "byte" {
              value 2;
            }
            enum "string" {
              value 3;
            }
          }
          description
            "The tmnxSonetSectionTraceMode variable along with the
             tmnxSonetJ0String object determines the contents of
             the section trace bytes (j0/z0) in the SONET Section Header. If the
             mode is set to 'increment-z0', then the j0 byte is 0x01, and the
             z0 byte increments. If the mode is set to 'byte', then the j0 byte is
             the first octet of the tmnxSonetJ0String object and the z0 byte
             is 0xcc. If the mode is set to 'string', then the J0 byte is set to
             the 16 values in the tmnxSonetJ0String object and the z0 byte is
             0xcc.";
          smiv2:defval "byte";
          smiv2:max-access "read-write";
          smiv2:oid "1.3.6.1.4.1.6527.3.1.2.2.4.5.1.18";
          config true;
        }
        leaf tmnxSonetJ0String {
          type binary {
            length "0..16";
          }
          description
            "The tmnxSonetJ0String is used with the tmnxSonetSectionTraceMode
             variable to determine the contents of the j0 byte in the SONET Section
             Header. If the tmnxSonetSectionTraceMode is increment-z0, this object
             is ignored. If the mode is byte, then the first octet of this object is
             used for the J0 byte. If the mode is string, then the 16 bytes in this
             object are used for the J0 byte. If set to less than 16 bytes it, will
             be padded out to 16 with zeros. The default value is 0x01 and 15 NULLs";
          smiv2:defval "'01'H";
          smiv2:max-access "read-write";
          smiv2:oid "1.3.6.1.4.1.6527.3.1.2.2.4.5.1.19";
          config true;
        }
        leaf tmnxSonetMonS1Byte {
          type uint32 {
            range "0..255";
          }
          description
            "The tmnxSonetMonS1Byte variable reports the Synchronization Status
             Message from the S1 byte in the Line Overhead Header. A value of 0x00
             indicates unknown quality. A value of 0xF0 indicates
             `Do not use for synchronization`. Other values are documented in
             Telcordia GR253 and ITU G.707";
          smiv2:defval "204";
          smiv2:max-access "read-only";
          smiv2:oid "1.3.6.1.4.1.6527.3.1.2.2.4.5.1.20";
          config false;
        }
        leaf tmnxSonetMonJ0String {
          type binary {
            length "0..16";
          }
          description
            "The tmnxSonetMonJ0String variable reports the contents of the j0 byte
             in the SONET Section Header.";
          smiv2:max-access "read-only";
          smiv2:oid "1.3.6.1.4.1.6527.3.1.2.2.4.5.1.21";
          config false;
        }
        leaf tmnxSonetMonK1Byte {
          type uint32 {
            range "0..255";
          }
          description
            "The tmnxSonetMonK1Byte variable reports the Automatic Protection
             Switching(APS) signalling status from the K1 byte in the SONET
             Line Overhead Header.";
          smiv2:max-access "read-only";
          smiv2:oid "1.3.6.1.4.1.6527.3.1.2.2.4.5.1.22";
          config false;
        }
        leaf tmnxSonetMonK2Byte {
          type uint32 {
            range "0..255";
          }
          description
            "The tmnxSonetMonK1Byte variable reports the Automatic Protection
             Switching(APS) signalling status from the K2 byte in the SONET
             Line Overhead Header.";
          smiv2:max-access "read-only";
          smiv2:oid "1.3.6.1.4.1.6527.3.1.2.2.4.5.1.23";
          config false;
        }
        leaf tmnxSonetSingleFiber {
          type boolean;
          description
            "tmnxSonetSingleFiber is used to enable/disable packet gathering and
             redirection of IP packets from a single fiber on RX port of the
             SONET interface and redistribute packets to other interfaces
             through either state routes or policy-based forwarding.";
          smiv2:defval "false";
          smiv2:max-access "read-write";
          smiv2:oid "1.3.6.1.4.1.6527.3.1.2.2.4.5.1.24";
          config true;
        }
        leaf tmnxSonetHoldTimeUp {
          type uint32 {
            range "0..100";
          }
          units "100s of milliseconds";
          description
            "The value of tmnxSonetHoldTimeUp is used to configure the
             hold-timer for link up event dampening. This guards against
             reporting excessive interface transitions. This is implemented
             by not advertising subsequent transitions of the interface to
             upper layer protocols until the configured timer has expired.
             A value of zero (0) indicates that an up transition is reported
             immediately.";
          smiv2:defval "5";
          smiv2:max-access "read-write";
          smiv2:oid "1.3.6.1.4.1.6527.3.1.2.2.4.5.1.25";
          config true;
        }
        leaf tmnxSonetHoldTimeDown {
          type uint32 {
            range "0..100";
          }
          units "100s of milliseconds";
          description
            "The value of tmnxSonetHoldTimeDown is used to configure the
             hold-timer for link down event dampening. This guards against
             reporting excessive interface transitions. This is implemented
             by not advertising subsequent transitions of the interface to
             upper layer protocols until the configured timer has expired.
             A value of zero (0) indicates that a down transition is reported
             immediately.";
          smiv2:defval "0";
          smiv2:max-access "read-write";
          smiv2:oid "1.3.6.1.4.1.6527.3.1.2.2.4.5.1.26";
          config true;
        }
        leaf tmnxSonetSuppressLoOrderAlarm {
          type boolean;
          description
            "The value of tmnxSonetSuppressLoOrderAlarm specifies whether
             or not the lower order alarms on Sonet ports are suppressed.";
          smiv2:defval "false";
          smiv2:max-access "read-write";
          smiv2:oid "1.3.6.1.4.1.6527.3.1.2.2.4.5.1.27";
          config true;
        }
        leaf tmnxSonetTxDus {
          type boolean;
          description
            "The value of tmnxSonetTxDus specifies whether or not the value
             0xF (dus/dnu) is forced in the S1 overhead byte.";
          smiv2:defval "false";
          smiv2:max-access "read-write";
          smiv2:oid "1.3.6.1.4.1.6527.3.1.2.2.4.5.1.28";
          config true;
        }
        leaf tmnxSonetTxS1Byte {
          type uint32;
          description
            "The value of tmnxSonetTxS1Byte indicates the transmitted S1 Byte.";
          smiv2:max-access "read-only";
          smiv2:oid "1.3.6.1.4.1.6527.3.1.2.2.4.5.1.29";
          config false;
        }
        config true;
      }
      config true;
    }
    container tmnxSonetPathTable {
      description
        "The tmnxSonetPathTable has an entry for each sonet path
         configured in each packet over Sonet port on each IOM card
         in each chassis in the TMNX system.";
      smiv2:oid "1.3.6.1.4.1.6527.3.1.2.2.4.6";
      list tmnxSonetPathEntry {
        key "tmnxChassisIndex tmnxPortPortID";
        description
          "Each row entry represents a configured sonet path in a packet
           over Sonet port on a IOM card in a chassis in the system.
           The tmnxSonetPathEntry contains attributes that are
           unique to a sonet path of a 'sonet' TmnxPortType. The
           tmnxPortPortID for a sonet port includes a sonet path number
           in the lower bits.  If the sonet path number is zero, '0', it
           represents a single (clear) sonet path on the port that uses
           the full bandwidth of the sonet port.  Entries in this table
           that have the sonet path number part of their tmnxPortPortID
           index value set to zero cannot be created and deleted via
           SNMP SET operations.  They are created by the SNMP agent
           when the corresponding entry in the tmnxSonetTable is
           created.
           
           Entries with non-zero sonet path numbers can be created and
           deleted via SNMP SET operations using tmnxSonetPathRowStatus.
           When a row is created in the tmnxSonetPathTable, the
           agent also creates a row with the same index values in the
           tmnxPortTable.  In order to delete an entry,
           tmnxPortAdminStatus must first be set to 'outOfService'.  When
           the tmnxSonetPathEntry is deleted, the agent also deletes
           the corresponding row in the tmnxPortTable.";
        smiv2:oid "1.3.6.1.4.1.6527.3.1.2.2.4.6.1";
        leaf tmnxChassisIndex {
          type leafref {
            path "/timetra-chassis:TIMETRA-CHASSIS-MIB/timetra-chassis:tmnxChassisTable/timetra-chassis:tmnxChassisEntry/timetra-chassis:tmnxChassisIndex";
          }
          config true;
        }
        leaf tmnxPortPortID {
          type leafref {
            path "/timetra-port:TIMETRA-PORT-MIB/timetra-port:tmnxPortTable/timetra-port:tmnxPortEntry/timetra-port:tmnxPortPortID";
          }
          config true;
        }
        leaf tmnxSonetPathRowStatus {
          type snmpv2-tc:RowStatus;
          description
            "tmnxSonetPathRowStatus controls the creation and deletion of
             row entries in the tmnxSonetPathTable. The tmnxPortPortID
             for a sonet port includes a sonet path number in the lower bits.
             If the sonet path number is zero, '0', it represents a single
             (clear) sonet path on the port that uses the full bandwidth of
             the sonet port.  Entries in this table that have the sonet path
             number part of their tmnxPortPortID index value set to zero
             cannot be created and deleted via SNMP SET operations. They
             are created by the SNMP agent when the corresponding entry in
             the tmnxSonetTable is created.
             
             Entries with non-zero sonet path numbers can be created and deleted
             via SNMP SET operations.  When a row is created in the
             tmnxSonetPathTable, the agent also creates a row with the
             same index values in the tmnxPortTable.  In order to delete an
             entry, tmnxPortAdminStatus must first be set to 'outOfService'.
             When the tmnxSonetPathEntry is deleted, the agent also
             deletes the corresponding row in the tmnxPortTable for this
             sonet path port.";
          smiv2:max-access "read-write";
          smiv2:oid "1.3.6.1.4.1.6527.3.1.2.2.4.6.1.1";
          config false;
        }
        leaf tmnxSonetPathLastChangeTime {
          type yang:timestamp;
          description
            "The tmnxSonetPathLastChangeTime variable contains the sysUpTime
             value of the most recently modified writable variable in the
             tmnxSonetPathEntry row for this sonet path.";
          smiv2:max-access "read-only";
          smiv2:oid "1.3.6.1.4.1.6527.3.1.2.2.4.6.1.2";
          config false;
        }
        leaf tmnxSonetPathMTU {
          type uint32 {
            range "0|512..9208";
          }
          units "bytes";
          description
            "The size of the largest packet which can be sent/received
             on the sonet path, specified in octets.  For paths that
             are used for transmitting network datagrams, this is the
             size of the largest network datagram that can be sent on the
             sonet path.
             
             Setting tmnxSonetPathMTU to a value of zero (0), causes the agent
             to recalculate the default MTU size which can vary based on the
             current setting of tmnxPortMode and tmnxPortEncapType variables.
             Some typical default values are:
                    1522 with mode access and encap-type bcp-null
                    1526 with mode access and encap-type bcp-dot1q
                    1502 with mode access and encap-type ipcp
                    1506 with mode access and encap-type mplscp
                    1524 with mode access and encap-type atm
                    9208 with mode network";
          smiv2:max-access "read-write";
          smiv2:oid "1.3.6.1.4.1.6527.3.1.2.2.4.6.1.3";
          config true;
        }
        leaf tmnxSonetPathScramble {
          type boolean;
          description
            "If the tmnxSonetPathScramble variable is set to 'true',
             SONET (SDH) payload scrambling is enabled on this sonet path.
             Both ends of the connection must use the same scrambling
             algorithm.  If tmnxSonetPathScramble is set to 'false',
             scrambling is disabled.
             The default value for non-ATM paths is 'false'.
             The default value for ATM paths is 'true'
             
             If the value of tmnxSonetPathC2Byte is set to the default for
             the currently configured tmnxSonetPathScramble, then changing
             the value of tmnxSonetPathScramble  for non-ATM paths causes a change
             to tmnxSonetPathC2Byte to a default value for a new scrambling
             option. The default values are as follows:
             scrambled non-ATM sonet/sdh path - C2 Byte value is 0x16
             unscrambled non-ATM sonet/sdh path - C2 Byte value is 0xCF";
          smiv2:max-access "read-write";
          smiv2:oid "1.3.6.1.4.1.6527.3.1.2.2.4.6.1.4";
          config true;
        }
        leaf tmnxSonetPathC2Byte {
          type uint32 {
            range "0..254";
          }
          description
            "The tmnxSonetPathC2Byte variable is used configure the value
             used in the SONET/SDH C2 header byte.
             
             For paths on an MDA that does not support channelization:
             Setting C2 equal to 0x16 indicates scrambled sonet.
             
             Setting C2 equal to 0xCF indicates unscrambled sonet.
             
             Setting C2 equal to 0x13 indicates ATM.
             
             For paths on an MDA that supports channelization, the default
             value is based on the value of tmnxMDAMaxChannelization.
             For 'pdhDs3' or 'pdhE3' channelization, the default value is 0x04.
             
             Setting tmnxSonetPathC2Byte to a value of zero(0) causes the agent
             to assign the default value to this object.";
          smiv2:max-access "read-write";
          smiv2:oid "1.3.6.1.4.1.6527.3.1.2.2.4.6.1.5";
          config true;
        }
        leaf tmnxSonetPathJ1String {
          type binary {
            length "0..62";
          }
          description
            "The tmnxSonetPathJ1String variable is used to configure the sonet path
             trace string to be sent in the J1 Path Overhead bytes. The bytes
             must be printable ASCII. If the string is less than 62 bytes, it
             will be padded with NULLs. For SONET framing, an additional CR (0x0D)
             / LF (0x0A) pair will be added by the driver. For SDH framing only
             16 bytes are sent in the J1 bytes. The driver will set the MSB of
             the first byte, and put the first 15 bytes of the user configured string
             as the following bytes. The driver will set the CRC-7 of the 16 bytes
             into the other 7 bits of the first byte.
             
             The default value is `Alcatel 7x50 SR`.
             Setting a 1-byte long string containing 0xFF will restore the default.
             Setting the string 'zeros' will send all-zeros (ASCII NULL characters
             without CR/LF or CRC-7)in the J1 bytes.";
          smiv2:max-access "read-write";
          smiv2:oid "1.3.6.1.4.1.6527.3.1.2.2.4.6.1.6";
          config true;
        }
        leaf tmnxSonetPathCRC {
          type enumeration {
            enum "crc16" {
              value 1;
            }
            enum "crc32" {
              value 2;
            }
          }
          description
            "The value of tmnxSonetPathCRC variable indicates the precision of
             the cyclic redundancy check.  A value of 'crc16' is a 16-bit
             CRC calculation.  A value of 'crc32' is a 32-bit CRC
             calculation.  32-bit CRC increases the error detection ability,
             but it also adds some performance overhead.
             
             For paths with encapsulation set to ATM the default and only
             supported value is crc32 and applies to AAL5 CRC calculations
             on that path.";
          smiv2:defval "crc32";
          smiv2:max-access "read-write";
          smiv2:oid "1.3.6.1.4.1.6527.3.1.2.2.4.6.1.7";
          config true;
        }
        leaf tmnxSonetPathOperMTU {
          type uint32;
          units "bytes";
          description
            "The negotiated size of the largest packet which can be sent on
             the sonet path, specified in octets.  For sonet paths that are used
             for transmitting network datagrams, this is the size of the largest
             network datagram that can be sent on the sonet path.";
          smiv2:max-access "read-only";
          smiv2:oid "1.3.6.1.4.1.6527.3.1.2.2.4.6.1.8";
          config false;
        }
        leaf tmnxSonetPathOperMRU {
          type uint32;
          units "bytes";
          description
            "The negotiated size of the largest packet that can be received
             on the sonet path, specified in octets.";
          smiv2:max-access "read-only";
          smiv2:oid "1.3.6.1.4.1.6527.3.1.2.2.4.6.1.9";
          config false;
        }
        leaf tmnxSonetPathReportAlarm {
          type bits {
            bit notUsed {
              position 0;
            }
            bit pais {
              position 1;
            }
            bit plop {
              position 2;
            }
            bit prdi {
              position 3;
            }
            bit pb3err {
              position 4;
            }
            bit pplm {
              position 5;
            }
            bit prei {
              position 6;
            }
            bit puneq {
              position 7;
            }
            bit plcd {
              position 8;
            }
          }
          description
            "The value of tmnxSonetPathReportAlarm determines when and if to
             generate tmnxEqPortSonetPathAlarm and tmnxEqPortSonetPathAlarmClear
             notifications for this port:
                pais(1)     Reports path alarm indication signal errors. Not set by
                            default.
                plop(2)     Reports path loss of pointer (per tributary) errors.
                            Set by default.
                prdi(3)     Reports path remote defect indication errors.  Not set
                            by default.
                pb3err(4)   Reports path B3 errors.  Not set by default.
                pplm(5)     Reports a path payload mismatch.  As a result the
                            path will be operationally downed.  Set by default.
                prei(6)     Reports a path error condition raised by the remote as
                            a result of B3 errors received from this node.  Not
                            set by default.
                puneq(7)    Reports unequipped path errors. Set by default.
                plcd(8)     Reports path loss of codegroup delineation error.
                            It is applicable only when the value of
                            tmnxPortEtherXGigMode is set to 'wan'.
                            Not set by default.";
          smiv2:defval "{plop, pplm, puneq}";
          smiv2:max-access "read-write";
          smiv2:oid "1.3.6.1.4.1.6527.3.1.2.2.4.6.1.10";
          config true;
        }
        leaf tmnxSonetPathAcctPolicyId {
          type uint32 {
            range "0..99";
          }
          description
            "The value of the accounting policy must be defined prior to associating
             the policy with the sonet path. Accounting policies can only be
             associated with network sonet path.
             A non-zero value indicates the tmnxLogApPolicyId index identifying the
             policy entry in the tmnxLogApTable from the TIMETRA-LOG-MIB which is
             associated with this port.  A zero value indicates that there is no
             accounting policy associated with this port";
          smiv2:defval "0";
          smiv2:max-access "read-write";
          smiv2:oid "1.3.6.1.4.1.6527.3.1.2.2.4.6.1.11";
          config true;
        }
        leaf tmnxSonetPathCollectStats {
          type boolean;
          description
            "Enable/disable the collection of accounting and statistical data
             for the network sonet path. When applying accounting policies the
             data by default will be collected in the appropriate records and
             written to the designated billing file.
             When the value is set to false, the statistics are still accumulated
             by the IOM cards, however, the CPU will not obtain the results and
             write them to the billing file.";
          smiv2:defval "true";
          smiv2:max-access "read-write";
          smiv2:oid "1.3.6.1.4.1.6527.3.1.2.2.4.6.1.12";
          config true;
        }
        leaf tmnxSonetPathReportAlarmStatus {
          type bits {
            bit notUsed {
              position 0;
            }
            bit pais {
              position 1;
            }
            bit plop {
              position 2;
            }
            bit prdi {
              position 3;
            }
            bit pb3err {
              position 4;
            }
            bit pplm {
              position 5;
            }
            bit prei {
              position 6;
            }
            bit puneq {
              position 7;
            }
            bit plcd {
              position 8;
            }
          }
          description
            "The bits in this object are used for indicating the alarms. The bits
             are explained as follows:
                pais(1)     Indicates path alarm indication signal errors.
                plop(2)     Indicates path loss of pointer (per tributary) errors.
                prdi(3)     Indicates path remote defect indication errors.
                pb3err(4)   Indicates path B3 errors.
                pplm(5)     Indicates a path payload mismatch.
                prei(6)     Indicates a path error condition raised by the remote as
                            a result of B3 errors received from this node.
                puneq(7)    Indicates a far-end unequipped error.
                plcd(8)     Indicates a path loss of codegroup delineation error.
                            It is applicable only when the value of
                            tmnxPortEtherXGigMode is set to 'wan'.
                            Not set by default.";
          smiv2:max-access "read-only";
          smiv2:oid "1.3.6.1.4.1.6527.3.1.2.2.4.6.1.13";
          config false;
        }
        leaf tmnxSonetPathMonC2Byte {
          type uint32 {
            range "0..255";
          }
          description
            "The tmnxSonetPathC2Byte variable reports the value in the SONET/SDH
             C2 header byte.";
          smiv2:max-access "read-only";
          smiv2:oid "1.3.6.1.4.1.6527.3.1.2.2.4.6.1.14";
          config false;
        }
        leaf tmnxSonetPathMonJ1String {
          type binary {
            length "0..64";
          }
          description
            "The tmnxSonetPathJ1String variable reports the sonet path
             trace string received in the J1 Path Overhead bytes.";
          smiv2:max-access "read-only";
          smiv2:oid "1.3.6.1.4.1.6527.3.1.2.2.4.6.1.15";
          config false;
        }
        leaf tmnxSonetPathType {
          type enumeration {
            enum "ds3" {
              value 1;
            }
            enum "e3" {
              value 2;
            }
            enum "vtg" {
              value 3;
            }
            enum "tug-2" {
              value 4;
            }
            enum "tug-3" {
              value 5;
            }
          }
          status obsolete;
          description
            "tmnxSonetPathType specifies if the associated SONET/SDH Path
             is an asynchronous circuit, a virtual tributary group or
             a tributary unit group.
                ds3   - Configures the port or channel as service access(ds3)
                e3    - Configures the port or channel as service access(e3)
                vtg   - Configures the path as a virtual tributary group.
                tug-2 - Configures the path as a tributary unit group.
                tug-3 - Configures the port or channel for transport network use.";
          smiv2:defval "ds3";
          smiv2:max-access "read-write";
          smiv2:oid "1.3.6.1.4.1.6527.3.1.2.2.4.6.1.16";
          config true;
        }
        leaf tmnxSonetPathChildType {
          type timetra-chassis:TmnxMDAChanType;
          description
            "tmnxSonetPathChildType is used to configure the type of this path.
             Some typical default values are:
               pdhDs3 for STS-1 paths
               pdhE3 for TU3 paths
               pdhE1 for VT2 paths
               pdhDs1 for VT15 paths
             Examples of valid child path types are sonetSts3, sdhTug3,
             pdhDs3, pdhE3, sonetVt15, sonetVt2, pdhDs1 and pdhE1.";
          smiv2:max-access "read-write";
          smiv2:oid "1.3.6.1.4.1.6527.3.1.2.2.4.6.1.17";
          config true;
        }
        config true;
      }
      config true;
    }
    container tmnxPortTypeTable {
      description
        "The Port type table has an entry for each Alcatel-Lucent SROS series
         port model.";
      smiv2:oid "1.3.6.1.4.1.6527.3.1.2.2.4.7";
      list tmnxPortTypeEntry {
        key "tmnxPortTypeIndex";
        description
          "Each row entry represents an Alcatel-Lucent SROS series port model.
           Rows in this table are created by the agent at initialization and
           cannot be created or destroyed by SNMP Get or Set requests.";
        smiv2:oid "1.3.6.1.4.1.6527.3.1.2.2.4.7.1";
        leaf tmnxPortTypeIndex {
          type timetra-port:TmnxPortType;
          description
            "The unique index value which identifies this type of Alcatel-Lucent
             SROS series port model.";
          smiv2:max-access "not-accessible";
          smiv2:oid "1.3.6.1.4.1.6527.3.1.2.2.4.7.1.1";
        }
        leaf tmnxPortTypeName {
          type timetra-tc:TNamedItemOrEmpty;
          description
            "The administrative name that identifies this type of Alcatel-Lucent
             SROS series port model.  This name string may be used in CLI
             commands to specify a particular Port model type.";
          smiv2:max-access "read-only";
          smiv2:oid "1.3.6.1.4.1.6527.3.1.2.2.4.7.1.2";
        }
        leaf tmnxPortTypeDescription {
          type timetra-tc:TItemDescription;
          description
            "A detailed description of this Alcatel-Lucent SROS series port model.";
          smiv2:max-access "read-only";
          smiv2:oid "1.3.6.1.4.1.6527.3.1.2.2.4.7.1.3";
        }
        leaf tmnxPortTypeStatus {
          type boolean;
          description
            "When tmnxPortTypeStatus has a value of 'true' it indicates that
             this port model is supported in this revision of the management
             software.  When it has a value of 'false' there is no support.";
          smiv2:max-access "read-only";
          smiv2:oid "1.3.6.1.4.1.6527.3.1.2.2.4.7.1.4";
        }
      }
      config false;
    }
    container tmnxPortConnectTypeTable {
      description
        "The Port Connector type table has an entry for each Alcatel-Lucent
         SROS series port connector model.";
      smiv2:oid "1.3.6.1.4.1.6527.3.1.2.2.4.8";
      list tmnxPortConnectTypeEntry {
        key "tmnxPortConnectTypeIndex";
        description
          "Each row entry represents an Alcatel-Lucent SROS series port
           Connector model.  Rows in this table are created by the agent
           at initialization and cannot be created or destroyed by SNMP
           Get or Set requests.";
        smiv2:oid "1.3.6.1.4.1.6527.3.1.2.2.4.8.1";
        leaf tmnxPortConnectTypeIndex {
          type timetra-port:TmnxPortConnectorType;
          description
            "The unique index value which identifies this type of Alcatel-Lucent
             SROS series port connector model.";
          smiv2:max-access "not-accessible";
          smiv2:oid "1.3.6.1.4.1.6527.3.1.2.2.4.8.1.1";
        }
        leaf tmnxPortConnectTypeName {
          type timetra-tc:TNamedItemOrEmpty;
          description
            "The administrative name that identifies this type of Alcatel-Lucent
             SROS series port connector model.  This name string may be
             used in CLI commands to specify a particular port connector
             model type.";
          smiv2:max-access "read-only";
          smiv2:oid "1.3.6.1.4.1.6527.3.1.2.2.4.8.1.2";
        }
        leaf tmnxPortConnectTypeDescription {
          type timetra-tc:TItemDescription;
          description
            "A detailed description of this Alcatel-Lucent SROS series port
             connector model.";
          smiv2:max-access "read-only";
          smiv2:oid "1.3.6.1.4.1.6527.3.1.2.2.4.8.1.3";
        }
        leaf tmnxPortConnectTypeStatus {
          type boolean;
          description
            "When tmnxPortConnectTypeStatus has a value of 'true' it indicates that
             this port connector model is supported in this revision of the
             chassis management software.  When it has a value of 'false' there
             is no support.";
          smiv2:max-access "read-only";
          smiv2:oid "1.3.6.1.4.1.6527.3.1.2.2.4.8.1.4";
        }
      }
      config false;
    }
    container tmnxPortFCStatsTable {
      status obsolete;
      description
        "The Network Port FC Stats table has an entry for each forwarding
         class defined on each network port.";
      smiv2:oid "1.3.6.1.4.1.6527.3.1.2.2.4.9";
      list tmnxPortFCStatsEntry {
        key "tmnxChassisIndex tmnxPortPortID tmnxPortFCStatsIndex";
        status obsolete;
        description
          "Each row entry represents a set of ingress and egress packet and
           octet statistics for the given network port and forwarding class.
           Rows in this table are created by the agent when the network port
           is provisioned and cannot be created or destroyed by SNMP Get or
           Set requests.";
        smiv2:oid "1.3.6.1.4.1.6527.3.1.2.2.4.9.1";
        leaf tmnxChassisIndex {
          type leafref {
            path "/timetra-chassis:TIMETRA-CHASSIS-MIB/timetra-chassis:tmnxChassisTable/timetra-chassis:tmnxChassisEntry/timetra-chassis:tmnxChassisIndex";
          }
        }
        leaf tmnxPortPortID {
          type leafref {
            path "/timetra-port:TIMETRA-PORT-MIB/timetra-port:tmnxPortTable/timetra-port:tmnxPortEntry/timetra-port:tmnxPortPortID";
          }
        }
        leaf tmnxPortFCStatsIndex {
          type timetra-tc:TFCName;
          status obsolete;
          description
            "The forwarding class associated with these stats
             on this network port.";
          smiv2:max-access "not-accessible";
          smiv2:oid "1.3.6.1.4.1.6527.3.1.2.2.4.9.1.1";
        }
        leaf tmnxPortFCStatsIngFwdInProfPkts {
          type yang:counter64;
          status obsolete;
          description
            "The number of in-profile packets (rate below CIR)
             forwarded by the ingress Qchip.";
          smiv2:max-access "read-only";
          smiv2:oid "1.3.6.1.4.1.6527.3.1.2.2.4.9.1.2";
        }
        leaf tmnxPortFCStatsIngFwdOutProfPkts {
          type yang:counter64;
          status obsolete;
          description
            "The number of out-of-profile packets (rate above CIR)
             forwarded by the ingress Qchip.";
          smiv2:max-access "read-only";
          smiv2:oid "1.3.6.1.4.1.6527.3.1.2.2.4.9.1.3";
        }
        leaf tmnxPortFCStatsIngFwdInProfOcts {
          type yang:counter64;
          status obsolete;
          description
            "The number of in-profile octets (rate below CIR)
             forwarded by the ingress Qchip.";
          smiv2:max-access "read-only";
          smiv2:oid "1.3.6.1.4.1.6527.3.1.2.2.4.9.1.4";
        }
        leaf tmnxPortFCStatsIngFwdOutProfOcts {
          type yang:counter64;
          status obsolete;
          description
            "The number of out-of-profile octets (rate above CIR)
             forwarded by the ingress Qchip.";
          smiv2:max-access "read-only";
          smiv2:oid "1.3.6.1.4.1.6527.3.1.2.2.4.9.1.5";
        }
        leaf tmnxPortFCStatsIngDroInProfPkts {
          type yang:counter64;
          status obsolete;
          description
            "The number of in-profile packets (rate below CIR)
             dropped by the ingress Qchip due to: MBS exceeded,
             buffer pool limit exceeded, etc.";
          smiv2:max-access "read-only";
          smiv2:oid "1.3.6.1.4.1.6527.3.1.2.2.4.9.1.6";
        }
        leaf tmnxPortFCStatsIngDroOutProfPkts {
          type yang:counter64;
          status obsolete;
          description
            "The number of out-of-profile packets (rate above CIR)
             dropped by the ingress Qchip due to: MBS exceeded,
             buffer pool limit exceeded, etc.";
          smiv2:max-access "read-only";
          smiv2:oid "1.3.6.1.4.1.6527.3.1.2.2.4.9.1.7";
        }
        leaf tmnxPortFCStatsIngDroInProfOcts {
          type yang:counter64;
          status obsolete;
          description
            "The number of in-profile octets (rate below CIR)
             dropped by the ingress Qchip due to: MBS exceeded,
             buffer pool limit exceeded, etc.";
          smiv2:max-access "read-only";
          smiv2:oid "1.3.6.1.4.1.6527.3.1.2.2.4.9.1.8";
        }
        leaf tmnxPortFCStatsIngDroOutProfOcts {
          type yang:counter64;
          status obsolete;
          description
            "The number of out-of-profile octets (rate above CIR)
             dropped by the ingress Qchip due to: MBS exceeded,
             buffer pool limit exceeded, etc.";
          smiv2:max-access "read-only";
          smiv2:oid "1.3.6.1.4.1.6527.3.1.2.2.4.9.1.9";
        }
        leaf tmnxPortFCStatsEgrFwdInProfPkts {
          type yang:counter64;
          status obsolete;
          description
            "The number of in-profile packets (rate below CIR)
             forwarded by the egress Qchip.";
          smiv2:max-access "read-only";
          smiv2:oid "1.3.6.1.4.1.6527.3.1.2.2.4.9.1.10";
        }
        leaf tmnxPortFCStatsEgrFwdOutProfPkts {
          type yang:counter64;
          status obsolete;
          description
            "The number of out-of-profile packets (rate above CIR)
             forwarded by the egress Qchip.";
          smiv2:max-access "read-only";
          smiv2:oid "1.3.6.1.4.1.6527.3.1.2.2.4.9.1.11";
        }
        leaf tmnxPortFCStatsEgrFwdInProfOcts {
          type yang:counter64;
          status obsolete;
          description
            "The number of in-profile octets (rate below CIR)
             forwarded by the egress Qchip.";
          smiv2:max-access "read-only";
          smiv2:oid "1.3.6.1.4.1.6527.3.1.2.2.4.9.1.12";
        }
        leaf tmnxPortFCStatsEgrFwdOutProfOcts {
          type yang:counter64;
          status obsolete;
          description
            "The number of out-of-profile octets (rate above CIR)
             forwarded by the egress Qchip.";
          smiv2:max-access "read-only";
          smiv2:oid "1.3.6.1.4.1.6527.3.1.2.2.4.9.1.13";
        }
        leaf tmnxPortFCStatsEgrDroInProfPkts {
          type yang:counter64;
          status obsolete;
          description
            "The number of in-profile packets (rate below CIR)
             dropped by the egress Qchip due to: MBS exceeded,
             buffer pool limit exceeded, etc.";
          smiv2:max-access "read-only";
          smiv2:oid "1.3.6.1.4.1.6527.3.1.2.2.4.9.1.14";
        }
        leaf tmnxPortFCStatsEgrDroOutProfPkts {
          type yang:counter64;
          status obsolete;
          description
            "The number of out-of-profile packets (rate above CIR)
             dropped by the egress Qchip due to: MBS exceeded,
             buffer pool limit exceeded, etc.";
          smiv2:max-access "read-only";
          smiv2:oid "1.3.6.1.4.1.6527.3.1.2.2.4.9.1.15";
        }
        leaf tmnxPortFCStatsEgrDroInProfOcts {
          type yang:counter64;
          status obsolete;
          description
            "The number of in-profile octets (rate below CIR)
             dropped by the egress Qchip due to: MBS exceeded,
             buffer pool limit exceeded, etc.";
          smiv2:max-access "read-only";
          smiv2:oid "1.3.6.1.4.1.6527.3.1.2.2.4.9.1.16";
        }
        leaf tmnxPortFCStatsEgrDroOutProfOcts {
          type yang:counter64;
          status obsolete;
          description
            "The number of out-of-profile octets (rate above CIR)
             dropped by the egress Qchip due to: MBS exceeded,
             buffer pool limit exceeded, etc.";
          smiv2:max-access "read-only";
          smiv2:oid "1.3.6.1.4.1.6527.3.1.2.2.4.9.1.17";
        }
      }
      config false;
    }
    container tmnxDS3Table {
      description
        "The tmnxDS3Table has an entry for a DS3 physical port.";
      smiv2:oid "1.3.6.1.4.1.6527.3.1.2.2.4.10";
      list tmnxDS3Entry {
        key "tmnxChassisIndex tmnxPortPortID";
        description
          "Each row entry represents a physical DS3 port on a
           IOM card in a chassis in the system.  Entries cannot be created
           and deleted via SNMP SET operations.  Entries in this table will
           be created automatically when the tmnxMDAAssignedType object is
           set to the DS3 MDA type The tmnxDS3Entry contains attributes that are
           unique to the 'ds3e3' TmnxPortType. The tmnxPortPortID contains
           the slot, mda and port numbers encoded into it.
           
           For each tmnxDS3Entry, there will be a corresponding entry
           in the tmnxPortTable and the ifTable.";
        smiv2:oid "1.3.6.1.4.1.6527.3.1.2.2.4.10.1";
        leaf tmnxChassisIndex {
          type leafref {
            path "/timetra-chassis:TIMETRA-CHASSIS-MIB/timetra-chassis:tmnxChassisTable/timetra-chassis:tmnxChassisEntry/timetra-chassis:tmnxChassisIndex";
          }
          config true;
        }
        leaf tmnxPortPortID {
          type leafref {
            path "/timetra-port:TIMETRA-PORT-MIB/timetra-port:tmnxPortTable/timetra-port:tmnxPortEntry/timetra-port:tmnxPortPortID";
          }
          config true;
        }
        leaf tmnxDS3Buildout {
          type enumeration {
            enum "short" {
              value 1;
            }
            enum "long" {
              value 2;
            }
          }
          description
            "tmnxDS3Buildout configures the T3 line buildout. A T3 port has two
             settings for the T3 line buildout: a short setting, which is less
             than 225 feet, and a long setting, which is greater than 225 feet.
             This object applies to copper-cable-based T3 ports only.";
          smiv2:defval "short";
          smiv2:max-access "read-write";
          smiv2:oid "1.3.6.1.4.1.6527.3.1.2.2.4.10.1.1";
          config true;
        }
        leaf tmnxDS3LastChangeTime {
          type yang:timestamp;
          description
            "The tmnxDS3LastChangeTime variable contains the sysUpTime
             value of the most recently modified writable variable in the
             tmnxDS3Entry row for this port.";
          smiv2:max-access "read-only";
          smiv2:oid "1.3.6.1.4.1.6527.3.1.2.2.4.10.1.2";
          config false;
        }
        leaf tmnxDS3Type {
          type enumeration {
            enum "ds3" {
              value 1;
            }
            enum "e3" {
              value 2;
            }
          }
          description
            "tmnxDS3Type configures the type of the physical port to 'ds3' or 'e3'.";
          smiv2:defval "ds3";
          smiv2:max-access "read-write";
          smiv2:oid "1.3.6.1.4.1.6527.3.1.2.2.4.10.1.3";
          config true;
        }
        config true;
      }
      config true;
    }
    container tmnxDS3ChannelTable {
      description
        "The tmnxDS3ChannelTable has an entry for a DS3 channel.";
      smiv2:oid "1.3.6.1.4.1.6527.3.1.2.2.4.11";
      list tmnxDS3ChannelEntry {
        key "tmnxChassisIndex tmnxPortPortID";
        description
          "Each row entry represents a DS3 channel. Entries can be created
           and deleted via SNMP SET operations.  The tmnxDS3ChannelEntry
           contains attributes that are applicable to a DS3 channel which
           can belong to the DS3 physical port or belong to a container
           on a sonet path. The tmnxPortPortID contains the slot, mda and
           port numbers encoded into it.
           
           For each tmnxDS3ChannelEntry, there will be a corresponding entry
           in the tmnxPortTable and the ifTable.";
        smiv2:oid "1.3.6.1.4.1.6527.3.1.2.2.4.11.1";
        leaf tmnxChassisIndex {
          type leafref {
            path "/timetra-chassis:TIMETRA-CHASSIS-MIB/timetra-chassis:tmnxChassisTable/timetra-chassis:tmnxChassisEntry/timetra-chassis:tmnxChassisIndex";
          }
          config true;
        }
        leaf tmnxPortPortID {
          type leafref {
            path "/timetra-port:TIMETRA-PORT-MIB/timetra-port:tmnxPortTable/timetra-port:tmnxPortEntry/timetra-port:tmnxPortPortID";
          }
          config true;
        }
        leaf tmnxDS3ChannelRowStatus {
          type snmpv2-tc:RowStatus;
          description
            "tmnxDS3ChannelRowStatus controls the creation and deletion of
             row entries in the tmnxDS3ChannelTable.
             For row creation, the manager has to first calculate the
             tmnxPortPortID based on the TiMOS encoding scheme.";
          smiv2:max-access "read-write";
          smiv2:oid "1.3.6.1.4.1.6527.3.1.2.2.4.11.1.1";
          config false;
        }
        leaf tmnxDS3ChannelType {
          type enumeration {
            enum "ds3" {
              value 1;
            }
            enum "e3" {
              value 2;
            }
          }
          description
            "The value of tmnxDS3ChannelType indicates whether the channel is
             in DS3 or E3 mode.";
          smiv2:max-access "read-only";
          smiv2:oid "1.3.6.1.4.1.6527.3.1.2.2.4.11.1.2";
          config false;
        }
        leaf tmnxDS3ChannelFraming {
          type enumeration {
            enum "cbit" {
              value 1;
            }
            enum "m23" {
              value 2;
            }
            enum "g751" {
              value 3;
            }
            enum "g832" {
              value 4;
            }
            enum "e3-unframed" {
              value 5;
            }
            enum "ds3-unframed" {
              value 6;
            }
          }
          description
            "The value of tmnxDS3ChannelFraming indicates the type of framing
             associated with the DS3 channel.
             If tmnxDS3ChannelType is set to 'ds3', the default framing is 'cbit'.
             If tmnxDS3ChannelType is set to 'e3', the default framing is 'g751'.";
          smiv2:defval "cbit";
          smiv2:max-access "read-write";
          smiv2:oid "1.3.6.1.4.1.6527.3.1.2.2.4.11.1.3";
          config true;
        }
        leaf tmnxDS3ChannelClockSource {
          type timetra-port:TmnxDSXClockSource;
          description
            "tmnxDS3ChannelClockSource configures the clock for transmitted data
             from either the internal clock ('nodeTimed'), or from a clock
             recovered from the line's receive data stream ('loopTimed').";
          smiv2:defval "loopTimed";
          smiv2:max-access "read-write";
          smiv2:oid "1.3.6.1.4.1.6527.3.1.2.2.4.11.1.4";
          config true;
        }
        leaf tmnxDS3ChannelChannelized {
          type enumeration {
            enum "none" {
              value 1;
            }
            enum "ds1" {
              value 2;
            }
            enum "e1" {
              value 3;
            }
            enum "j1" {
              value 4;
            }
          }
          description
            "tmnxDS3ChannelChannelized is used to create sub-channels of type
             'ds1' or 'e1' or 'j1' on the interface. Setting the value to 'none'
             removes the sub-channels on the interface.";
          smiv2:defval "none";
          smiv2:max-access "read-write";
          smiv2:oid "1.3.6.1.4.1.6527.3.1.2.2.4.11.1.5";
          config true;
        }
        leaf tmnxDS3ChannelSubrateCSUMode {
          type enumeration {
            enum "notUsed" {
              value 0;
            }
            enum "digital-link" {
              value 1;
            }
          }
          description
            "tmnxDS3ChannelSubrateCSUMode configures the channel service unit (CSU)
             compatibility mode to interoperate with existing DS3 subrate
             standards.
             This configuration applies only for a non-channelized DS3.
             
             Changing the value of tmnxDS3ChannelSubrateCSUMode to notUsed resets
             the value of tmnxDS3ChannelScramble to 'false'.
             
             Changing the value of tmnxDS3ChannelSubrateCSUMode
             resets the value of tmnxDS3ChannelSubrate to default for the mode if
             tmnxDS3ChannelSubrate is not provided.";
          smiv2:defval "notUsed";
          smiv2:max-access "read-write";
          smiv2:oid "1.3.6.1.4.1.6527.3.1.2.2.4.11.1.6";
          config true;
        }
        leaf tmnxDS3ChannelSubrate {
          type uint32;
          description
            "tmnxDS3ChannelSubrate configures the subrate step.
             
             tmnxDS3ChannelSubrate multiplied by the granularity for a
             particular mode as defined by tmnxDS3ChannelSubrateCSUMode gives
             the absoulte subrate in kbps.
             
             ----------------------------------------------------------------------
              Subrate CSU Mode|Granularity|Default |Range     |Subrate speed range
             ----------------------------------------------------------`-----------
              notUsed         | N/A       | 0      | 0        |N/A
              digital-link    | 301 kbps  | 1      | 1 to 147 |301 kbps to 44.2 mbps
             ----------------------------------------------------------------------";
          smiv2:max-access "read-write";
          smiv2:oid "1.3.6.1.4.1.6527.3.1.2.2.4.11.1.7";
          config true;
        }
        leaf tmnxDS3ChannelIdleCycleFlags {
          type timetra-port:TmnxDSXIdleCycleFlags;
          description
            "tmnxDS3ChannelIdleCycleFlags configures the value that the
             DS3 port transmits during idle cycle.
             
             The default value applies to HDLC channels only. For ATM
             channels the object does not really apply so a default value
             of 'none' is used and cannot be changed.";
          smiv2:defval "flags";
          smiv2:max-access "read-write";
          smiv2:oid "1.3.6.1.4.1.6527.3.1.2.2.4.11.1.8";
          config true;
        }
        leaf tmnxDS3ChannelLoopback {
          type timetra-port:TmnxDS3Loopback;
          description
            "tmnxDS3ChannelLoopback is used to put the channel into a loopback mode.
             The value of tmnxPortAdminStatus should be set to 'outOfService'
             in order for the loopback to be enabled.
             A 'line' loopback loops frames received on this port back to the
             remote system.
             A 'internal' loopback loops the frames from the local system back at
             the framer.
             When the value is set to 'remote', a signal is sent to the remote
             system to provide a line loopback.";
          smiv2:defval "none";
          smiv2:max-access "read-write";
          smiv2:oid "1.3.6.1.4.1.6527.3.1.2.2.4.11.1.9";
          config true;
        }
        leaf tmnxDS3ChannelBitErrorInsertionRate {
          type int32 {
            range "0|2..7";
          }
          description
            "tmnxDS3ChannelBitErrorInsertionRate is used to insert bit errors for a
             BERT test. The number of error corresponds to 10^(-rate). A rate of 7
             will cause an error rate of 10^(-7), or 1 error in every 10
             million bits transmitted.
             If the value is set to 0, it disables the insertion of bit errors
             into the BERT.
             Change in this value while the test is running is accepted but
             does not take effect until the test gets restarted.";
          smiv2:defval "0";
          smiv2:max-access "read-write";
          smiv2:oid "1.3.6.1.4.1.6527.3.1.2.2.4.11.1.10";
          config true;
        }
        leaf tmnxDS3ChannelBERTPattern {
          type timetra-port:TmnxDSXBertPattern;
          description
            "tmnxDS3ChannelBERTPattern indicates the pattern used for the
             Bit Error Rate Test (BERT). The value of tmnxDS3ChannelBERTDuration
             indicates the duration of the test.
             Setting the value of this object to 'none' terminates the test.";
          smiv2:defval "none";
          smiv2:max-access "read-write";
          smiv2:oid "1.3.6.1.4.1.6527.3.1.2.2.4.11.1.11";
          config true;
        }
        leaf tmnxDS3ChannelBERTDuration {
          type uint32 {
            range "0..86400";
          }
          units "seconds";
          description
            "tmnxDS3ChannelBERTDuration is used to set the duration of the
             BERT test.";
          smiv2:max-access "read-write";
          smiv2:oid "1.3.6.1.4.1.6527.3.1.2.2.4.11.1.12";
          config true;
        }
        leaf tmnxDS3ChannelMDLEicString {
          type snmpv2-tc:DisplayString {
            length "0..10";
          }
          description
            "tmnxDS3ChannelMDLEicString configures the Equipment ID Code(EIC) of the
             Message Data Link (MDL).";
          smiv2:max-access "read-write";
          smiv2:oid "1.3.6.1.4.1.6527.3.1.2.2.4.11.1.13";
          config true;
        }
        leaf tmnxDS3ChannelMDLLicString {
          type snmpv2-tc:DisplayString {
            length "0..11";
          }
          description
            "tmnxDS3ChannelMDLLicString configures the Location ID Code(LIC) of the
             Message Data Link (MDL).";
          smiv2:max-access "read-write";
          smiv2:oid "1.3.6.1.4.1.6527.3.1.2.2.4.11.1.14";
          config true;
        }
        leaf tmnxDS3ChannelMDLFicString {
          type snmpv2-tc:DisplayString {
            length "0..10";
          }
          description
            "tmnxDS3ChannelMDLFicString configures the Frame ID Code(FIC) of the
             Message Data Link (MDL).";
          smiv2:max-access "read-write";
          smiv2:oid "1.3.6.1.4.1.6527.3.1.2.2.4.11.1.15";
          config true;
        }
        leaf tmnxDS3ChannelMDLUnitString {
          type snmpv2-tc:DisplayString {
            length "0..6";
          }
          description
            "tmnxDS3ChannelMDLUnitString configures the Unit ID Code(UIC) of the
             Message Data Link (MDL).";
          smiv2:max-access "read-write";
          smiv2:oid "1.3.6.1.4.1.6527.3.1.2.2.4.11.1.16";
          config true;
        }
        leaf tmnxDS3ChannelMDLPfiString {
          type snmpv2-tc:DisplayString {
            length "0..38";
          }
          description
            "tmnxDS3ChannelMDLPfiString configures the Facility ID Code sent in
             the Message Data Link (MDL) Path message.";
          smiv2:max-access "read-write";
          smiv2:oid "1.3.6.1.4.1.6527.3.1.2.2.4.11.1.17";
          config true;
        }
        leaf tmnxDS3ChannelMDLPortString {
          type snmpv2-tc:DisplayString {
            length "0..38";
          }
          description
            "tmnxDS3ChannelMDLPortString configures the port number string sent in
             the Message Data Link (MDL) idle signal message.";
          smiv2:max-access "read-write";
          smiv2:oid "1.3.6.1.4.1.6527.3.1.2.2.4.11.1.18";
          config true;
        }
        leaf tmnxDS3ChannelMDLGenString {
          type snmpv2-tc:DisplayString {
            length "0..38";
          }
          description
            "tmnxDS3ChannelMDLGenString configures the generator number string
             sent in the Message Data Link (MDL) test signal message.";
          smiv2:max-access "read-write";
          smiv2:oid "1.3.6.1.4.1.6527.3.1.2.2.4.11.1.19";
          config true;
        }
        leaf tmnxDS3ChannelMDLMessageType {
          type bits {
            bit none {
              position 0;
            }
            bit ds3Path {
              position 1;
            }
            bit idleSignal {
              position 2;
            }
            bit testSignal {
              position 3;
            }
          }
          description
            "tmnxDS3ChannelMDLMessageType configures the type of MDL message that
             is transmitted over the DS3 interface. If the value of this object is
             set to 'none', MDL messages are not transmitted.
             ds3Path(0)   - Enables transmission of the MDL path message.
                            An MDL path message, as defined by ANSI T1.107, is
                            distinguished from idle and test signal messages in
                            that it contains a facility identification code as its
                            final data element.
             idleSignal(1) - Enables transmission of the MDL idle signal message.
                            An MDL idle signal message, as defined by ANSI T1.107,
                            is distinguished from path and test signal messages in
                            that it contains a port number as its final data
                            element.
             testSignal(2) - Enables transmission of the MDL test signal message.
                            An MDL test signal message, as defined by ANSI T1.107,
                            is distinguished from path and idle signal messages in
                            that it contains a generator number as its final data
                            element.";
          smiv2:defval "{none}";
          smiv2:max-access "read-write";
          smiv2:oid "1.3.6.1.4.1.6527.3.1.2.2.4.11.1.20";
          config true;
        }
        leaf tmnxDS3ChannelFEACLoopRespond {
          type boolean;
          description
            "When tmnxDS3ChannelFEACLoopRespond has a value of 'true', the channel
             is enabled to respond to remote loop signals.  When it has
             a value of 'false' the port will not respond.";
          smiv2:defval "false";
          smiv2:max-access "read-write";
          smiv2:oid "1.3.6.1.4.1.6527.3.1.2.2.4.11.1.21";
          config true;
        }
        leaf tmnxDS3ChannelCRC {
          type enumeration {
            enum "crc16" {
              value 1;
            }
            enum "crc32" {
              value 2;
            }
          }
          description
            "The value of tmnxDS3ChannelCRC variable indicates the precision of
             the cyclic redundancy check.  A value of 'crc16' is a 16-bit
             CRC calculation.  A value of 'crc32' is a 32-bit CRC
             calculation.  32-bit CRC increases the error detection ability,
             but it also adds some performance overhead.
             
             For ATM channels, crc32 is the default and the only value supported
             and applies to AAL5 CRC calculation on that channel.";
          smiv2:defval "crc16";
          smiv2:max-access "read-write";
          smiv2:oid "1.3.6.1.4.1.6527.3.1.2.2.4.11.1.22";
          config true;
        }
        leaf tmnxDS3ChannelMTU {
          type uint32 {
            range "0|512..9208";
          }
          units "bytes";
          description
            "The size of the largest packet which can be sent/received
             on the port, specified in octets.  For ports that
             are used for transmitting network datagrams, this is the
             size of the largest network datagram that can be sent on the
             sonet path.
             
             Setting tmnxDS3ChannelMTU to a value of zero (0), causes the agent
             to recalculate the default MTU size which can vary based on the
             current setting of tmnxPortMode and tmnxPortEncapType variables.
             Some typical default values are:
                    1522 with mode access and encap-type bcp-null
                    1526 with mode access and encap-type bcp-dot1q
                    1502 with mode access and encap-type ipcp
                    4474 with mode access and encap-type frame-relay
                    1524 with mode access and encap-type atm
                    2092 with mode access and encap-type cem";
          smiv2:max-access "read-write";
          smiv2:oid "1.3.6.1.4.1.6527.3.1.2.2.4.11.1.23";
          config true;
        }
        leaf tmnxDS3ChannelOperMTU {
          type uint32;
          units "bytes";
          description
            "The negotiated size of the largest packet which can be sent on
             the channel, specified in octets.  For channels that are used
             for transmitting network datagrams, this is the size of the largest
             network datagram that can be sent.";
          smiv2:max-access "read-only";
          smiv2:oid "1.3.6.1.4.1.6527.3.1.2.2.4.11.1.24";
          config false;
        }
        leaf tmnxDS3ChannelReportAlarm {
          type timetra-port:TmnxDSXReportAlarm;
          description
            "The value of tmnxDS3ChannelReportAlarm determines when and if to
             generate notifications for this channel:
             ais - Reports alarm indication signal errors.
                   ais alarms are issued by default.
             los - Reports loss of signal errors.
                   los alarms are issued by default.
             oof - Reports out-of-frame errors.
                   oof alarms are not issued by default.
             rai - Reports resource availability indicator events.
                   rai alarms are not issued by default.
             looped - Reports if the far end has forced the near end to loopback.
                   looped alarms are not issued by default.
             berSd - Reports DS3/E3 signal degradation bit errors.
                     berSd alarms are not issued by default.
             berSf - Reports DS3/E3 signal failure bit errors.
                     berSf alarms are not issued by default";
          smiv2:defval "{ais, los}";
          smiv2:max-access "read-write";
          smiv2:oid "1.3.6.1.4.1.6527.3.1.2.2.4.11.1.25";
          config true;
        }
        leaf tmnxDS3ChannelReportAlarmStatus {
          type timetra-port:TmnxDSXReportAlarm;
          description
            "The value of tmnxDS3ChannelReportAlarmStatus indicates the current
             alarms on this port.";
          smiv2:max-access "read-only";
          smiv2:oid "1.3.6.1.4.1.6527.3.1.2.2.4.11.1.26";
          config false;
        }
        leaf tmnxDS3ChannelLastChangeTime {
          type yang:timestamp;
          description
            "The tmnxDS3ChannelLastChangeTime variable contains the sysUpTime
             value of the most recently modified writable variable in the
             tmnxDS3ChannelEntry row for this port.";
          smiv2:max-access "read-only";
          smiv2:oid "1.3.6.1.4.1.6527.3.1.2.2.4.11.1.27";
          config false;
        }
        leaf tmnxDS3ChannelInFEACLoop {
          type boolean;
          description
            "tmnxDS3ChannelInFEACLoop indicates whether the remote end has put
             this channel in FEAC(Far End Alarm Control) loopback.";
          smiv2:max-access "read-only";
          smiv2:oid "1.3.6.1.4.1.6527.3.1.2.2.4.11.1.28";
          config false;
        }
        leaf tmnxDS3ChannelMDLMonPortString {
          type snmpv2-tc:DisplayString {
            length "0..38";
          }
          description
            "tmnxDS3ChannelMDLMonPortString indicates the port number string
             received in the Message Data Link (MDL) idle signal message.";
          smiv2:max-access "read-only";
          smiv2:oid "1.3.6.1.4.1.6527.3.1.2.2.4.11.1.29";
          config false;
        }
        leaf tmnxDS3ChannelMDLMonGenString {
          type snmpv2-tc:DisplayString {
            length "0..38";
          }
          description
            "tmnxDS3ChannelMDLMonGenString indicates the generator number string
             received in the Message Data Link (MDL) test signal message.";
          smiv2:max-access "read-only";
          smiv2:oid "1.3.6.1.4.1.6527.3.1.2.2.4.11.1.30";
          config false;
        }
        leaf tmnxDS3ChannelBERTOperStatus {
          type timetra-port:TmnxDSXBertOperStatus;
          description
            "tmnxDS3ChannelBERTOperStatus indicates the status of the BERT test
             as specified by TmnxDSXBertOperStatus.";
          smiv2:max-access "read-only";
          smiv2:oid "1.3.6.1.4.1.6527.3.1.2.2.4.11.1.31";
          config false;
        }
        leaf tmnxDS3ChannelBERTSynched {
          type uint32;
          units "seconds";
          description
            "tmnxDS3ChannelBERTSynched is the number of seconds for which the
             BERT hardware was synchronized. This will be less than or equal to
             the duration of the last BERT test. It is valid only after
             tmnxDS3ChannelBERTOperStatus transitioned from 'active' to 'idle'
             the last time BERT was activated.";
          smiv2:max-access "read-only";
          smiv2:oid "1.3.6.1.4.1.6527.3.1.2.2.4.11.1.32";
          config false;
        }
        leaf tmnxDS3ChannelBERTErrors {
          type yang:counter64;
          description
            "tmnxDS3ChannelBERTErrors is the number of bit errors detected during
             the last BERT test. It is valid only after tmnxDS3ChannelBERTOperStatus
             transitioned from 'active' to 'idle' the last time BERT
             was activated.";
          smiv2:max-access "read-only";
          smiv2:oid "1.3.6.1.4.1.6527.3.1.2.2.4.11.1.33";
          config false;
        }
        leaf tmnxDS3ChannelBERTTotalBits {
          type yang:counter64;
          description
            "tmnxDS3ChannelBERTTotalBits is the total number of bits received
             during the last BERT test. Bits are only counted when the BERT
             hardware is synchronized. It is valid only after
             tmnxDS3ChannelBERTOperStatus transitioned from 'active' to 'idle'
             the last time BERT was activated.";
          smiv2:max-access "read-only";
          smiv2:oid "1.3.6.1.4.1.6527.3.1.2.2.4.11.1.34";
          config false;
        }
        leaf tmnxDS3ChannelScramble {
          type boolean;
          description
            "When tmnxDS3ChannelScramble indicates whether scrambling
             is enabled on this channel.  Both ends of the connection
             must use the same scrambling algorithm.  The default value
             is 'true' if the tmnxPortEncapType is atmEncap for this
             channel and indicates ATM payload scrambling; otherwise
             (tmnxPortEncapType is not atmEncap) the default is 'false'
             and can only be changed to true if the value of
             tmnxDS3ChannelSubrateCSUMode is digital-link (1)";
          smiv2:max-access "read-write";
          smiv2:oid "1.3.6.1.4.1.6527.3.1.2.2.4.11.1.35";
          config true;
        }
        leaf tmnxDS3ChannelAcctPolicyId {
          type uint32 {
            range "0..99";
          }
          description
            "The value of tmnxDS3ChannelAcctPolicyId specifies an existing
             accounting policy to use for the ds3 channel. Accounting policies can
             only be associated with network ports or channels.
             
             A non-zero value indicates the tmnxLogApPolicyId index identifying the
             policy entry in the tmnxLogApTable from the TIMETRA-LOG-MIB which is
             associated with this channel.  A zero value indicates that there is no
             accounting policy associated with this channel";
          smiv2:defval "0";
          smiv2:max-access "read-write";
          smiv2:oid "1.3.6.1.4.1.6527.3.1.2.2.4.11.1.36";
          config true;
        }
        leaf tmnxDS3ChannelCollectStats {
          type boolean;
          description
            "The value of tmnxDS3ChannelCollectStats specifies whether or not the
             collection of accounting and statistical data for the network ds3
             channel is collected.
             
             When the value is set to false, the statistics are still accumulated
             by the IOM cards, however, the CPM will not obtain the results and
             write them to the billing file.
             
             When applying accounting policies the data by default will be collected
             in the appropriate records and written to the designated billing file.";
          smiv2:defval "true";
          smiv2:max-access "read-write";
          smiv2:oid "1.3.6.1.4.1.6527.3.1.2.2.4.11.1.37";
          config true;
        }
        leaf tmnxDS3ChannelClockSyncState {
          type timetra-port:TmnxDSXClockSyncState;
          description
            "The value of tmnxDS3ChannelClockSyncState indicates the current clock
             synchronization state if tmnxDS3ChannelClockSource is 'adaptive' or
             'differential'.";
          smiv2:max-access "read-only";
          smiv2:oid "1.3.6.1.4.1.6527.3.1.2.2.4.11.1.38";
          config false;
        }
        leaf tmnxDS3ChannelClockMasterPortId {
          type timetra-tc:TmnxPortID;
          description
            "The value of tmnxDS3ChannelClockMasterPortId indicates the current
             clock synchronization master port id if tmnxDS3ChannelClockSource
             is 'adaptive' or 'differential'.";
          smiv2:max-access "read-only";
          smiv2:oid "1.3.6.1.4.1.6527.3.1.2.2.4.11.1.39";
          config false;
        }
        config true;
      }
      config true;
    }
    container tmnxDS1Table {
      description
        "The tmnxDS1Table has an entry for each DS1 channel.";
      smiv2:oid "1.3.6.1.4.1.6527.3.1.2.2.4.12";
      list tmnxDS1Entry {
        key "tmnxChassisIndex tmnxPortPortID";
        description
          "Each row entry represents a DS1 channel on a IOM card
           in a chassis in the system.  DS1 channel entries for DS3
           ports cannot be created and deleted via SNMP SET operations.
           Entries in this table will be created automatically when
           tmnxDS3ChannelChannelized is set to 'true'. DS1 channel entries
           for DS1 ports can be created and deleted via SNMP SET operations.
           For each tmnxDS1Entry, there will be a corresponding entry
           in the tmnxPortTable and the ifTable.";
        smiv2:oid "1.3.6.1.4.1.6527.3.1.2.2.4.12.1";
        leaf tmnxChassisIndex {
          type leafref {
            path "/timetra-chassis:TIMETRA-CHASSIS-MIB/timetra-chassis:tmnxChassisTable/timetra-chassis:tmnxChassisEntry/timetra-chassis:tmnxChassisIndex";
          }
          config true;
        }
        leaf tmnxPortPortID {
          type leafref {
            path "/timetra-port:TIMETRA-PORT-MIB/timetra-port:tmnxPortTable/timetra-port:tmnxPortEntry/timetra-port:tmnxPortPortID";
          }
          config true;
        }
        leaf tmnxDS1RowStatus {
          type snmpv2-tc:RowStatus;
          description
            "tmnxDS1RowStatus controls the creation and deletion of
             row entries in the tmnxDS1Table.
             For row creation, the manager has to first calculate the
             tmnxPortPortID based on the TiMOS encoding scheme.";
          smiv2:max-access "read-write";
          smiv2:oid "1.3.6.1.4.1.6527.3.1.2.2.4.12.1.1";
          config false;
        }
        leaf tmnxDS1Type {
          type enumeration {
            enum "ds1" {
              value 1;
            }
            enum "e1" {
              value 2;
            }
            enum "j1" {
              value 3;
            }
          }
          description
            "The value of tmnxDS1Type indicates whether the DS1 channel is
             in DS1, E1 or J1 mode.";
          smiv2:max-access "read-only";
          smiv2:oid "1.3.6.1.4.1.6527.3.1.2.2.4.12.1.2";
          config false;
        }
        leaf tmnxDS1Framing {
          type enumeration {
            enum "esf" {
              value 1;
            }
            enum "sf" {
              value 2;
            }
            enum "g704-no-crc" {
              value 3;
            }
            enum "g704" {
              value 4;
            }
            enum "e1-unframed" {
              value 5;
            }
            enum "ds1-unframed" {
              value 6;
            }
          }
          description
            "The value of tmnxDS1Framing indicates the type of framing associated
             with the channel:
             esf            ESF (extended super frame) mode for T1 interfaces.
             sf             SF (super frame) mode for T1 interfaces.
             g704           G.704 framing format for E1 interfaces.
             g704-no-crc4   G.704 framing with no CRC4 for E1 interfaces.
             e1-unframed    E1 Unframed (G.703) mode for E1 interfaces.
             ds1-unframed   Unframed mode for T1 interfaces.
             
             If tmnxDS1Type is set to 'ds1', the default framing is 'esf'.
             If tmnxDS1Type is set to 'e1', the default framing is 'g704'.
             
             Changing the value of tmnxDS1Framing resets the values of
             tmnxDS1BerSdThreshold and tmnxDS1BerSfThreshold to defaults
             and turns off reporting of berSd and berSf alarms
             in tmnxDS1ReportAlarm.";
          smiv2:defval "esf";
          smiv2:max-access "read-write";
          smiv2:oid "1.3.6.1.4.1.6527.3.1.2.2.4.12.1.3";
          config true;
        }
        leaf tmnxDS1IdleCycleFlags {
          type timetra-port:TmnxDSXIdleCycleFlags;
          status obsolete;
          description
            "tmnxDS1IdleCycleFlags configures the value that the DS1
             channel transmits during idle cycle.";
          smiv2:defval "flags";
          smiv2:max-access "read-write";
          smiv2:oid "1.3.6.1.4.1.6527.3.1.2.2.4.12.1.4";
          config true;
        }
        leaf tmnxDS1Loopback {
          type timetra-port:TmnxDS1Loopback;
          description
            "tmnxDS1Loopback is used to put the channel into a loopback mode. The
             value of tmnxPortAdminStatus should be set to 'outOfService' in order
             for the loopback to be enabled.
             A 'line' loopback loops frames received on this port back to the
             remote system.
             A 'internal' loopback loops frames from the local system back at
             the framer.
             A 'fdlAnsi' requests loopback of type FDL ANSI T1.403. This is valid
             with tmnxDS1Framing set to 'esf' framing.
             A 'fdlBellcore' requests loopback of type FDL Bellcore TR-TSY-000312.
             This is valid with tmnxDS1Framing set to 'esf'.
             A 'inbandAnsi' requests loopback of type inband ANSI T1.403. This is
             valid with tmnxDS1Framing set to 'sf'.";
          smiv2:defval "none";
          smiv2:max-access "read-write";
          smiv2:oid "1.3.6.1.4.1.6527.3.1.2.2.4.12.1.5";
          config true;
        }
        leaf tmnxDS1InvertData {
          type boolean;
          description
            "Setting tmnxDS1InvertData to 'true' causes all data bits to
             be inverted, to guarantee ones density. It is typically used with
             AMI line encoding.";
          smiv2:defval "false";
          smiv2:max-access "read-write";
          smiv2:oid "1.3.6.1.4.1.6527.3.1.2.2.4.12.1.6";
          config true;
        }
        leaf tmnxDS1BitErrorInsertionRate {
          type int32 {
            range "0|2..7";
          }
          description
            "tmnxDS1BitErrorInsertionRate is used to insert bit errors for a
             BERT test. The number of error corresponds to 10^(-rate). A rate of 7
             will cause an error rate of 10^(-7), or 1 error in every 10
             million bits transmitted.
             If the value is set to 0, disables the insertion of bit errors into
             the BERT.
             Change in this value while the test is running is accepted but
             does not take effect until the test gets restarted.";
          smiv2:defval "0";
          smiv2:max-access "read-write";
          smiv2:oid "1.3.6.1.4.1.6527.3.1.2.2.4.12.1.7";
          config true;
        }
        leaf tmnxDS1BERTPattern {
          type timetra-port:TmnxDSXBertPattern;
          description
            "tmnxDS1BERTPattern object indicates the pattern used for the
             Bit Error Rate Test (BERT). The value of tmnxDS1BERTDuration
             indicates the duration of the test.
             Setting the value to 'none' terminates the test.";
          smiv2:defval "none";
          smiv2:max-access "read-write";
          smiv2:oid "1.3.6.1.4.1.6527.3.1.2.2.4.12.1.8";
          config true;
        }
        leaf tmnxDS1BERTDuration {
          type uint32 {
            range "0..86400";
          }
          units "seconds";
          description
            "tmnxDS1BERTDuration is used to set the duration of the BERT test.";
          smiv2:max-access "read-write";
          smiv2:oid "1.3.6.1.4.1.6527.3.1.2.2.4.12.1.9";
          config true;
        }
        leaf tmnxDS1ReportAlarm {
          type timetra-port:TmnxDSXReportAlarm;
          description
            "The value of tmnxDS1ReportAlarm determines when and if to
             generate notifications for this channel:
             ais - Reports alarm indication signal errors.
                   ais alarms are issued by default.
             los - Reports loss of signal errors.
                   los alarms are issued by default.
             oof - Reports out-of-frame errors.
                   oof alarms are not issued by default.
             rai - Reports resource availability indicator events.
                   rai alarms are not issued by default.
             looped - Reports if the far end has forced the near end to loopback.
                   looped alarms are not issued by default.
             berSd - Reports DS1/E1/J1 signal degradation bit errors.
                     berSd alarms are not issued by default.
             berSf - Reports DS1/E1/J1 signal failure bit errors.
                     berSf alarms are not issued by default";
          smiv2:defval "{ais, los}";
          smiv2:max-access "read-write";
          smiv2:oid "1.3.6.1.4.1.6527.3.1.2.2.4.12.1.10";
          config true;
        }
        leaf tmnxDS1ReportAlarmStatus {
          type timetra-port:TmnxDSXReportAlarm;
          description
            "The value of tmnxDS1ReportAlarmStatus indicates the current alarms
             on this channel.";
          smiv2:max-access "read-only";
          smiv2:oid "1.3.6.1.4.1.6527.3.1.2.2.4.12.1.11";
          config false;
        }
        leaf tmnxDS1LastChangeTime {
          type yang:timestamp;
          description
            "The tmnxDS1LastChangeTime variable contains the sysUpTime
             value of the most recently modified writable variable in the
             tmnxDS1Entry row for this channel.";
          smiv2:max-access "read-only";
          smiv2:oid "1.3.6.1.4.1.6527.3.1.2.2.4.12.1.12";
          config false;
        }
        leaf tmnxDS1ClockSource {
          type timetra-port:TmnxDSXClockSource;
          description
            "tmnxDS1ClockSource configures the clock for transmitted data from
             either the internal clock ('nodeTimed'), or from a clock recovered
             from the line's receive data stream ('loopTimed'), or recovered
             adaptively from the rate at which the data that is received and not
             from the physical layer ('adaptive'), or recovered from the
             differential timestamp in the RTP header ('differential').";
          smiv2:defval "loopTimed";
          smiv2:max-access "read-write";
          smiv2:oid "1.3.6.1.4.1.6527.3.1.2.2.4.12.1.13";
          config true;
        }
        leaf tmnxDS1BERTOperStatus {
          type timetra-port:TmnxDSXBertOperStatus;
          description
            "tmnxDS1BERTOperStatus indicates the status of the BERT test as
             specified by TmnxDSXBertOperStatus.";
          smiv2:max-access "read-only";
          smiv2:oid "1.3.6.1.4.1.6527.3.1.2.2.4.12.1.14";
          config false;
        }
        leaf tmnxDS1BERTSynched {
          type uint32;
          units "seconds";
          description
            "tmnxDS1BERTSynched is the number of seconds for which the
             BERT hardware was synchronized. This will be less than or equal to
             the duration of the last BERT test. It is valid only after
             tmnxDS1BERTOperStatus transitioned from 'active' to 'idle'
             the last time BERT was activated.";
          smiv2:max-access "read-only";
          smiv2:oid "1.3.6.1.4.1.6527.3.1.2.2.4.12.1.15";
          config false;
        }
        leaf tmnxDS1BERTErrors {
          type yang:counter64;
          description
            "tmnxDS1BERTErrors is the number of bit errors detected during
             the last BERT test. It is valid only after tmnxDS1BERTOperStatus
             transitioned from 'active' to 'idle' the last time BERT
             was activated.";
          smiv2:max-access "read-only";
          smiv2:oid "1.3.6.1.4.1.6527.3.1.2.2.4.12.1.16";
          config false;
        }
        leaf tmnxDS1BERTTotalBits {
          type yang:counter64;
          description
            "tmnxDS1BERTTotalBits is the total number of bits received
             during the last BERT test. Bits are only counted when the BERT
             hardware is synchronized. It is valid only after
             tmnxDS1BERTOperStatus transitioned from 'active' to 'idle'
             the last time BERT was activated.";
          smiv2:max-access "read-only";
          smiv2:oid "1.3.6.1.4.1.6527.3.1.2.2.4.12.1.17";
          config false;
        }
        leaf tmnxDS1RemoteLoopRespond {
          type boolean;
          description
            "When tmnxDS1RemoteLoopRespond has a value of 'true', the channel
             is enabled to respond to remote loop signals.  When it has
             a value of 'false' the port will not respond.";
          smiv2:defval "false";
          smiv2:max-access "read-write";
          smiv2:oid "1.3.6.1.4.1.6527.3.1.2.2.4.12.1.18";
          config true;
        }
        leaf tmnxDS1InRemoteLoop {
          type boolean;
          description
            "tmnxDS1InRemoteLoop indicates whether the remote end has put
             this channel in remote loopback.";
          smiv2:max-access "read-only";
          smiv2:oid "1.3.6.1.4.1.6527.3.1.2.2.4.12.1.19";
          config false;
        }
        leaf tmnxDS1InsertSingleBitError {
          type timetra-tc:TmnxActionType;
          description
            "tmnxDS1InsertSingleBitError is used to insert a single bit error for a
             BERT test.";
          smiv2:max-access "read-write";
          smiv2:oid "1.3.6.1.4.1.6527.3.1.2.2.4.12.1.20";
          config true;
        }
        leaf tmnxDS1SignalMode {
          type enumeration {
            enum "none" {
              value 1;
            }
            enum "cas" {
              value 2;
            }
          }
          description
            "The value of tmnxDS1SignalMode indicates the type of signalling
             associated with the channel:
             none  - Indicates no signalling on this channel.
             cas   - Indicates Channel Associated Signalling (CAS) on this channel.
             The default signalling is 'none'. ";
          smiv2:defval "none";
          smiv2:max-access "read-write";
          smiv2:oid "1.3.6.1.4.1.6527.3.1.2.2.4.12.1.21";
          config true;
        }
        leaf tmnxDS1ClockSyncState {
          type timetra-port:TmnxDSXClockSyncState;
          description
            "The value of tmnxDS1ClockSyncState indicates the current clock
             synchronization state if tmnxDS1ClockSource is 'adaptive' or
             'differential'.";
          smiv2:max-access "read-only";
          smiv2:oid "1.3.6.1.4.1.6527.3.1.2.2.4.12.1.22";
          config false;
        }
        leaf tmnxDS1ClockMasterPortId {
          type timetra-tc:TmnxPortID;
          description
            "The value of tmnxDS1ClockMasterPortId indicates the current clock
             synchronization master port id if tmnxDS1ClockSource is 'adaptive'
             or 'differential'.";
          smiv2:max-access "read-only";
          smiv2:oid "1.3.6.1.4.1.6527.3.1.2.2.4.12.1.23";
          config false;
        }
        leaf tmnxDS1BerSdThreshold {
          type uint32 {
            range "1|5|10|50|100";
          }
          units "error bits in million bits received";
          description
            "The value of tmnxDS1BerSdThreshold specifies a bit error rate (BER)
             threshold used to determine when to send a tmnxEqPortDS1Alarm
             notification for a BER SD failure and a tmnxEqPortDS1AlarmClear
             notification for a BER SD failure clear. Bit error computed must
             reach/exceed threshold value over a pre-defined period of time
             for the tmnxEqPortSonetAlarm notification to be sent.
             
             The value of tmnxDS1Framing defines how the bit error is
             computed and what values of tmnxDS1BerSdThreshold are allowed.
             The following table defines this dependency:
             
             tmnxDS1Framing   Bit error calculation and value supported
             --------------   -----------------------------------------
               esf  (1)       each CRC error is counted as one bit error
               g704 (4)       values supported are 1,5,10,50,100
             
               other values   bit error alarms not supported, value
                              of tmnxDS1BerSdThreshold set to default and
                              cannot be changed
             
             tmnxDS1BerSdThreshold value must not exceed the value of
             tmnxDS1BerSfThreshold.";
          smiv2:defval "5";
          smiv2:max-access "read-write";
          smiv2:oid "1.3.6.1.4.1.6527.3.1.2.2.4.12.1.24";
          config true;
        }
        leaf tmnxDS1BerSfThreshold {
          type uint32 {
            range "1|5|10|50|100";
          }
          units "error bits in million bits received";
          description
            "The value of tmnxDS1BerSfThreshold specifies a bit error rate (BER)
             threshold used to determine when to send a tmnxEqPortDS1Alarm
             notification for a BER SF failure and a tmnxEqPortDS1AlarmClear
             notification for a BER SF failure clear. Bit error computed must
             reach/exceed threshold value over a pre-defined period of time
             for the tmnxEqPortSonetAlarm notification to be sent.
             
             The value of tmnxDS1Framing defines how the bit errors are
             computed and what values of tmnxDS1BerSfThreshold are allowed.
             The following table defines this dependency:
             
             tmnxDS1Framing   Bit error calculation and value supported
             --------------   -----------------------------------------
               esf  (1)       each CRC error is counted as one bit error
               g704 (4)       values supported are 1,5,10,50,100
             
               other values   bit error alarms not supported, value
                              of tmnxDS1BerSfThreshold set to default and
                              cannot be changed
             
             tmnxDS1BerSfThreshold value must not be smaller than
             tmnxDS1BerSdThreshold value";
          smiv2:defval "50";
          smiv2:max-access "read-write";
          smiv2:oid "1.3.6.1.4.1.6527.3.1.2.2.4.12.1.25";
          config true;
        }
        leaf tmnxDS1NationalUseBits {
          type bits {
            bit sa4 {
              position 0;
            }
            bit sa5 {
              position 1;
            }
            bit sa6 {
              position 2;
            }
            bit sa7 {
              position 3;
            }
            bit sa8 {
              position 4;
            }
          }
          description
            "The tmnxDS1NationalUseBits specifies the transmitted value for each of
             the E1 national use bits (Sa4 to Sa8).  This object is only
             applicable on E1 channels with tmnxDS1Framing set to g704-no-crc (3),
             or g704 (4).";
          smiv2:defval "{}";
          smiv2:max-access "read-write";
          smiv2:oid "1.3.6.1.4.1.6527.3.1.2.2.4.12.1.26";
          config true;
        }
        config true;
      }
      config true;
    }
    container tmnxDS0ChanGroupTable {
      description
        "The tmnxDS0ChanGroupTable has an entry for DS0 channels
         grouped together and belonging to a particular DS1 channel.";
      smiv2:oid "1.3.6.1.4.1.6527.3.1.2.2.4.13";
      list tmnxDS0ChanGroupEntry {
        key "tmnxChassisIndex tmnxPortPortID";
        description
          "Each row entry represents one or more DS0 channels on a
           DS1 interface.  tmnxDS0ChanGroupTimeSlots object is used to add or
           remove DS0 channels from the group.
           
           Entries can be created and deleted via SNMP SET operations
           using the tmnxDS0ChanGroupRowStatus object.
           
           For each tmnxDS0ChanGroupEntry, there will be a corresponding entry
           in the tmnxPortTable and the ifTable.";
        smiv2:oid "1.3.6.1.4.1.6527.3.1.2.2.4.13.1";
        leaf tmnxChassisIndex {
          type leafref {
            path "/timetra-chassis:TIMETRA-CHASSIS-MIB/timetra-chassis:tmnxChassisTable/timetra-chassis:tmnxChassisEntry/timetra-chassis:tmnxChassisIndex";
          }
          config true;
        }
        leaf tmnxPortPortID {
          type leafref {
            path "/timetra-port:TIMETRA-PORT-MIB/timetra-port:tmnxPortTable/timetra-port:tmnxPortEntry/timetra-port:tmnxPortPortID";
          }
          config true;
        }
        leaf tmnxDS0ChanGroupRowStatus {
          type snmpv2-tc:RowStatus;
          description
            "tmnxDS0ChanGroupRowStatus controls the creation and deletion of
             row entries in the tmnxDS0ChanGroupTable. The tmnxPortPortID
             for a channel group includes a group ID in the lower bits.
             The manager has to first calculate the tmnxPortPortID based on the
             TiMOS encoding scheme.";
          smiv2:max-access "read-write";
          smiv2:oid "1.3.6.1.4.1.6527.3.1.2.2.4.13.1.1";
          config false;
        }
        leaf tmnxDS0ChanGroupTimeSlots {
          type timetra-port:TmnxDs0ChannelList;
          description
            "tmnxDS0ChanGroupTimeSlots is a bitmap which is used to
             add/remove DS0 timeslots from a channel group.
             The description for TmnxDs0ChannelList contains details of the
             bitmap organization.
             
             When a channel group is created on unframed DS1/E1, all timeslots
             as applicable to a given speed are auto-allocated and cannot be
             changed.
             
             When a channel group is created on a framed DS1/E1 or
             existing channel group's encapsulation is changed from ATM,
             the default of no timeslots is auto-assigned to the group.
             
             When a channel group  on a framed DS1/E1 is configured for
             ATM encapsulation, the ATM defaults of 0x00FFFFFF (DS1)
             and 0XFFFEFFFE (E1) are auto-assigned and cannot be changed.";
          smiv2:max-access "read-write";
          smiv2:oid "1.3.6.1.4.1.6527.3.1.2.2.4.13.1.2";
          config true;
        }
        leaf tmnxDS0ChanGroupSpeed {
          type enumeration {
            enum "speed-56" {
              value 1;
            }
            enum "speed-64" {
              value 2;
            }
          }
          description
            "tmnxDS0ChanGroupSpeed configures the required link speed
             for all the time slots included in this channel group.";
          smiv2:max-access "read-write";
          smiv2:oid "1.3.6.1.4.1.6527.3.1.2.2.4.13.1.3";
          config true;
        }
        leaf tmnxDS0ChanGroupCRC {
          type enumeration {
            enum "crc16" {
              value 1;
            }
            enum "crc32" {
              value 2;
            }
          }
          description
            "The value of tmnxDS0ChanGroupCRC variable indicates the precision of
             the cyclic redundancy check.  A value of 'crc16' is a 16-bit
             CRC calculation.  A value of 'crc32' is a 32-bit CRC
             calculation.  32-bit CRC increases the error detection ability,
             but it also adds some performance overhead.
             
             For channel groups with encapsulation set to ATM, the default and
             only supported value is crc32 and applies to AAL5 CRC calculations
             on that channel group.";
          smiv2:defval "crc16";
          smiv2:max-access "read-write";
          smiv2:oid "1.3.6.1.4.1.6527.3.1.2.2.4.13.1.4";
          config true;
        }
        leaf tmnxDS0ChanGroupMTU {
          type uint32 {
            range "0|512..9208";
          }
          units "bytes";
          description
            "The size of the largest packet which can be sent/received
             on the channel group, specified in octets.  For groups that
             are used for transmitting network datagrams, this is the
             size of the largest network datagram that can be sent.
             
             Setting tmnxDS0ChanGroupMTU to a value of zero (0), causes the agent
             to recalculate the default MTU size which can vary based on the
             current setting of tmnxPortMode and tmnxPortEncapType variables.
             Some typical default values are:
                    1522 with mode access and encap-type bcp-null
                    1526 with mode access and encap-type bcp-dot1q
                    1502 with mode access and encap-type ipcp
                    4474 with mode access and encap-type frame-relay
                    1524 with mode access and encap-type atm
                    2092 with mode access and encap-type cem";
          smiv2:max-access "read-write";
          smiv2:oid "1.3.6.1.4.1.6527.3.1.2.2.4.13.1.5";
          config true;
        }
        leaf tmnxDS0ChanGroupOperMTU {
          type uint32;
          units "bytes";
          description
            "The negotiated size of the largest packet which can be sent on
             the channel group, specified in octets.  For channel groups that
             are used for transmitting network datagrams, this is the size of
             the largest network datagram that can be sent.";
          smiv2:max-access "read-only";
          smiv2:oid "1.3.6.1.4.1.6527.3.1.2.2.4.13.1.6";
          config false;
        }
        leaf tmnxDS0ChanGroupLastChangeTime {
          type yang:timestamp;
          description
            "The tmnxDS0ChanGroupLastChangeTime variable contains the sysUpTime
             value of the most recently modified writable variable in the
             tmnxDS0ChanGroupEntry row for this channel group.";
          smiv2:max-access "read-only";
          smiv2:oid "1.3.6.1.4.1.6527.3.1.2.2.4.13.1.7";
          config false;
        }
        leaf tmnxDS0ChanGroupIdleCycleFlags {
          type timetra-port:TmnxDSXIdleCycleFlags;
          description
            "tmnxDS0ChanGroupIdleCycleFlags configures the value that the
             channel group transmits during idle cycle.
             
             The default value applies to HDLC channels only. For ATM and CEM
             channels the object does not really apply so a default value of
             'none' is used and cannot be changed.";
          smiv2:defval "flags";
          smiv2:max-access "read-write";
          smiv2:oid "1.3.6.1.4.1.6527.3.1.2.2.4.13.1.8";
          config true;
        }
        leaf tmnxDS0ChanGroupScramble {
          type boolean;
          description
            "tmnxDS0ChanGroupScramble indicates whether payload scrambling
             is enabled on this ATM channel.  Both ends of the connection
             must use the same scrambling algorithm.  The default value
             is 'true' if the tmnxPortEncapType is atmEncap for this
             channel, otherwise the default is 'false' and not allowed to
             change.";
          smiv2:max-access "read-write";
          smiv2:oid "1.3.6.1.4.1.6527.3.1.2.2.4.13.1.9";
          config true;
        }
        leaf tmnxDS0ChanGroupAcctPolicyId {
          type uint32 {
            range "0..99";
          }
          description
            "The value of tmnxDS0ChanGroupAcctPolicyId specifies an existing
             accounting policy to use for the ds0 channel-group. Accounting policies
             can only be associated with network ports or channels.
             
             A non-zero value indicates the tmnxLogApPolicyId index identifying the
             policy entry in the tmnxLogApTable from the TIMETRA-LOG-MIB which is
             associated with this channel-group.  A zero value indicates that there
             is no accounting policy associated with this channel";
          smiv2:defval "0";
          smiv2:max-access "read-write";
          smiv2:oid "1.3.6.1.4.1.6527.3.1.2.2.4.13.1.10";
          config true;
        }
        leaf tmnxDS0ChanGroupCollectStats {
          type boolean;
          description
            "The value of tmnxDS0ChanGroupCollectStats specifies whether or not the
             collection of accounting and statistical data for the network ds0
             channel-group is collected.
             
             When the value is set to false, the statistics are still accumulated
             by the IOM cards, however, the CPM will not obtain the results and
             write them to the billing file.
             
             When applying accounting policies the data by default will be collected
             in the appropriate records and written to the designated billing file.";
          smiv2:defval "true";
          smiv2:max-access "read-write";
          smiv2:oid "1.3.6.1.4.1.6527.3.1.2.2.4.13.1.11";
          config true;
        }
        leaf tmnxDS0ChanGroupPayloadFillType {
          type timetra-port:TmnxDSXIdleFillType;
          description
            "The value of tmnxDS0ChanGroupPayloadFillType specifies the type of
             idle payload fill to be sent when the CEM channel group experiences
             an underrun.
             
             If the type is set to 'userDefinedPattern' then the value of
             tmnxDS0ChanGroupPayloadPattern is used to define the payload pattern.
             
             The default value depends on the encap type of the channel group:
             For CEM encap           - 'allOnes'
             For all other encaps    - 'notApplicable'
             
             For a ds1-unframed and e1-unframed CEM encap DS0 channel group the
             only supported value is 'allOnes'.
             
             For non-CEM encap channel groups the value cannot be changed.";
          smiv2:defval "notApplicable";
          smiv2:max-access "read-write";
          smiv2:oid "1.3.6.1.4.1.6527.3.1.2.2.4.13.1.12";
          config true;
        }
        leaf tmnxDS0ChanGroupPayloadPattern {
          type uint32 {
            range "0..255";
          }
          description
            "The value of tmnxDS0ChanGroupPayloadPattern specifies the idle payload
             fill pattern when the CEM channel group experiences an underrun and
             tmnxDS0ChanGroupPayloadFillType is set to 'userDefinedPattern'.
             
             The default value depends on the encap type of the channel group:
             For CEM encap channel group             - 255 (Valid range 0..255)
             For non-CEM encap channel group         -   0 (Valid range 0..0).";
          smiv2:defval "0";
          smiv2:max-access "read-write";
          smiv2:oid "1.3.6.1.4.1.6527.3.1.2.2.4.13.1.13";
          config true;
        }
        leaf tmnxDS0ChanGroupSignalFillType {
          type timetra-port:TmnxDSXIdleFillType;
          description
            "The value of tmnxDS0ChanGroupSignalFillType specifies the type of
             idle signal fill to be sent when the CAS CEM channel group experiences
             an underrun.
             
             If the type is set to 'userDefinedPattern' then the value of
             tmnxDS0ChanGroupSignalPattern is used to define the signal pattern.
             
             The default value depends on the encap of the DS0 channel group and
             the signal-mode of the DS1/E1:
             For CEM encap on DS1/E1 with CAS signal mode    - 'allOnes'
             For all other encaps or non-CAS CEM DS1/E1      - 'notApplicable'
             
             For CEM channel groups on DS1/E1 with no CAS signalling and non-CEM
             encap channel groups the value cannot be changed.";
          smiv2:defval "notApplicable";
          smiv2:max-access "read-write";
          smiv2:oid "1.3.6.1.4.1.6527.3.1.2.2.4.13.1.14";
          config true;
        }
        leaf tmnxDS0ChanGroupSignalPattern {
          type uint32 {
            range "0..15";
          }
          description
            "The value of tmnxDS0ChanGroupSignalPattern specifies the idle signal
             fill pattern when the CAS CEM channel group experiences an underrun
             and tmnxDS0ChanGroupSignalFillType is set to 'userDefinedPattern'.
             
             CAS ESF DS1 and CAS E1 support 4 signalling bits per timeslot (ABCD)
             CAS SF DS1 supports 2 signalling bits per timeslot (AB)
             
             The default value depends on the type of channel group:
             For CAS DS1 ESF or CAS E1 channel group -  15 (Valid range 0..15)
             For CAS DS1 SF channel group            -   3 (Valid range 0..3)
             For non-CAS or non-CEM channel group    -   0 (Valid range 0..0)";
          smiv2:defval "0";
          smiv2:max-access "read-write";
          smiv2:oid "1.3.6.1.4.1.6527.3.1.2.2.4.13.1.15";
          config true;
        }
        leaf tmnxDS0ChanGroupBerSfLinkDown {
          type boolean;
          description
            "The value of tmnxDS0ChanGroupBerSfLinkDown specifies whether or not
             the DS0 channel-group will become operationally down when a BER-SF
             alarm is raised. If tmnxDS0ChanGroupBerSfLinkDown is false then the
             channel-group will not operationally change state due to BER-SF
             alarms.";
          smiv2:defval "false";
          smiv2:max-access "read-write";
          smiv2:oid "1.3.6.1.4.1.6527.3.1.2.2.4.13.1.16";
          config true;
        }
        config true;
      }
      config true;
    }
    container tmnxBundleTable {
      description
        "The tmnxBundleTable has an entry for a bundle created on the system.";
      smiv2:oid "1.3.6.1.4.1.6527.3.1.2.2.4.14";
      list tmnxBundleEntry {
        key "tmnxChassisIndex tmnxBundleBundleID";
        description
          "Each row entry represents a multilink bundle on a MDA.
           Entries can be created and deleted via SNMP SET operations
           using the tmnxBundleRowStatus object. The tmnxBundleBundleID will
           contain the bundle number encoded in it. The bundle number is
           unique for a MDA.
           For each tmnxBundleEntry, there will be a corresponding entry
           in the tmnxPortTable and the ifTable.";
        smiv2:oid "1.3.6.1.4.1.6527.3.1.2.2.4.14.1";
        leaf tmnxChassisIndex {
          type leafref {
            path "/timetra-chassis:TIMETRA-CHASSIS-MIB/timetra-chassis:tmnxChassisTable/timetra-chassis:tmnxChassisEntry/timetra-chassis:tmnxChassisIndex";
          }
          config true;
        }
        leaf tmnxBundleBundleID {
          type timetra-port:TmnxBundleID;
          description
            "tmnxBundleBundleID identifies this multilink bundle. The value of
             this object is calculated using the TiMOS encoding scheme described
             in TmnxBundleID.
             tmnxBundleBundleID is used as an index into the ifTable and the
             tmnxPortTable to access an entry corresponding to this entry.";
          smiv2:max-access "not-accessible";
          smiv2:oid "1.3.6.1.4.1.6527.3.1.2.2.4.14.1.1";
          config true;
        }
        leaf tmnxBundleRowStatus {
          type snmpv2-tc:RowStatus;
          description
            "tmnxBundleRowStatus controls the creation and deletion of
             row entries in the tmnxBundleTable.
             
             The manager has to first calculate the tmnxBundleBundleID
             based on the TiMOS encoding.";
          smiv2:max-access "read-write";
          smiv2:oid "1.3.6.1.4.1.6527.3.1.2.2.4.14.1.2";
          config false;
        }
        leaf tmnxBundleType {
          type enumeration {
            enum "mlppp" {
              value 1;
            }
            enum "mlfr" {
              value 2;
            }
            enum "imagrp" {
              value 3;
            }
          }
          description
            "tmnxBundleType specifies the type of this multilink bundle.
             It provides a reference as to the type of bundle this row
             refers to but does not map to the direct value of
             bndle type defined in TmnxBundleID.";
          smiv2:defval "mlppp";
          smiv2:max-access "read-write";
          smiv2:oid "1.3.6.1.4.1.6527.3.1.2.2.4.14.1.3";
          config true;
        }
        leaf tmnxBundleMinimumLinks {
          type uint32 {
            range "1..8";
          }
          description
            "tmnxBundleMinimumLinks is the minimum number of links that must be
             active for a bundle to be active. If the number of links drop below
             the given minimum then the multilink bundle will transition to an
             operation down state.";
          smiv2:max-access "read-write";
          smiv2:oid "1.3.6.1.4.1.6527.3.1.2.2.4.14.1.4";
          config true;
        }
        leaf tmnxBundleNumLinks {
          type uint32;
          description
            "tmnxBundleNumLinks indicates the total number of links configured
             for this bundle.";
          smiv2:max-access "read-only";
          smiv2:oid "1.3.6.1.4.1.6527.3.1.2.2.4.14.1.5";
          config false;
        }
        leaf tmnxBundleNumActiveLinks {
          type uint32;
          description
            "tmnxBundleNumActiveLinks indicates the current number of active links
             belonging to this bundle.";
          smiv2:max-access "read-only";
          smiv2:oid "1.3.6.1.4.1.6527.3.1.2.2.4.14.1.6";
          config false;
        }
        leaf tmnxBundleMRRU {
          type uint32 {
            range "0|1500..9206";
          }
          units "bytes";
          description
            "tmnxBundleMRRU is used to configure the
             Max Received Reconstructed Unit (MRRU). This is the maximum frame that
             can be reconstructed from multilink fragments.
             This object is only applicable to tmnxBundleType value of mlppp.
             All non applicable types have a value of zero.";
          smiv2:defval "1524";
          smiv2:max-access "read-write";
          smiv2:oid "1.3.6.1.4.1.6527.3.1.2.2.4.14.1.7";
          config true;
        }
        leaf tmnxBundleOperMRRU {
          type uint32;
          units "bytes";
          description
            "tmnxBundleOperMRRU indicates the operational value of
             Max Received Reconstructed Unit (MRRU).
             This object is only applicable to tmnxBundleType value of mlppp.
             All non applicable types have a value of zero.";
          smiv2:max-access "read-only";
          smiv2:oid "1.3.6.1.4.1.6527.3.1.2.2.4.14.1.8";
          config false;
        }
        leaf tmnxBundlePeerMRRU {
          type uint32;
          units "bytes";
          description
            "tmnxBundlePeerMRRU indicates the MRRU value sent by the peer
             during negotiation.
             This object is only applicable to tmnxBundleType value of mlppp.
             All non applicable types have a value of zero.";
          smiv2:max-access "read-only";
          smiv2:oid "1.3.6.1.4.1.6527.3.1.2.2.4.14.1.9";
          config false;
        }
        leaf tmnxBundleOperMTU {
          type uint32;
          units "bytes";
          description
            "tmnxBundleOperMTU indicates the operational MTU of the bundle.";
          smiv2:max-access "read-only";
          smiv2:oid "1.3.6.1.4.1.6527.3.1.2.2.4.14.1.10";
          config false;
        }
        leaf tmnxBundleRedDiffDelay {
          type uint32 {
            range "0..50|0..25";
          }
          units "milliseconds";
          description
            "tmnxBundleRedDiffDelay configures the maximum acceptable differential
             delay for individual circuits within this multilink bundle. If
             the delay exceeds this threshold, a tmnxEqPortBndlRedDiffExceeded
             trap is issued.
             
             For a tmnxBundleType value of 'imagrp' a range of 0 to 50 is supported,
             0 to 25 otherwise.";
          smiv2:max-access "read-write";
          smiv2:oid "1.3.6.1.4.1.6527.3.1.2.2.4.14.1.11";
          config true;
        }
        leaf tmnxBundleRedDiffDelayAction {
          type enumeration {
            enum "none" {
              value 0;
            }
            enum "down" {
              value 1;
            }
          }
          description
            "tmnxBundleRedDiffDelayAction specifies the action to be taken
             when the differential delay exceeds the threshold configured in
             tmnxBundleRedDiffDelay.
             For a tmnxBundleType value of 'imagrp', only the down action is
             supported.";
          smiv2:defval "none";
          smiv2:max-access "read-write";
          smiv2:oid "1.3.6.1.4.1.6527.3.1.2.2.4.14.1.12";
          config true;
        }
        leaf tmnxBundleYellowDiffDelay {
          type uint32 {
            range "0..25";
          }
          units "milliseconds";
          description
            "tmnxBundleYellowDiffDelay configures the yellow warning
             threshold for the differential delay for the circuits
             within a given multilink bundle. If the delay exceeds this
             threshold, a tmnxEqPortBndlYellowDiffExceeded trap is issued.
             This object is only applicable to tmnxBundleType values of
             'mlppp' or 'mlfr'. All non applicable types have a value
             of zero.";
          smiv2:max-access "read-write";
          smiv2:oid "1.3.6.1.4.1.6527.3.1.2.2.4.14.1.13";
          config true;
        }
        leaf tmnxBundleShortSequence {
          type boolean;
          description
            "tmnxBundleShortSequence command specifies that the MLPPP bundle
             should use short (12 bit) sequence numbers. Instead of the
             standard long (24 bits) sequence number.
             This object is only applicable to tmnxBundleType value of mlppp.";
          smiv2:defval "false";
          smiv2:max-access "read-write";
          smiv2:oid "1.3.6.1.4.1.6527.3.1.2.2.4.14.1.14";
          config true;
        }
        leaf tmnxBundleLastChangeTime {
          type yang:timestamp;
          description
            "The tmnxBundleLastChangeTime variable contains the sysUpTime
             value of the most recently modified writable variable in the
             tmnxBundleEntry row for this channel group.";
          smiv2:max-access "read-only";
          smiv2:oid "1.3.6.1.4.1.6527.3.1.2.2.4.14.1.15";
          config false;
        }
        leaf tmnxBundleFragmentThreshold {
          type uint32 {
            range "0|128..512";
          }
          units "bytes";
          description
            "The value of tmnxBundleFragmentThreshold specifies the maximum length
             of a fragment transmitted across the multilink bundle. Values supported
             within each bundle type are hardware dependent. The value of 0
             specifies no fragmentation.
             
             Currently, the following values are supported depending upon the
             tmnxBundleType value:
             
                 tmnxBundleType         tmnxBundleFragmentThreshold values supported
                  mlppp                   0; 128 to 512 inclusive
                  imagrp                  128
                  mlfr                    0; 128 to 512 inclusive";
          smiv2:defval "128";
          smiv2:max-access "read-write";
          smiv2:oid "1.3.6.1.4.1.6527.3.1.2.2.4.14.1.16";
          config true;
        }
        leaf tmnxBundleUpTime {
          type uint32;
          units "seconds";
          description
            "tmnxBundleUpTime indicates the time since the bundle is operationally
             'inService'.";
          smiv2:max-access "read-only";
          smiv2:oid "1.3.6.1.4.1.6527.3.1.2.2.4.14.1.17";
          config false;
        }
        leaf tmnxBundleInputDiscards {
          type yang:counter32;
          description
            "tmnxBundleInputDiscards indicates the number of LCP packets that
             were discarded. This object is only supported for a
             tmnxBundleType value of mlppp.";
          smiv2:max-access "read-only";
          smiv2:oid "1.3.6.1.4.1.6527.3.1.2.2.4.14.1.18";
          config false;
        }
        leaf tmnxBundlePrimaryMemberPortID {
          type timetra-tc:TmnxPortID;
          description
            "tmnxBundlePrimaryMemberPortID indicates the TmnxPortID of the primary
             member of this bundle. The value of this object will be zero if
             there are no members configured in this bundle.";
          smiv2:max-access "read-only";
          smiv2:oid "1.3.6.1.4.1.6527.3.1.2.2.4.14.1.19";
          config false;
        }
        leaf tmnxBundleLFI {
          type boolean;
          description
            "tmnxBundleLFI specifies if Link Fragmentation and
             Interleaving is enabled on the multilink bundle. A value of 'false'
             indicates that Link Fragmentation and Interleaving is disabled on the
             multilink bundle while a value of 'true' indicates that Link
             Fragmentation and Interleaving is enabled on the multilink bundle.
             
             This object is only supported for tmnxBundleType value of mlppp.
             
             The value of tmnxBundleLFI may be modified only when no members are
             part of the bundle.
             
             This object cannot be set to true when tmnxBundleMlpppClassCount object
             value is set to enable Multiclass MLPPP on the bundle.";
          smiv2:defval "false";
          smiv2:max-access "read-write";
          smiv2:oid "1.3.6.1.4.1.6527.3.1.2.2.4.14.1.20";
          config true;
        }
        leaf tmnxBundleProtectedType {
          type enumeration {
            enum "none" {
              value 0;
            }
            enum "working" {
              value 1;
            }
            enum "protection" {
              value 2;
            }
          }
          description
            "tmnxBundleProtectedType identifies how this bundle is part
             of a tmnxBundleParentBundle. A value of 'none' identifies no
             protection, 'working' identifies it to be a working bundle of a
             tmnxBundleParentBundle and 'protection' identifies it to be a
             protection bundle of a tmnxBundleParentBundle.
             tmnxBundleProtectedType can only be set at row creation.";
          smiv2:defval "none";
          smiv2:max-access "read-write";
          smiv2:oid "1.3.6.1.4.1.6527.3.1.2.2.4.14.1.21";
          config true;
        }
        leaf tmnxBundleParentBundle {
          type timetra-port:TmnxBundleID;
          description
            "tmnxBundleParentBundle specifies the parent to which this bundle
             belongs.  A row for the given non zero walue of tmnxBundleParentBundle
             must exist for this row to be successfully created. If a bundle has no
             parent, its value is zero. tmnxBundleParentBundle can only be set at
             row creation.";
          smiv2:defval "0";
          smiv2:max-access "read-write";
          smiv2:oid "1.3.6.1.4.1.6527.3.1.2.2.4.14.1.22";
          config true;
        }
        config true;
      }
      config true;
    }
    container tmnxBundleMemberTable {
      description
        "The tmnxBundleMemberTable has an entry for a member port
         associated with a multilink bundle.";
      smiv2:oid "1.3.6.1.4.1.6527.3.1.2.2.4.15";
      list tmnxBundleMemberEntry {
        key "tmnxBundleBundleID tmnxPortPortID";
        description
          "Each row represents a port associated with a bundle. Entries
           can be added or removed from this table using SNMP SET operation.";
        smiv2:oid "1.3.6.1.4.1.6527.3.1.2.2.4.15.1";
        leaf tmnxBundleBundleID {
          type leafref {
            path "/timetra-port:TIMETRA-PORT-MIB/timetra-port:tmnxBundleTable/timetra-port:tmnxBundleEntry/timetra-port:tmnxBundleBundleID";
          }
        }
        leaf tmnxPortPortID {
          type leafref {
            path "/timetra-port:TIMETRA-PORT-MIB/timetra-port:tmnxPortTable/timetra-port:tmnxPortEntry/timetra-port:tmnxPortPortID";
          }
        }
        leaf tmnxBundleMemberRowStatus {
          type snmpv2-tc:RowStatus;
          description
            "tmnxBundleMemberRowStatus controls the creation and deletion of
             row entries in the tmnxBundleMemberTable.
             tmnxPortPortID identifies the port to be associated with the bundle.
             A bundle entry with tmnxBundleBundleID has to exist in the
             tmnxBundleTable before creating an entry in this table.";
          smiv2:max-access "read-write";
          smiv2:oid "1.3.6.1.4.1.6527.3.1.2.2.4.15.1.1";
        }
        leaf tmnxBundleMemberActive {
          type boolean;
          description
            "tmnxBundleMemberActive is set to 'false' for one of reasons in
             tmnxBundleMemberDownReason.";
          smiv2:max-access "read-only";
          smiv2:oid "1.3.6.1.4.1.6527.3.1.2.2.4.15.1.2";
        }
        leaf tmnxBundleMemberDownReason {
          type enumeration {
            enum "none" {
              value 0;
            }
            enum "outOfService" {
              value 1;
            }
            enum "redDiffDelayExceeded" {
              value 2;
            }
            enum "mismatchEndPtDiscriminator" {
              value 3;
            }
            enum "peerNotBundleMember" {
              value 4;
            }
            enum "underNegotiation" {
              value 5;
            }
            enum "peerInvalidMlHdrFmt" {
              value 6;
            }
            enum "other" {
              value 7;
            }
          }
          description
            "tmnxBundleMemberDownReason contains the reason code for marking
             the member link of the bundle to down (i.e. tmnxBundleMemberActive
             will be set to false):
                 none - The link is active and the value of tmnxBundleMemberActive
                        is 'true'.
                 outOfService - The link operational status is down.
                 redDiffDelayExceeded - The differential delay of the link
                        exceeded the configured value of red differential delay
                        and tmnxBundleRedDiffDelayAction was configured as 'down'.
                 mismatchEndPtDiscriminator - Detected inconsistent peer endpoint
                        discriminator for the bundle.
                 peerNotBundleMember - When the peer is either not added to the
                        bundle or is removed from the bundle.
                 underNegotiation - When the local end is trying to negotiate with
                        the peer.
                 peerInvalidMlHdrFmt - The peer does not support the required ML-PPP
                        header format. The remote peer must support the same
                        short/long sequence code, and at least as many classes as
                        configured for the local bundle.
                 other - Refer to the corresponding member table, if any, for more
                         information based on the tmnxBundleType.";
          smiv2:max-access "read-only";
          smiv2:oid "1.3.6.1.4.1.6527.3.1.2.2.4.15.1.3";
        }
        leaf tmnxBundleMemberUpTime {
          type uint32;
          units "seconds";
          description
            "tmnxBundleMemberUpTime indicates the time since the bundle member is
             active as indicated by tmnxBundleMemberActive.";
          smiv2:max-access "read-only";
          smiv2:oid "1.3.6.1.4.1.6527.3.1.2.2.4.15.1.4";
        }
      }
      config false;
    }
    container tmnxPortToChannelTable {
      description
        "The tmnxPortToChannelTable is a mapping table. Given a chassis index,
         physical port index and channel string, it maps it to the index
         of the channel. This channel index can then be used as an index
         into the ifTable or the tmnxPortTable.";
      smiv2:oid "1.3.6.1.4.1.6527.3.1.2.2.4.16";
      list tmnxPortToChannelEntry {
        key "tmnxChassisIndex tmnxPortPortID tmnxChannelIdxString";
        description
          "Each row represents a mapping of the physical port index and the
           channel index string to the index of the channel.";
        smiv2:oid "1.3.6.1.4.1.6527.3.1.2.2.4.16.1";
        leaf tmnxChassisIndex {
          type leafref {
            path "/timetra-chassis:TIMETRA-CHASSIS-MIB/timetra-chassis:tmnxChassisTable/timetra-chassis:tmnxChassisEntry/timetra-chassis:tmnxChassisIndex";
          }
        }
        leaf tmnxPortPortID {
          type leafref {
            path "/timetra-port:TIMETRA-PORT-MIB/timetra-port:tmnxPortTable/timetra-port:tmnxPortEntry/timetra-port:tmnxPortPortID";
          }
        }
        leaf tmnxChannelIdxString {
          type snmpv2-tc:DisplayString;
          description
            "tmnxChannelIdxString is an index into the table. It contains
             a string identifying a channel on the physical port.";
          smiv2:max-access "not-accessible";
          smiv2:oid "1.3.6.1.4.1.6527.3.1.2.2.4.16.1.1";
        }
        leaf tmnxChannelPortID {
          type timetra-tc:TmnxPortID;
          description
            "tmnxChannelPortID contains the port ID of the channel. This value
             is used to identify the entry for this channel in the ifTable or
             the tmnxPortTable.";
          smiv2:max-access "read-only";
          smiv2:oid "1.3.6.1.4.1.6527.3.1.2.2.4.16.1.2";
        }
      }
      config false;
    }
    container tmnxPortIngrMdaQosStatTable {
      description
        "The table tmnxPortIngrMdaQosStatTable contains a row for each ethernet
         or SONET/SDH port located on an oversubscribed MDA.
         
         Each object in a row refers to a QoS priority and forwarding class,
         which is a decimal value between 00 and 15 inclusive.  The following
         table describes each decimal value:
         
                              | Priority
                              |------------------
         Forwarding Class     | High       Low
         ----------------------------------------
         NC (Network Control) | 00         01
         H1 (Voice)           | 02         03
         EF (Premium)         | 04         05
         H2 (Video)           | 06         07
         L1 (Management)      | 08         09
         AF (Assured)         | 10         11
         L2 (Priority)        | 12         13
         BE (Best Effort)     | 14         15";
      smiv2:oid "1.3.6.1.4.1.6527.3.1.2.2.4.17";
      list tmnxPortIngrMdaQosStatEntry {
        key "tmnxChassisIndex tmnxPortPortID";
        description
          "Each row indicates the MDA QoS discard statistics on an ethernet or
           SONET/SDH port located on an oversubscribed MDA. For ethernet ports,
           the tmnxPortEtherIngressRate object indicates the ingress shaping
           rate configured.";
        smiv2:oid "1.3.6.1.4.1.6527.3.1.2.2.4.17.1";
        leaf tmnxChassisIndex {
          type leafref {
            path "/timetra-chassis:TIMETRA-CHASSIS-MIB/timetra-chassis:tmnxChassisTable/timetra-chassis:tmnxChassisEntry/timetra-chassis:tmnxChassisIndex";
          }
        }
        leaf tmnxPortPortID {
          type leafref {
            path "/timetra-port:TIMETRA-PORT-MIB/timetra-port:tmnxPortTable/timetra-port:tmnxPortEntry/timetra-port:tmnxPortPortID";
          }
        }
        leaf tmnxPortIngrMdaQos00StatDropPkts {
          type yang:counter64;
          description
            "tmnxPortIngrMdaQos00StatDropPkts indicates the number of packets
             dropped on the oversubscribed MDA for QoS classifier result threshold
             00 because of an overload condition on the MDA.";
          smiv2:max-access "read-only";
          smiv2:oid "1.3.6.1.4.1.6527.3.1.2.2.4.17.1.1";
        }
        leaf tmnxPortIngrMdaQos00StatDropOcts {
          type yang:counter64;
          description
            "tmnxPortIngrMdaQos00StatDropOcts indicates the number of octets
             dropped on the oversubscribed MDA for QoS classifier result threshold
             00 because of an overload condition on the MDA.";
          smiv2:max-access "read-only";
          smiv2:oid "1.3.6.1.4.1.6527.3.1.2.2.4.17.1.2";
        }
        leaf tmnxPortIngrMdaQos01StatDropPkts {
          type yang:counter64;
          description
            "tmnxPortIngrMdaQos01StatDropPkts indicates the number of packets
             dropped on the oversubscribed MDA for QoS classifier result threshold
             01 because of an overload condition on the MDA.";
          smiv2:max-access "read-only";
          smiv2:oid "1.3.6.1.4.1.6527.3.1.2.2.4.17.1.3";
        }
        leaf tmnxPortIngrMdaQos01StatDropOcts {
          type yang:counter64;
          description
            "tmnxPortIngrMdaQos01StatDropOcts indicates the number of octets
             dropped on the oversubscribed MDA for QoS classifier result threshold
             01 because of an overload condition on the MDA.";
          smiv2:max-access "read-only";
          smiv2:oid "1.3.6.1.4.1.6527.3.1.2.2.4.17.1.4";
        }
        leaf tmnxPortIngrMdaQos02StatDropPkts {
          type yang:counter64;
          description
            "tmnxPortIngrMdaQos02StatDropPkts indicates the number of packets
             dropped on the oversubscribed MDA for QoS classifier result threshold
             02 because of an overload condition on the MDA.";
          smiv2:max-access "read-only";
          smiv2:oid "1.3.6.1.4.1.6527.3.1.2.2.4.17.1.5";
        }
        leaf tmnxPortIngrMdaQos02StatDropOcts {
          type yang:counter64;
          description
            "tmnxPortIngrMdaQos02StatDropOcts indicates the number of octets
             dropped on the oversubscribed MDA for QoS classifier result threshold
             02 because of an overload condition on the MDA.";
          smiv2:max-access "read-only";
          smiv2:oid "1.3.6.1.4.1.6527.3.1.2.2.4.17.1.6";
        }
        leaf tmnxPortIngrMdaQos03StatDropPkts {
          type yang:counter64;
          description
            "tmnxPortIngrMdaQos03StatDropPkts indicates the number of packets
             dropped on the oversubscribed MDA for QoS classifier result threshold
             03 because of an overload condition on the MDA.";
          smiv2:max-access "read-only";
          smiv2:oid "1.3.6.1.4.1.6527.3.1.2.2.4.17.1.7";
        }
        leaf tmnxPortIngrMdaQos03StatDropOcts {
          type yang:counter64;
          description
            "tmnxPortIngrMdaQos03StatDropOcts indicates the number of octets
             dropped on the oversubscribed MDA for QoS classifier result threshold
             03 because of an overload condition on the MDA.";
          smiv2:max-access "read-only";
          smiv2:oid "1.3.6.1.4.1.6527.3.1.2.2.4.17.1.8";
        }
        leaf tmnxPortIngrMdaQos04StatDropPkts {
          type yang:counter64;
          description
            "tmnxPortIngrMdaQos04StatDropPkts indicates the number of packets
             dropped on the oversubscribed MDA for QoS classifier result threshold
             04 because of an overload condition on the MDA.";
          smiv2:max-access "read-only";
          smiv2:oid "1.3.6.1.4.1.6527.3.1.2.2.4.17.1.9";
        }
        leaf tmnxPortIngrMdaQos04StatDropOcts {
          type yang:counter64;
          description
            "tmnxPortIngrMdaQos04StatDropOcts indicates the number of octets
             dropped on the oversubscribed MDA for QoS classifier result threshold
             04 because of an overload condition on the MDA.";
          smiv2:max-access "read-only";
          smiv2:oid "1.3.6.1.4.1.6527.3.1.2.2.4.17.1.10";
        }
        leaf tmnxPortIngrMdaQos05StatDropPkts {
          type yang:counter64;
          description
            "tmnxPortIngrMdaQos05StatDropPkts indicates the number of packets
             dropped on the oversubscribed MDA for QoS classifier result threshold
             05 because of an overload condition on the MDA.";
          smiv2:max-access "read-only";
          smiv2:oid "1.3.6.1.4.1.6527.3.1.2.2.4.17.1.11";
        }
        leaf tmnxPortIngrMdaQos05StatDropOcts {
          type yang:counter64;
          description
            "tmnxPortIngrMdaQos05StatDropOcts indicates the number of octets
             dropped on the oversubscribed MDA for QoS classifier result threshold
             05 because of an overload condition on the MDA.";
          smiv2:max-access "read-only";
          smiv2:oid "1.3.6.1.4.1.6527.3.1.2.2.4.17.1.12";
        }
        leaf tmnxPortIngrMdaQos06StatDropPkts {
          type yang:counter64;
          description
            "tmnxPortIngrMdaQos06StatDropPkts indicates the number of packets
             dropped on the oversubscribed MDA for QoS classifier result threshold
             06 because of an overload condition on the MDA.";
          smiv2:max-access "read-only";
          smiv2:oid "1.3.6.1.4.1.6527.3.1.2.2.4.17.1.13";
        }
        leaf tmnxPortIngrMdaQos06StatDropOcts {
          type yang:counter64;
          description
            "tmnxPortIngrMdaQos06StatDropOcts indicates the number of octets
             dropped on the oversubscribed MDA for QoS classifier result threshold
             06 because of an overload condition on the MDA.";
          smiv2:max-access "read-only";
          smiv2:oid "1.3.6.1.4.1.6527.3.1.2.2.4.17.1.14";
        }
        leaf tmnxPortIngrMdaQos07StatDropPkts {
          type yang:counter64;
          description
            "tmnxPortIngrMdaQos07StatDropPkts indicates the number of packets
             dropped on the oversubscribed MDA for QoS classifier result threshold
             07 because of an overload condition on the MDA.";
          smiv2:max-access "read-only";
          smiv2:oid "1.3.6.1.4.1.6527.3.1.2.2.4.17.1.15";
        }
        leaf tmnxPortIngrMdaQos07StatDropOcts {
          type yang:counter64;
          description
            "tmnxPortIngrMdaQos07StatDropOcts indicates the number of octets
             dropped on the oversubscribed MDA for QoS classifier result threshold
             07 because of an overload condition on the MDA.";
          smiv2:max-access "read-only";
          smiv2:oid "1.3.6.1.4.1.6527.3.1.2.2.4.17.1.16";
        }
        leaf tmnxPortIngrMdaQos08StatDropPkts {
          type yang:counter64;
          description
            "tmnxPortIngrMdaQos08StatDropPkts indicates the number of packets
             dropped on the oversubscribed MDA for QoS classifier result threshold
             08 because of an overload condition on the MDA.";
          smiv2:max-access "read-only";
          smiv2:oid "1.3.6.1.4.1.6527.3.1.2.2.4.17.1.17";
        }
        leaf tmnxPortIngrMdaQos08StatDropOcts {
          type yang:counter64;
          description
            "tmnxPortIngrMdaQos08StatDropOcts indicates the number of octets
             dropped on the oversubscribed MDA for QoS classifier result threshold
             08 because of an overload condition on the MDA.";
          smiv2:max-access "read-only";
          smiv2:oid "1.3.6.1.4.1.6527.3.1.2.2.4.17.1.18";
        }
        leaf tmnxPortIngrMdaQos09StatDropPkts {
          type yang:counter64;
          description
            "tmnxPortIngrMdaQos09StatDropPkts indicates the number of packets
             dropped on the oversubscribed MDA for QoS classifier result threshold
             09 because of an overload condition on the MDA.";
          smiv2:max-access "read-only";
          smiv2:oid "1.3.6.1.4.1.6527.3.1.2.2.4.17.1.19";
        }
        leaf tmnxPortIngrMdaQos09StatDropOcts {
          type yang:counter64;
          description
            "tmnxPortIngrMdaQos09StatDropOcts indicates the number of octets
             dropped on the oversubscribed MDA for QoS classifier result threshold
             09 because of an overload condition on the MDA.";
          smiv2:max-access "read-only";
          smiv2:oid "1.3.6.1.4.1.6527.3.1.2.2.4.17.1.20";
        }
        leaf tmnxPortIngrMdaQos10StatDropPkts {
          type yang:counter64;
          description
            "tmnxPortIngrMdaQos10StatDropPkts indicates the number of packets
             dropped on the oversubscribed MDA for QoS classifier result threshold
             10 because of an overload condition on the MDA.";
          smiv2:max-access "read-only";
          smiv2:oid "1.3.6.1.4.1.6527.3.1.2.2.4.17.1.21";
        }
        leaf tmnxPortIngrMdaQos10StatDropOcts {
          type yang:counter64;
          description
            "tmnxPortIngrMdaQos10StatDropOcts indicates the number of octets
             dropped on the oversubscribed MDA for QoS classifier result threshold
             10 because of an overload condition on the MDA.";
          smiv2:max-access "read-only";
          smiv2:oid "1.3.6.1.4.1.6527.3.1.2.2.4.17.1.22";
        }
        leaf tmnxPortIngrMdaQos11StatDropPkts {
          type yang:counter64;
          description
            "tmnxPortIngrMdaQos11StatDropPkts indicates the number of packets
             dropped on the oversubscribed MDA for QoS classifier result threshold
             11 because of an overload condition on the MDA.";
          smiv2:max-access "read-only";
          smiv2:oid "1.3.6.1.4.1.6527.3.1.2.2.4.17.1.23";
        }
        leaf tmnxPortIngrMdaQos11StatDropOcts {
          type yang:counter64;
          description
            "tmnxPortIngrMdaQos11StatDropOcts indicates the number of octets
             dropped on the oversubscribed MDA for QoS classifier result threshold
             11 because of an overload condition on the MDA.";
          smiv2:max-access "read-only";
          smiv2:oid "1.3.6.1.4.1.6527.3.1.2.2.4.17.1.24";
        }
        leaf tmnxPortIngrMdaQos12StatDropPkts {
          type yang:counter64;
          description
            "tmnxPortIngrMdaQos12StatDropPkts indicates the number of packets
             dropped on the oversubscribed MDA for QoS classifier result threshold
             12 because of an overload condition on the MDA.";
          smiv2:max-access "read-only";
          smiv2:oid "1.3.6.1.4.1.6527.3.1.2.2.4.17.1.25";
        }
        leaf tmnxPortIngrMdaQos12StatDropOcts {
          type yang:counter64;
          description
            "tmnxPortIngrMdaQos12StatDropOcts indicates the number of octets
             dropped on the oversubscribed MDA for QoS classifier result threshold
             12 because of an overload condition on the MDA.";
          smiv2:max-access "read-only";
          smiv2:oid "1.3.6.1.4.1.6527.3.1.2.2.4.17.1.26";
        }
        leaf tmnxPortIngrMdaQos13StatDropPkts {
          type yang:counter64;
          description
            "tmnxPortIngrMdaQos13StatDropPkts indicates the number of packets
             dropped on the oversubscribed MDA for QoS classifier result threshold
             13 because of an overload condition on the MDA.";
          smiv2:max-access "read-only";
          smiv2:oid "1.3.6.1.4.1.6527.3.1.2.2.4.17.1.27";
        }
        leaf tmnxPortIngrMdaQos13StatDropOcts {
          type yang:counter64;
          description
            "tmnxPortIngrMdaQos13StatDropOcts indicates the number of octets
             dropped on the oversubscribed MDA for QoS classifier result threshold
             13 because of an overload condition on the MDA.";
          smiv2:max-access "read-only";
          smiv2:oid "1.3.6.1.4.1.6527.3.1.2.2.4.17.1.28";
        }
        leaf tmnxPortIngrMdaQos14StatDropPkts {
          type yang:counter64;
          description
            "tmnxPortIngrMdaQos14StatDropPkts indicates the number of packets
             dropped on the oversubscribed MDA for QoS classifier result threshold
             14 because of an overload condition on the MDA.";
          smiv2:max-access "read-only";
          smiv2:oid "1.3.6.1.4.1.6527.3.1.2.2.4.17.1.29";
        }
        leaf tmnxPortIngrMdaQos14StatDropOcts {
          type yang:counter64;
          description
            "tmnxPortIngrMdaQos14StatDropOcts indicates the number of octets
             dropped on the oversubscribed MDA for QoS classifier result threshold
             14 because of an overload condition on the MDA.";
          smiv2:max-access "read-only";
          smiv2:oid "1.3.6.1.4.1.6527.3.1.2.2.4.17.1.30";
        }
        leaf tmnxPortIngrMdaQos15StatDropPkts {
          type yang:counter64;
          description
            "tmnxPortIngrMdaQos15StatDropPkts indicates the number of packets
             dropped on the oversubscribed MDA for QoS classifier result threshold
             15 because of an overload condition on the MDA.";
          smiv2:max-access "read-only";
          smiv2:oid "1.3.6.1.4.1.6527.3.1.2.2.4.17.1.31";
        }
        leaf tmnxPortIngrMdaQos15StatDropOcts {
          type yang:counter64;
          description
            "tmnxPortIngrMdaQos15StatDropOcts indicates the number of octets
             dropped on the oversubscribed MDA for QoS classifier result threshold
             15 because of an overload condition on the MDA.";
          smiv2:max-access "read-only";
          smiv2:oid "1.3.6.1.4.1.6527.3.1.2.2.4.17.1.32";
        }
      }
      config false;
    }
    container tmnxSonetGroupTable {
      description
        "The tmnxSonetGroupTable has an entry for each
         Tributary Unit Group(TUG3) on a path. On a port which supports
         unchannelized STS-3's, rows in this table are created when a
         channelized STS-3 has its tmnxSonetPathChildType set to sdhTug3.
         On a port which does not support unchannelized STS-3's, the rows
         in this table are implicitly created when a STS-3 is created
         in the tmnxSonetPathTable.  Entries in this table are implicitly
         deleted when the parent entry of this group is deleted from the
         tmnxSonetPathTable or if the tmnxSonetPathChildType of the parent
         is set to something other than sdhTug3.";
      smiv2:oid "1.3.6.1.4.1.6527.3.1.2.2.4.18";
      list tmnxSonetGroupEntry {
        key "tmnxChassisIndex tmnxPortPortID";
        description
          "Each row entry represents a Tributary Unit Group(TUG3) on a path.";
        smiv2:oid "1.3.6.1.4.1.6527.3.1.2.2.4.18.1";
        leaf tmnxChassisIndex {
          type leafref {
            path "/timetra-chassis:TIMETRA-CHASSIS-MIB/timetra-chassis:tmnxChassisTable/timetra-chassis:tmnxChassisEntry/timetra-chassis:tmnxChassisIndex";
          }
          config true;
        }
        leaf tmnxPortPortID {
          type leafref {
            path "/timetra-port:TIMETRA-PORT-MIB/timetra-port:tmnxPortTable/timetra-port:tmnxPortEntry/timetra-port:tmnxPortPortID";
          }
          config true;
        }
        leaf tmnxSonetGroupType {
          type timetra-chassis:TmnxMDAChanType;
          description
            "tmnxSonetGroupType indicates the sonet group type of this entry.
             For STS-3/STM-1 channelization, the value of this object will
             be 'sdhTug3'.";
          smiv2:max-access "read-only";
          smiv2:oid "1.3.6.1.4.1.6527.3.1.2.2.4.18.1.1";
          config false;
        }
        leaf tmnxSonetGroupParentPortID {
          type timetra-tc:TmnxPortID;
          description
            "tmnxSonetGroupParentPortID indicates the TmnxPortID of the parent of
             this group.";
          smiv2:max-access "read-only";
          smiv2:oid "1.3.6.1.4.1.6527.3.1.2.2.4.18.1.2";
          config false;
        }
        leaf tmnxSonetGroupChildType {
          type timetra-chassis:TmnxMDAChanType;
          description
            "tmnxSonetGroupChildType is used to configure the type of the children
             of this group. Based on the value of this object, entries of
             a certain channel type can be created in the tmnxSonetPathTable.
             For example, if the value of this object is set to 'sonetVt15',
             then 28 entries of type 'sonetVt15' can be created in
             the tmnxSonetPathTable.";
          smiv2:max-access "read-write";
          smiv2:oid "1.3.6.1.4.1.6527.3.1.2.2.4.18.1.3";
          config true;
        }
        leaf tmnxSonetGroupName {
          type timetra-tc:TNamedItemOrEmpty;
          description
            "tmnxSonetGroupName is the textual name for this sonet group.";
          smiv2:max-access "read-only";
          smiv2:oid "1.3.6.1.4.1.6527.3.1.2.2.4.18.1.4";
          config false;
        }
        config true;
      }
      config true;
    }
    container tmnxCiscoHDLCTable {
      description
        "The tmnxCiscoHDLCTable has an entry for each port in the system
         that is configured for Cisco HDLC. It contains the parameters related
         to Cisco HDLC protocol on this port.";
      smiv2:oid "1.3.6.1.4.1.6527.3.1.2.2.4.20";
      list tmnxCiscoHDLCEntry {
        key "tmnxChassisIndex tmnxPortPortID";
        description
          "The tmnxCiscoHDLCEntry specifies parameters for a particular
           interfaces running Cisco HDLC encapsulation. Entries cannot be created
           and deleted via SNMP SET operations.";
        smiv2:oid "1.3.6.1.4.1.6527.3.1.2.2.4.20.1";
        leaf tmnxChassisIndex {
          type leafref {
            path "/timetra-chassis:TIMETRA-CHASSIS-MIB/timetra-chassis:tmnxChassisTable/timetra-chassis:tmnxChassisEntry/timetra-chassis:tmnxChassisIndex";
          }
          config true;
        }
        leaf tmnxPortPortID {
          type leafref {
            path "/timetra-port:TIMETRA-PORT-MIB/timetra-port:tmnxPortTable/timetra-port:tmnxPortEntry/timetra-port:tmnxPortPortID";
          }
          config true;
        }
        leaf tmnxCiscoHDLCKeepAliveInt {
          type uint32 {
            range "0..300";
          }
          units "seconds";
          description
            "tmnxCiscoHDLCKeepAliveInt specifies the interval in seconds
             used for sending periodic keepalive packets. The default value is set
             to 10 seconds. A value of 0 specifies that the keepalive function is
             turned off.
             
             It is expected that the nodes at the two endpoints of
             the Cisco HDLC link are provisioned with the same values.";
          smiv2:defval "10";
          smiv2:max-access "read-write";
          smiv2:oid "1.3.6.1.4.1.6527.3.1.2.2.4.20.1.1";
          config true;
        }
        leaf tmnxCiscoHDLCUpCount {
          type uint32 {
            range "1..3";
          }
          description
            "tmnxCiscoHDLCUpCount specifies the number of continual
             keepalive packets that has to be received to declare the link up.
             
             It is expected that the nodes at the two endpoints of
             the Cisco HDLC link are provisioned with the same values.";
          smiv2:defval "1";
          smiv2:max-access "read-write";
          smiv2:oid "1.3.6.1.4.1.6527.3.1.2.2.4.20.1.2";
          config true;
        }
        leaf tmnxCiscoHDLCDownCount {
          type uint32 {
            range "3..16";
          }
          description
            "tmnxCiscoHDLCDownCount specifies the number of
             'tmnxCiscoHDLCKeepAliveInt' intervals that must
             pass without receiving a keepalive packet before the
             link is declared down.
             
             It is expected that the nodes at the two endpoints of
             the Cisco HDLC link are provisioned with the same values.";
          smiv2:defval "3";
          smiv2:max-access "read-write";
          smiv2:oid "1.3.6.1.4.1.6527.3.1.2.2.4.20.1.3";
          config true;
        }
        leaf tmnxCiscoHDLCOperState {
          type timetra-tc:TmnxOperState;
          description
            "The value of tmnxCiscoHDLCOperState indicates the operational
             status of the Cisco HDLC protocol for this port.";
          smiv2:max-access "read-only";
          smiv2:oid "1.3.6.1.4.1.6527.3.1.2.2.4.20.1.4";
          config false;
        }
        config true;
      }
      config true;
    }
    container tmnxBundleImaGrpTable {
      description
        "The tmnxBundleImaGrpTable contains IMA Group data";
      smiv2:oid "1.3.6.1.4.1.6527.3.1.2.2.4.21";
      list tmnxBundleImaGrpEntry {
        key "tmnxChassisIndex tmnxBundleBundleID";
        description
          "Each row entry contains data on an IMA Group.";
        smiv2:oid "1.3.6.1.4.1.6527.3.1.2.2.4.21.1";
        leaf tmnxChassisIndex {
          type leafref {
            path "/timetra-chassis:TIMETRA-CHASSIS-MIB/timetra-chassis:tmnxChassisTable/timetra-chassis:tmnxChassisEntry/timetra-chassis:tmnxChassisIndex";
          }
          config true;
        }
        leaf tmnxBundleBundleID {
          type leafref {
            path "/timetra-port:TIMETRA-PORT-MIB/timetra-port:tmnxBundleTable/timetra-port:tmnxBundleEntry/timetra-port:tmnxBundleBundleID";
          }
          config true;
        }
        leaf tmnxBundleImaGrpLnkActTimer {
          type uint32 {
            range "1..30000";
          }
          units "milliseconds";
          description
            "tmnxBundleImaGrpLnkActTimer specifies the Link Activation Timer
             used to clear an existing LIF, LODS and FRI-IMA alarm. The time
             specified determines how long is needed for member links to
             stabilize before being activated.";
          smiv2:defval "10000";
          smiv2:max-access "read-write";
          smiv2:oid "1.3.6.1.4.1.6527.3.1.2.2.4.21.1.1";
          config true;
        }
        leaf tmnxBundleImaGrpLnkDeactTimer {
          type uint32 {
            range "1..30000";
          }
          units "milliseconds";
          description
            "tmnxBundleImaGrpLnkDeactTimer specifies the Link Deactivation Timer
             used to raise an LIF, LODS and FRI-IMA alarm. The time
             specified determines how long before a member link is declared in
             error and is deactivated.";
          smiv2:defval "2000";
          smiv2:max-access "read-write";
          smiv2:oid "1.3.6.1.4.1.6527.3.1.2.2.4.21.1.2";
          config true;
        }
        leaf tmnxBundleImaGrpSymmetryMode {
          type enumeration {
            enum "symmetric" {
              value 1;
            }
          }
          description
            "tmnxBundleImaGrpSymmetryMode specifies the type of cell rate
             transfer over the virtual link.";
          smiv2:defval "symmetric";
          smiv2:max-access "read-write";
          smiv2:oid "1.3.6.1.4.1.6527.3.1.2.2.4.21.1.3";
          config true;
        }
        leaf tmnxBundleImaGrpTxId {
          type int32;
          description
            "tmnxBundleImaGrpTxId specifies the IMA Id generated at group
             creation time used by the near-end.";
          smiv2:max-access "read-only";
          smiv2:oid "1.3.6.1.4.1.6527.3.1.2.2.4.21.1.4";
          config false;
        }
        leaf tmnxBundleImaGrpRxId {
          type int32;
          description
            "tmnxBundleImaGrpRxId specifies the IMA ID generated at group
             creation time used by the far-end.";
          smiv2:max-access "read-only";
          smiv2:oid "1.3.6.1.4.1.6527.3.1.2.2.4.21.1.5";
          config false;
        }
        leaf tmnxBundleImaGrpTxRefLnk {
          type timetra-tc:TmnxPortID;
          description
            "tmnxBundleImaGrpTxRefLnk specifies the IMA bundle member
             that was selected to be the transmit timing reference link.
             If no member has been selected as the reference link a value
             of zero is returned. ";
          smiv2:max-access "read-only";
          smiv2:oid "1.3.6.1.4.1.6527.3.1.2.2.4.21.1.6";
          config false;
        }
        leaf tmnxBundleImaGrpRxRefLnk {
          type timetra-tc:TmnxPortID;
          description
            "tmnxBundleImaGrpRxRefLnk specifies the IMA bundle member
             that was detected to be the receive timing reference link.
             If no member has been detected as the reference link a value
             of zero is returned. ";
          smiv2:max-access "read-only";
          smiv2:oid "1.3.6.1.4.1.6527.3.1.2.2.4.21.1.7";
          config false;
        }
        leaf tmnxBundleImaGrpSmNeState {
          type timetra-port:TmnxImaGrpState;
          description
            "tmnxBundleImaGrpSmNeState specifies the current state
             of the IMA Group for the near-end.";
          smiv2:max-access "read-only";
          smiv2:oid "1.3.6.1.4.1.6527.3.1.2.2.4.21.1.8";
          config false;
        }
        leaf tmnxBundleImaGrpSmFeState {
          type timetra-port:TmnxImaGrpState;
          description
            "tmnxBundleImaGrpSmFeState specifies the current state
             of the IMA Group for the far-end.";
          smiv2:max-access "read-only";
          smiv2:oid "1.3.6.1.4.1.6527.3.1.2.2.4.21.1.9";
          config false;
        }
        leaf tmnxBundleImaGrpSmFailState {
          type timetra-port:TmnxImaGrpFailState;
          description
            "tmnxBundleImaGrpSmFailState specifies the current state
             of the IMA Group.";
          smiv2:max-access "read-only";
          smiv2:oid "1.3.6.1.4.1.6527.3.1.2.2.4.21.1.10";
          config false;
        }
        leaf tmnxBundleImaGrpSmDownSecs {
          type yang:counter32;
          description
            "tmnxBundleImaGrpSmDownSecs specifies the number of seconds
             that the IMA Group State Machine is not Operational.";
          smiv2:max-access "read-only";
          smiv2:oid "1.3.6.1.4.1.6527.3.1.2.2.4.21.1.11";
          config false;
        }
        leaf tmnxBundleImaGrpSmOperSecs {
          type yang:counter32;
          description
            "tmnxBundleImaGrpSmOperSecs specifies the number of seconds
             that the IMA Group State Machine has been in the Operational
             State.";
          smiv2:max-access "read-only";
          smiv2:oid "1.3.6.1.4.1.6527.3.1.2.2.4.21.1.12";
          config false;
        }
        leaf tmnxBundleImaGrpAvailTxCR {
          type yang:gauge32;
          description
            "tmnxBundleImaGrpAvailTxCR specifies the available transmit
             bandwidth on this IMA group. It only considers members that
             are in the Active State.";
          smiv2:max-access "read-only";
          smiv2:oid "1.3.6.1.4.1.6527.3.1.2.2.4.21.1.13";
          config false;
        }
        leaf tmnxBundleImaGrpAvailRxCR {
          type yang:gauge32;
          description
            "tmnxBundleImaGrpAvailRxCR specifies the available bandwidth
             on this IMA group in the receive direction. It only considers
             members that are in the Active State.";
          smiv2:max-access "read-only";
          smiv2:oid "1.3.6.1.4.1.6527.3.1.2.2.4.21.1.14";
          config false;
        }
        leaf tmnxBundleImaGrpNeFails {
          type yang:counter32;
          description
            "tmnxBundleImaGrpNeFails specifies the number of reported
             IMA Group failures since boot time.";
          smiv2:max-access "read-only";
          smiv2:oid "1.3.6.1.4.1.6527.3.1.2.2.4.21.1.15";
          config false;
        }
        leaf tmnxBundleImaGrpFeFails {
          type yang:counter32;
          description
            "tmnxBundleImaGrpFeFails specifies the number of reported
             IMA Group far-end failures since boot time.";
          smiv2:max-access "read-only";
          smiv2:oid "1.3.6.1.4.1.6527.3.1.2.2.4.21.1.16";
          config false;
        }
        leaf tmnxBundleImaGrpTxIcpCells {
          type yang:counter32;
          description
            "tmnxBundleImaGrpTxIcpCells specifies number of transmitted
             ICP cells for this IMA Group.";
          smiv2:max-access "read-only";
          smiv2:oid "1.3.6.1.4.1.6527.3.1.2.2.4.21.1.17";
          config false;
        }
        leaf tmnxBundleImaGrpRxIcpCells {
          type yang:counter32;
          description
            "tmnxBundleImaGrpRxIcpCells specifies number of received
             ICP cells for this IMA Group.";
          smiv2:max-access "read-only";
          smiv2:oid "1.3.6.1.4.1.6527.3.1.2.2.4.21.1.18";
          config false;
        }
        leaf tmnxBundleImaGrpErrorIcpCells {
          type yang:counter32;
          description
            "tmnxBundleImaGrpErrorIcpCells specifies number of
             ICP cells with HEC or CRC-10 errors.";
          smiv2:max-access "read-only";
          smiv2:oid "1.3.6.1.4.1.6527.3.1.2.2.4.21.1.19";
          config false;
        }
        leaf tmnxBundleImaGrpLostRxIcpCells {
          type yang:counter32;
          description
            "tmnxBundleImaGrpLostRxIcpCells specifies the number of
             missing ICP cells at the expected offset.";
          smiv2:max-access "read-only";
          smiv2:oid "1.3.6.1.4.1.6527.3.1.2.2.4.21.1.20";
          config false;
        }
        leaf tmnxBundleImaGrpTxOamLablVal {
          type int32;
          description
            "tmnxBundleImaGrpTxOamLablVal specifies near-end value
             to be transmitted.";
          smiv2:max-access "read-only";
          smiv2:oid "1.3.6.1.4.1.6527.3.1.2.2.4.21.1.21";
          config false;
        }
        leaf tmnxBundleImaGrpRxOamLablVal {
          type int32;
          description
            "tmnxBundleImaGrpRxOamLablVal specifies far-end value
             received.";
          smiv2:max-access "read-only";
          smiv2:oid "1.3.6.1.4.1.6527.3.1.2.2.4.21.1.22";
          config false;
        }
        leaf tmnxBundleImaGrpAlphaValue {
          type int32;
          description
            "tmnxBundleImaGrpAlphaValue specifies the number of
             consecutive ICP cells that need to be detected
             before moving from the IMA Sync State to the IMA Hunt
             State.";
          smiv2:defval "2";
          smiv2:max-access "read-write";
          smiv2:oid "1.3.6.1.4.1.6527.3.1.2.2.4.21.1.23";
          config true;
        }
        leaf tmnxBundleImaGrpBetaValue {
          type int32;
          description
            "tmnxBundleImaGrpBetaValue specifies the number of
             consecutive errored ICP cells that need to be detected
             before moving from the IMA Sync State to the IMA Hunt
             State";
          smiv2:defval "2";
          smiv2:max-access "read-write";
          smiv2:oid "1.3.6.1.4.1.6527.3.1.2.2.4.21.1.24";
          config true;
        }
        leaf tmnxBundleImaGrpGammaValue {
          type int32;
          description
            "tmnxBundleImaGrpGammaValue specifies the number of
             consecutive valid ICP cells that need to be detected
             before moving from the IMA pre-Sync State to the
             IMA Hunt State.";
          smiv2:defval "1";
          smiv2:max-access "read-write";
          smiv2:oid "1.3.6.1.4.1.6527.3.1.2.2.4.21.1.25";
          config true;
        }
        leaf tmnxBundleImaGrpNeClockMode {
          type timetra-port:TmnxImaGrpClockModes;
          description
            "tmnxBundleImaGrpNeClockMode specifies near-end transmit
             clock mode.";
          smiv2:defval "ctc";
          smiv2:max-access "read-write";
          smiv2:oid "1.3.6.1.4.1.6527.3.1.2.2.4.21.1.26";
          config true;
        }
        leaf tmnxBundleImaGrpFeClockMode {
          type timetra-port:TmnxImaGrpClockModes;
          description
            "tmnxBundleImaGrpFeClockMode specifies far-end transmit
             clock mode.";
          smiv2:defval "ctc";
          smiv2:max-access "read-write";
          smiv2:oid "1.3.6.1.4.1.6527.3.1.2.2.4.21.1.27";
          config true;
        }
        leaf tmnxBundleImaGrpVersion {
          type timetra-port:TmnxImaGrpVersion;
          description
            "tmnxBundleImaGrpVersion specifies the IMA Version for
             this group.";
          smiv2:defval "oneDotOne";
          smiv2:max-access "read-write";
          smiv2:oid "1.3.6.1.4.1.6527.3.1.2.2.4.21.1.28";
          config true;
        }
        leaf tmnxBundleImaGrpMaxConfBw {
          type uint32 {
            range "1..8";
          }
          description
            "tmnxBundleImaGrpMaxConfBw specifies the number of links
             that is used to determine the maximum configurable
             bandwidth that is allowed to be used for this IMA group.";
          smiv2:defval "8";
          smiv2:max-access "read-write";
          smiv2:oid "1.3.6.1.4.1.6527.3.1.2.2.4.21.1.29";
          config true;
        }
        leaf tmnxBundleImaGrpTestState {
          type timetra-port:TmnxImaTestState;
          description
            "tmnxBundleImaGrpTestState specifies the current state of
             the test pattern procedure. A value of 'disabled' specifies
             that the group is currently not running. A value of
             'operating' enables the test pattern procedure. The test
             pattern procedure continues until it is 'disabled'.";
          smiv2:defval "disabled";
          smiv2:max-access "read-write";
          smiv2:oid "1.3.6.1.4.1.6527.3.1.2.2.4.21.1.30";
          config true;
        }
        leaf tmnxBundleImaGrpTestMember {
          type timetra-tc:TmnxPortID;
          description
            "tmnxBundleImaGrpTestMember specifies a member link to
             be used for the test pattern procedure. A value of zero
             indicates that no member link has been selected.
             
             When tmnxBundleImaGrpTestState does not have the value
             'disabled', an attempt to set this object will be
             rejected with an inconsistentValue error.";
          smiv2:defval "0";
          smiv2:max-access "read-write";
          smiv2:oid "1.3.6.1.4.1.6527.3.1.2.2.4.21.1.31";
          config true;
        }
        leaf tmnxBundleImaGrpTestPattern {
          type int32 {
            range "0..255";
          }
          description
            "tmnxBundleImaGrpTestPattern specifies the Transmit Test
             Pattern in an IMA group loopback operation. This value
             may only be changed when tmnxBundleImaGrpTestState is
             'disabled'.";
          smiv2:defval "0";
          smiv2:max-access "read-write";
          smiv2:oid "1.3.6.1.4.1.6527.3.1.2.2.4.21.1.32";
          config true;
        }
        leaf tmnxBundleImaGrpDiffDelayMaxObs {
          type uint32;
          units "milliseconds";
          description
            "tmnxBundleImaGrpDiffDelayMaxObs indicates the latest
             maximum differential delay observed between links
             having the least and most link propagation delay
             among the received links configured in this IMA group.";
          smiv2:max-access "read-only";
          smiv2:oid "1.3.6.1.4.1.6527.3.1.2.2.4.21.1.33";
          config false;
        }
        leaf tmnxBundleImaGrpLeastDelayLink {
          type uint32;
          units "milliseconds";
          description
            "tmnxBundleImaGrpLeastDelayLink indicates a member link
             which has the smallest link propagation delay. If this
             delay has yet to be determined or no member link has
             been configured, a value of zero is returned.";
          smiv2:max-access "read-only";
          smiv2:oid "1.3.6.1.4.1.6527.3.1.2.2.4.21.1.34";
          config false;
        }
        config true;
      }
      config true;
    }
    container tmnxBundleMemberImaTable {
      description
        "The tmnxBundleMemberImaTable has an entry for an
         IMA link associated with an IMA Group.";
      smiv2:oid "1.3.6.1.4.1.6527.3.1.2.2.4.22";
      list tmnxBundleMemberImaEntry {
        key "tmnxBundleBundleID tmnxPortPortID";
        description
          "Each row entry represents an IMA link associated with
           an IMA Group.";
        smiv2:oid "1.3.6.1.4.1.6527.3.1.2.2.4.22.1";
        leaf tmnxBundleBundleID {
          type leafref {
            path "/timetra-port:TIMETRA-PORT-MIB/timetra-port:tmnxBundleTable/timetra-port:tmnxBundleEntry/timetra-port:tmnxBundleBundleID";
          }
        }
        leaf tmnxPortPortID {
          type leafref {
            path "/timetra-port:TIMETRA-PORT-MIB/timetra-port:tmnxPortTable/timetra-port:tmnxPortEntry/timetra-port:tmnxPortPortID";
          }
        }
        leaf tmnxBundleMemberImaNeTxState {
          type timetra-port:TmnxImaLnkState;
          description
            "tmnxBundleMemberImaNeTxState indicates the state of near-end
             transmit IMA link.";
          smiv2:max-access "read-only";
          smiv2:oid "1.3.6.1.4.1.6527.3.1.2.2.4.22.1.1";
        }
        leaf tmnxBundleMemberImaNeRxState {
          type timetra-port:TmnxImaLnkState;
          description
            "tmnxBundleMemberImaNeRxState indicates the state of near-end
             receive IMA link.";
          smiv2:max-access "read-only";
          smiv2:oid "1.3.6.1.4.1.6527.3.1.2.2.4.22.1.2";
        }
        leaf tmnxBundleMemberImaFeTxState {
          type timetra-port:TmnxImaLnkState;
          description
            "tmnxBundleMemberImaFeTxState indicates the state of far-end
             transmit IMA link.";
          smiv2:max-access "read-only";
          smiv2:oid "1.3.6.1.4.1.6527.3.1.2.2.4.22.1.3";
        }
        leaf tmnxBundleMemberImaFeRxState {
          type timetra-port:TmnxImaLnkState;
          description
            "tmnxBundleMemberImaFeRxState indicates the state of far-end
             receive IMA link.";
          smiv2:max-access "read-only";
          smiv2:oid "1.3.6.1.4.1.6527.3.1.2.2.4.22.1.4";
        }
        leaf tmnxBundleMemberImaNeRxFailState {
          type timetra-port:TmnxImaLnkFailState;
          description
            "tmnxBundleMemberImaNeRxFailState indicates the IMA link failure
             reason for the near-end.";
          smiv2:max-access "read-only";
          smiv2:oid "1.3.6.1.4.1.6527.3.1.2.2.4.22.1.5";
        }
        leaf tmnxBundleMemberImaFeRxFailState {
          type timetra-port:TmnxImaLnkFailState;
          description
            "tmnxBundleMemberImaFeRxFailState indicates the IMA link failure
             reason for the far-end.";
          smiv2:max-access "read-only";
          smiv2:oid "1.3.6.1.4.1.6527.3.1.2.2.4.22.1.6";
        }
        leaf tmnxBundleMemberImaTxLid {
          type int32;
          description
            "tmnxBundleMemberImaTxLid indicates the Link Identifier
             assigned to the transmit IMA link.";
          smiv2:max-access "read-only";
          smiv2:oid "1.3.6.1.4.1.6527.3.1.2.2.4.22.1.7";
        }
        leaf tmnxBundleMemberImaRxLid {
          type int32;
          description
            "tmnxBundleMemberImaRxLid indicates the Link Identifier
             used on the receive IMA link.";
          smiv2:max-access "read-only";
          smiv2:oid "1.3.6.1.4.1.6527.3.1.2.2.4.22.1.8";
        }
        leaf tmnxBundleMemberImaViolations {
          type yang:counter32;
          description
            "tmnxBundleMemberImaViolations indicates the number of
             ICP violations including errored, invalid or missing ICP
             cells.";
          smiv2:max-access "read-only";
          smiv2:oid "1.3.6.1.4.1.6527.3.1.2.2.4.22.1.9";
        }
        leaf tmnxBundleMemberImaNeSevErrSecs {
          type yang:counter32;
          description
            "tmnxBundleMemberImaNeSevErrSecs indicates the number
             of one second intervals in which thirty percent or
             more of the near-end ICP cells are in violation, or
             link defects have occurred.";
          smiv2:max-access "read-only";
          smiv2:oid "1.3.6.1.4.1.6527.3.1.2.2.4.22.1.10";
        }
        leaf tmnxBundleMemberImaFeSevErrSecs {
          type yang:counter32;
          description
            "tmnxBundleMemberImaFeSevErrSecs indicates the number
             of one second intervals in which the far-end contains
             IMA-RDI defects.";
          smiv2:max-access "read-only";
          smiv2:oid "1.3.6.1.4.1.6527.3.1.2.2.4.22.1.11";
        }
        leaf tmnxBundleMemberImaNeUnavailSecs {
          type yang:counter32;
          description
            "tmnxBundleMemberImaNeUnavailSecs indicates the number
             of unavailable seconds at the near-end.";
          smiv2:max-access "read-only";
          smiv2:oid "1.3.6.1.4.1.6527.3.1.2.2.4.22.1.12";
        }
        leaf tmnxBundleMemberImaFeUnavailSecs {
          type yang:counter32;
          description
            "tmnxBundleMemberImaFeUnavailSecs indicates the number
             of unavailable seconds at the near-end.";
          smiv2:max-access "read-only";
          smiv2:oid "1.3.6.1.4.1.6527.3.1.2.2.4.22.1.13";
        }
        leaf tmnxBundleMemberImaNeTxUnuseSecs {
          type yang:counter32;
          description
            "tmnxBundleMemberImaNeTxUnuseSecs indicates the number
             of unavailable seconds at the near-end transmit link
             state machine.";
          smiv2:max-access "read-only";
          smiv2:oid "1.3.6.1.4.1.6527.3.1.2.2.4.22.1.14";
        }
        leaf tmnxBundleMemberImaNeRxUnuseSecs {
          type yang:counter32;
          description
            "tmnxBundleMemberImaNeRxUnuseSecs indicates the number
             of unavailable seconds at the near-end receive link
             state machine.";
          smiv2:max-access "read-only";
          smiv2:oid "1.3.6.1.4.1.6527.3.1.2.2.4.22.1.15";
        }
        leaf tmnxBundleMemberImaFeTxUnuseSecs {
          type yang:counter32;
          description
            "tmnxBundleMemberImaFeTxUnuseSecs indicates the number
             of unavailable seconds at the far-end transmit link
             state machine.";
          smiv2:max-access "read-only";
          smiv2:oid "1.3.6.1.4.1.6527.3.1.2.2.4.22.1.16";
        }
        leaf tmnxBundleMemberImaFeRxUnuseSecs {
          type yang:counter32;
          description
            "tmnxBundleMemberImaFeRxUnuseSecs indicates the number
             of unavailable seconds at the far-end receive link
             state machine.";
          smiv2:max-access "read-only";
          smiv2:oid "1.3.6.1.4.1.6527.3.1.2.2.4.22.1.17";
        }
        leaf tmnxBundleMemberImaNeTxNumFails {
          type yang:counter32;
          description
            "tmnxBundleMemberImaNeTxNumFails indicates the number
             of times that a near-end transmit alarm is set on the
             IMA link.";
          smiv2:max-access "read-only";
          smiv2:oid "1.3.6.1.4.1.6527.3.1.2.2.4.22.1.18";
        }
        leaf tmnxBundleMemberImaNeRxNumFails {
          type yang:counter32;
          description
            "tmnxBundleMemberImaNeRxNumFails indicates the number
             of times that a near-end receive alarm is set on the
             IMA link.";
          smiv2:max-access "read-only";
          smiv2:oid "1.3.6.1.4.1.6527.3.1.2.2.4.22.1.19";
        }
        leaf tmnxBundleMemberImaFeTxNumFails {
          type yang:counter32;
          description
            "tmnxBundleMemberImaFeTxNumFails indicates the number
             of times that a far-end transmit alarm is set on the
             IMA link.";
          smiv2:max-access "read-only";
          smiv2:oid "1.3.6.1.4.1.6527.3.1.2.2.4.22.1.20";
        }
        leaf tmnxBundleMemberImaFeRxNumFails {
          type yang:counter32;
          description
            "tmnxBundleMemberImaFeRxNumFails indicates the number
             of times that a far-end receive alarm is set on the
             IMA link.";
          smiv2:max-access "read-only";
          smiv2:oid "1.3.6.1.4.1.6527.3.1.2.2.4.22.1.21";
        }
        leaf tmnxBundleMemberImaTxIcpCells {
          type yang:counter32;
          description
            "tmnxBundleMemberImaTxIcpCells indicates the number
             of ICP cells that have been transmitted on the IMA
             link.";
          smiv2:max-access "read-only";
          smiv2:oid "1.3.6.1.4.1.6527.3.1.2.2.4.22.1.22";
        }
        leaf tmnxBundleMemberImaRxIcpCells {
          type yang:counter32;
          description
            "tmnxBundleMemberImaRxIcpCells indicates the number
             of ICP cells that have been received on the IMA
             link.";
          smiv2:max-access "read-only";
          smiv2:oid "1.3.6.1.4.1.6527.3.1.2.2.4.22.1.23";
        }
        leaf tmnxBundleMemberImaErrorIcpCells {
          type yang:counter32;
          description
            "tmnxBundleMemberImaErrorIcpCells indicates the number
             of ICP cells with HEC or CRC-10 errors.";
          smiv2:max-access "read-only";
          smiv2:oid "1.3.6.1.4.1.6527.3.1.2.2.4.22.1.24";
        }
        leaf tmnxBundleMemberImaLstRxIcpCells {
          type yang:counter32;
          description
            "tmnxBundleMemberImaLstRxIcpCells indicates the number
             of lost ICP cells at the expected offset.";
          smiv2:max-access "read-only";
          smiv2:oid "1.3.6.1.4.1.6527.3.1.2.2.4.22.1.25";
        }
        leaf tmnxBundleMemberImaOifAnomalies {
          type yang:counter32;
          description
            "tmnxBundleMemberImaOifAnomalies indicates the number
             of OIF anomalies at the near-end.";
          smiv2:max-access "read-only";
          smiv2:oid "1.3.6.1.4.1.6527.3.1.2.2.4.22.1.26";
        }
        leaf tmnxBundleMemberImaRxTestState {
          type timetra-port:TmnxImaTestState;
          description
            "tmnxBundleMemberImaRxTestState indicates the current
             state of the test pattern on this link.";
          smiv2:max-access "read-only";
          smiv2:oid "1.3.6.1.4.1.6527.3.1.2.2.4.22.1.27";
        }
        leaf tmnxBundleMemberImaRxTestPattern {
          type int32 {
            range "0..255";
          }
          description
            "tmnxBundleMemberImaRxTestPattern indicates the received
             test pattern value on this link.";
          smiv2:max-access "read-only";
          smiv2:oid "1.3.6.1.4.1.6527.3.1.2.2.4.22.1.28";
        }
        leaf tmnxBundleMemberImaRelDelay {
          type uint32;
          units "milliseconds";
          description
            "tmnxBundleMemberImaRelDelay indicates the latest measured
             delay on this member link relative to the member link with
             the least delay within the same IMA group";
          smiv2:max-access "read-only";
          smiv2:oid "1.3.6.1.4.1.6527.3.1.2.2.4.22.1.29";
        }
      }
      config false;
    }
    container tmnxDS1PortTable {
      description
        "The tmnxDS1PortTable has an entry for a DS1 physical port.";
      smiv2:oid "1.3.6.1.4.1.6527.3.1.2.2.4.23";
      list tmnxDS1PortEntry {
        key "tmnxChassisIndex tmnxPortPortID";
        description
          "Each row entry represents a physical DS1 port on a
           IOM card in a chassis in the system.  Entries cannot be created
           and deleted via SNMP SET operations.  Entries in this table will
           be created automatically when the tmnxMDAAssignedType object is
           set to the DS1 MDA type The tmnxDS1PortEntry contains attributes
           that are unique to the 'ds1e1' TmnxPortType. The tmnxPortPortID
           contains the slot, mda and port numbers encoded into it.
           
           For each tmnxDS1PortEntry, there will be a corresponding entry
           in the tmnxPortTable and the ifTable.";
        smiv2:oid "1.3.6.1.4.1.6527.3.1.2.2.4.23.1";
        leaf tmnxChassisIndex {
          type leafref {
            path "/timetra-chassis:TIMETRA-CHASSIS-MIB/timetra-chassis:tmnxChassisTable/timetra-chassis:tmnxChassisEntry/timetra-chassis:tmnxChassisIndex";
          }
          config true;
        }
        leaf tmnxPortPortID {
          type leafref {
            path "/timetra-port:TIMETRA-PORT-MIB/timetra-port:tmnxPortTable/timetra-port:tmnxPortEntry/timetra-port:tmnxPortPortID";
          }
          config true;
        }
        leaf tmnxDS1PortBuildout {
          type enumeration {
            enum "short" {
              value 1;
            }
            enum "long" {
              value 2;
            }
          }
          description
            "tmnxDS1PortBuildout configures the cable buildout length.  A ds1 port
             has two settings for the DS1 cable buildout: a 'short' setting, for
             cable lengths of less than or equal to 655 feet, and a 'long' setting
             for cable lengths of greater than 655 feet.
             This object applies to copper-cable-based DS1 ports only.";
          smiv2:defval "short";
          smiv2:max-access "read-write";
          smiv2:oid "1.3.6.1.4.1.6527.3.1.2.2.4.23.1.1";
          config true;
        }
        leaf tmnxDS1PortLastChangeTime {
          type yang:timestamp;
          description
            "The tmnxDS1PortLastChangeTime variable contains the sysUpTime
             value of the most recently modified writable variable in the
             tmnxDS1PortEntry row for this port.";
          smiv2:max-access "read-only";
          smiv2:oid "1.3.6.1.4.1.6527.3.1.2.2.4.23.1.2";
          config false;
        }
        leaf tmnxDS1PortType {
          type enumeration {
            enum "ds1" {
              value 1;
            }
            enum "e1" {
              value 2;
            }
            enum "j1" {
              value 3;
            }
          }
          description
            "tmnxDS1PortType configures the type of the physical port to 'ds1',
             'e1' or 'j1'.";
          smiv2:defval "ds1";
          smiv2:max-access "read-write";
          smiv2:oid "1.3.6.1.4.1.6527.3.1.2.2.4.23.1.3";
          config true;
        }
        leaf tmnxDS1PortLineLength {
          type enumeration {
            enum "lengthNotApplicable" {
              value 1;
            }
            enum "length0To133" {
              value 2;
            }
            enum "length134To266" {
              value 3;
            }
            enum "length267To399" {
              value 4;
            }
            enum "length400To533" {
              value 5;
            }
            enum "length534To655" {
              value 6;
            }
          }
          description
            "tmnxDS1PortLineLength configuration only applies to a ds1 port
             configured with a 'short' buildout.  tmnxDS1PortLineLength configures
             the length of the line (in feet).  For line lengths longer than 655
             feet configure the ds1 port buildout as 'long'.
             For 'long' buildout the following values are valid:
                 lengthNotApplicable - Not applicable
             For 'short' buildout the following values are valid:
                 length0To133        - For line length from 0 to 133 feet
                 length134To266      - For line length from 134 to 266 feet
                 length267To399      - For line length from 267 to 399 feet
                 length400To533      - For line length from 400 to 533 feet
                 length534To655      - For line length from 534 to 655 feet
             The default for 'long' buildout is 'lengthNotApplicable' while the
             default for 'short' buildout is 'length0To133'.";
          smiv2:max-access "read-write";
          smiv2:oid "1.3.6.1.4.1.6527.3.1.2.2.4.23.1.4";
          config true;
        }
        leaf tmnxDS1PortLbo {
          type enumeration {
            enum "lboNotApplicable" {
              value 1;
            }
            enum "lbo0dB" {
              value 2;
            }
            enum "lboNeg7p5dB" {
              value 3;
            }
            enum "lboNeg15p0dB" {
              value 4;
            }
            enum "lboNeg22p5dB" {
              value 5;
            }
          }
          description
            "tmnxDS1PortLbo configuration only applies to a ds1 port
             configured with a 'long' buildout.  tmnxDS1PortLbo configures the
             number of decibels(dB) the transmission signal decreases over the line.
             For 'short' buildout the following values are valid:
                 lboNotApplicable - Not applicable
             For 'long' buildout the following values are valid:
                 lbo0dB           - For 0 dB
                 lboNeg7p5dB      - For -7.5 dB
                 lboNeg15p0dB     - For -15.0 dB
                 lboNeg22p5dB     - For -22.5 dB
             The default for 'short' build out is 'lboNotApplicable' while the
             default for 'long' buildout is 'lbo0dB'";
          smiv2:max-access "read-write";
          smiv2:oid "1.3.6.1.4.1.6527.3.1.2.2.4.23.1.5";
          config true;
        }
        leaf tmnxDS1PortDbGain {
          type int32;
          units "db";
          description
            "tmnxDS1PortDbGain only applies to a ds1 port configured with a
             'long' buildout.  tmnxDS1PortDbGain shows the number of decibels
             the received signal is increased to compensate for loss.";
          smiv2:max-access "read-only";
          smiv2:oid "1.3.6.1.4.1.6527.3.1.2.2.4.23.1.6";
          config false;
        }
        config true;
      }
      config true;
    }
    container tmnxPortSchedOverrideTable {
      description
        "The tmnxPortSchedOverrideTable has an entry for each port
         scheduler override configured on this system.";
      smiv2:oid "1.3.6.1.4.1.6527.3.1.2.2.4.24";
      list tmnxPortSchedOverrideEntry {
        key "tmnxChassisIndex tmnxPortPortID";
        description
          "Each row represents a particular port-scheduler override. Entries
           are created and deleted by the user.";
        smiv2:oid "1.3.6.1.4.1.6527.3.1.2.2.4.24.1";
        leaf tmnxChassisIndex {
          type leafref {
            path "/timetra-chassis:TIMETRA-CHASSIS-MIB/timetra-chassis:tmnxChassisTable/timetra-chassis:tmnxChassisEntry/timetra-chassis:tmnxChassisIndex";
          }
          config true;
        }
        leaf tmnxPortPortID {
          type leafref {
            path "/timetra-port:TIMETRA-PORT-MIB/timetra-port:tmnxPortTable/timetra-port:tmnxPortEntry/timetra-port:tmnxPortPortID";
          }
          config true;
        }
        leaf tmnxPortSchedOverrideRowStatus {
          type snmpv2-tc:RowStatus;
          description
            "The value of tmnxPortSchedOverrideRowStatus is used for the
             creation and deletion of port-scheduler overrides. When
             tmnxPortEgrPortSchedPlcy of the tmnxPortEntry indexed by the
             same indices of this table is an empty string, creation
             will fail.";
          smiv2:max-access "read-write";
          smiv2:oid "1.3.6.1.4.1.6527.3.1.2.2.4.24.1.1";
          config false;
        }
        leaf tmnxPortSchedOverrideSchedName {
          type snmpv2-tc:DisplayString;
          description
            "The value of tmnxPortSchedOverrideSchedName indicates the name
             of the port scheduler policy that this row entry overrides.";
          smiv2:max-access "read-only";
          smiv2:oid "1.3.6.1.4.1.6527.3.1.2.2.4.24.1.2";
          config false;
        }
        leaf tmnxPortSchedOverrideLastChanged {
          type yang:timestamp;
          description
            "The value of tmnxPortSchedOverrideLastChanged indicates the value
             of sysUpTime at the time of the most recent management change to
             this row.";
          smiv2:max-access "read-only";
          smiv2:oid "1.3.6.1.4.1.6527.3.1.2.2.4.24.1.3";
          config false;
        }
        leaf tmnxPortSchedOverrideMaxRate {
          type timetra-tc:TPortSchedulerPIRRate;
          units "kbps";
          description
            "The value of tmnxPortSchedOverrideMaxRate specifies the explicit
             maximum frame based bandwidth limit. This object overrides
             TIMETRA-QOS-MIB::tPortSchedulerPlcyMaxRate.";
          smiv2:defval "-1";
          smiv2:max-access "read-write";
          smiv2:oid "1.3.6.1.4.1.6527.3.1.2.2.4.24.1.4";
          config true;
        }
        leaf tmnxPortSchedOverrideLvl1PIR {
          type timetra-tc:TPortSchedulerPIRRate;
          units "kbps";
          description
            "The value of tmnxPortSchedOverrideLvl1PIR specifies the total
             bandwidth limit, PIR, for priority level 1. This object
             overrides TIMETRA-QOS-MIB::tPortSchedulerPlcyLvl1PIR.";
          smiv2:defval "-1";
          smiv2:max-access "read-write";
          smiv2:oid "1.3.6.1.4.1.6527.3.1.2.2.4.24.1.5";
          config true;
        }
        leaf tmnxPortSchedOverrideLvl1CIR {
          type timetra-tc:TPortSchedulerCIR;
          units "kbps";
          description
            "The value of tmnxPortSchedOverrideLvl1CIR specifies the within-cir
             bandwidth limit for priority level 1. This object overrides
             TIMETRA-QOS-MIB::tPortSchedulerPlcyLvl1CIR.";
          smiv2:defval "-1";
          smiv2:max-access "read-write";
          smiv2:oid "1.3.6.1.4.1.6527.3.1.2.2.4.24.1.6";
          config true;
        }
        leaf tmnxPortSchedOverrideLvl2PIR {
          type timetra-tc:TPortSchedulerPIRRate;
          units "kbps";
          description
            "The value of tmnxPortSchedOverrideLvl2PIR specifies the total
             bandwidth limit, PIR, for priority level 2. This object
             overrides TIMETRA-QOS-MIB::tPortSchedulerPlcyLvl2PIR.";
          smiv2:defval "-1";
          smiv2:max-access "read-write";
          smiv2:oid "1.3.6.1.4.1.6527.3.1.2.2.4.24.1.7";
          config true;
        }
        leaf tmnxPortSchedOverrideLvl2CIR {
          type timetra-tc:TPortSchedulerCIR;
          units "kbps";
          description
            "The value of tmnxPortSchedOverrideLvl2CIR specifies the within-cir
             bandwidth limit for priority level 2. This object overrides
             TIMETRA-QOS-MIB::tPortSchedulerPlcyLvl2CIR.";
          smiv2:defval "-1";
          smiv2:max-access "read-write";
          smiv2:oid "1.3.6.1.4.1.6527.3.1.2.2.4.24.1.8";
          config true;
        }
        leaf tmnxPortSchedOverrideLvl3PIR {
          type timetra-tc:TPortSchedulerPIRRate;
          units "kbps";
          description
            "The value of tmnxPortSchedOverrideLvl3PIR specifies the total
             bandwidth limit, PIR, for priority level 3. This object
             overrides TIMETRA-QOS-MIB::tPortSchedulerPlcyLvl3PIR.";
          smiv2:defval "-1";
          smiv2:max-access "read-write";
          smiv2:oid "1.3.6.1.4.1.6527.3.1.2.2.4.24.1.9";
          config true;
        }
        leaf tmnxPortSchedOverrideLvl3CIR {
          type timetra-tc:TPortSchedulerCIR;
          units "kbps";
          description
            "The value of tmnxPortSchedOverrideLvl3CIR specifies the within-cir
             bandwidth limit for priority level 3. This object overrides
             TIMETRA-QOS-MIB::tPortSchedulerPlcyLvl3CIR.";
          smiv2:defval "-1";
          smiv2:max-access "read-write";
          smiv2:oid "1.3.6.1.4.1.6527.3.1.2.2.4.24.1.10";
          config true;
        }
        leaf tmnxPortSchedOverrideLvl4PIR {
          type timetra-tc:TPortSchedulerPIRRate;
          units "kbps";
          description
            "The value of tmnxPortSchedOverrideLvl4PIR specifies the total
             bandwidth limit, PIR, for priority level 4. This object
             overrides TIMETRA-QOS-MIB::tPortSchedulerPlcyLvl4PIR.";
          smiv2:defval "-1";
          smiv2:max-access "read-write";
          smiv2:oid "1.3.6.1.4.1.6527.3.1.2.2.4.24.1.11";
          config true;
        }
        leaf tmnxPortSchedOverrideLvl4CIR {
          type timetra-tc:TPortSchedulerCIR;
          units "kbps";
          description
            "The value of tmnxPortSchedOverrideLvl4CIR specifies the within-cir
             bandwidth limit for priority level 4. This object overrides
             TIMETRA-QOS-MIB::tPortSchedulerPlcyLvl4CIR.";
          smiv2:defval "-1";
          smiv2:max-access "read-write";
          smiv2:oid "1.3.6.1.4.1.6527.3.1.2.2.4.24.1.12";
          config true;
        }
        leaf tmnxPortSchedOverrideLvl5PIR {
          type timetra-tc:TPortSchedulerPIRRate;
          units "kbps";
          description
            "The value of tmnxPortSchedOverrideLvl5PIR specifies the total
             bandwidth limit, PIR, for priority level 5. This object
             overrides TIMETRA-QOS-MIB::tPortSchedulerPlcyLvl5PIR.";
          smiv2:defval "-1";
          smiv2:max-access "read-write";
          smiv2:oid "1.3.6.1.4.1.6527.3.1.2.2.4.24.1.13";
          config true;
        }
        leaf tmnxPortSchedOverrideLvl5CIR {
          type timetra-tc:TPortSchedulerCIR;
          units "kbps";
          description
            "The value of tmnxPortSchedOverrideLvl5CIR specifies the within-cir
             bandwidth limit for priority level 5. This object overrides
             TIMETRA-QOS-MIB::tPortSchedulerPlcyLvl5CIR.";
          smiv2:defval "-1";
          smiv2:max-access "read-write";
          smiv2:oid "1.3.6.1.4.1.6527.3.1.2.2.4.24.1.14";
          config true;
        }
        leaf tmnxPortSchedOverrideLvl6PIR {
          type timetra-tc:TPortSchedulerPIRRate;
          units "kbps";
          description
            "The value of tmnxPortSchedOverrideLvl6PIR specifies the total
             bandwidth limit, PIR, for priority level 6. This object
             overrides TIMETRA-QOS-MIB::tPortSchedulerPlcyLvl6PIR.";
          smiv2:defval "-1";
          smiv2:max-access "read-write";
          smiv2:oid "1.3.6.1.4.1.6527.3.1.2.2.4.24.1.15";
          config true;
        }
        leaf tmnxPortSchedOverrideLvl6CIR {
          type timetra-tc:TPortSchedulerCIR;
          units "kbps";
          description
            "The value of tmnxPortSchedOverrideLvl6CIR specifies the within-cir
             bandwidth limit for priority level 6. This object overrides
             TIMETRA-QOS-MIB::tPortSchedulerPlcyLvl6CIR.";
          smiv2:defval "-1";
          smiv2:max-access "read-write";
          smiv2:oid "1.3.6.1.4.1.6527.3.1.2.2.4.24.1.16";
          config true;
        }
        leaf tmnxPortSchedOverrideLvl7PIR {
          type timetra-tc:TPortSchedulerPIRRate;
          units "kbps";
          description
            "The value of tmnxPortSchedOverrideLvl7PIR specifies the total
             bandwidth limit, PIR, for priority level 7. This object
             overrides TIMETRA-QOS-MIB::tPortSchedulerPlcyLvl7PIR.";
          smiv2:defval "-1";
          smiv2:max-access "read-write";
          smiv2:oid "1.3.6.1.4.1.6527.3.1.2.2.4.24.1.17";
          config true;
        }
        leaf tmnxPortSchedOverrideLvl7CIR {
          type timetra-tc:TPortSchedulerCIR;
          units "kbps";
          description
            "The value of tmnxPortSchedOverrideLvl7CIR specifies the within-cir
             bandwidth limit for priority level 7. This object overrides
             TIMETRA-QOS-MIB::tPortSchedulerPlcyLvl7CIR.";
          smiv2:defval "-1";
          smiv2:max-access "read-write";
          smiv2:oid "1.3.6.1.4.1.6527.3.1.2.2.4.24.1.18";
          config true;
        }
        leaf tmnxPortSchedOverrideLvl8PIR {
          type timetra-tc:TPortSchedulerPIRRate;
          units "kbps";
          description
            "The value of tmnxPortSchedOverrideLvl8PIR specifies the total
             bandwidth limit, PIR, for priority level 8. This object
             overrides TIMETRA-QOS-MIB::tPortSchedulerPlcyLvl8PIR.";
          smiv2:defval "-1";
          smiv2:max-access "read-write";
          smiv2:oid "1.3.6.1.4.1.6527.3.1.2.2.4.24.1.19";
          config true;
        }
        leaf tmnxPortSchedOverrideLvl8CIR {
          type timetra-tc:TPortSchedulerCIR;
          units "kbps";
          description
            "The value of tmnxPortSchedOverrideLvl8CIR specifies the within-cir
             bandwidth limit for priority level 8. This object overrides
             TIMETRA-QOS-MIB::tPortSchedulerPlcyLvl8CIR.";
          smiv2:defval "-1";
          smiv2:max-access "read-write";
          smiv2:oid "1.3.6.1.4.1.6527.3.1.2.2.4.24.1.20";
          config true;
        }
        leaf tmnxPortSchedOverrideFlags {
          type bits {
            bit maxRate {
              position 0;
            }
            bit lvl1PIR {
              position 1;
            }
            bit lvl1CIR {
              position 2;
            }
            bit lvl2PIR {
              position 3;
            }
            bit lvl2CIR {
              position 4;
            }
            bit lvl3PIR {
              position 5;
            }
            bit lvl3CIR {
              position 6;
            }
            bit lvl4PIR {
              position 7;
            }
            bit lvl4CIR {
              position 8;
            }
            bit lvl5PIR {
              position 9;
            }
            bit lvl5CIR {
              position 10;
            }
            bit lvl6PIR {
              position 11;
            }
            bit lvl6CIR {
              position 12;
            }
            bit lvl7PIR {
              position 13;
            }
            bit lvl7CIR {
              position 14;
            }
            bit lvl8PIR {
              position 15;
            }
            bit lvl8CIR {
              position 16;
            }
          }
          description
            "The value of tmnxPortSchedOverrideFlags specifies the set of
             attributes whose values have been overridden via management
             on this port scheduler. Clearing a given flag will return the
             corresponding overridden attribute to the value defined in
             the port's port-scheduler policy.";
          smiv2:max-access "read-write";
          smiv2:oid "1.3.6.1.4.1.6527.3.1.2.2.4.24.1.21";
          config true;
        }
        config true;
      }
      config true;
    }
    container tmnxBPGrpAssocTable {
      description
        "The tmnxBPGrpAssocTable has an entry for each Bundle Protection Group
         created on the system.";
      smiv2:oid "1.3.6.1.4.1.6527.3.1.2.2.4.25";
      list tmnxBPGrpAssocEntry {
        key "tmnxChassisIndex tmnxBundleBundleID";
        description
          "Each row displays the relationship between a Bundle Protection
           group and its working and protection bundle.";
        smiv2:oid "1.3.6.1.4.1.6527.3.1.2.2.4.25.1";
        leaf tmnxChassisIndex {
          type leafref {
            path "/timetra-chassis:TIMETRA-CHASSIS-MIB/timetra-chassis:tmnxChassisTable/timetra-chassis:tmnxChassisEntry/timetra-chassis:tmnxChassisIndex";
          }
        }
        leaf tmnxBundleBundleID {
          type leafref {
            path "/timetra-port:TIMETRA-PORT-MIB/timetra-port:tmnxBundleTable/timetra-port:tmnxBundleEntry/timetra-port:tmnxBundleBundleID";
          }
        }
        leaf tmnxBPGrpAssocWorkingBundleID {
          type timetra-port:TmnxBundleID;
          description
            "tmnxBPGrpAssocWorkingBundleID identifies the working bundle. A value
             of zero is given if no working bundle is associated with the given
             tmnxBundleBundleID.";
          smiv2:max-access "read-only";
          smiv2:oid "1.3.6.1.4.1.6527.3.1.2.2.4.25.1.1";
        }
        leaf tmnxBPGrpAssocProtectBundleID {
          type timetra-port:TmnxBundleID;
          description
            "tmnxBPGrpAssocProtectBundleID identifies the protection bundle. A value
             of zero is given if no protection bundle is associated with the given
             tmnxBundleBundleID.";
          smiv2:max-access "read-only";
          smiv2:oid "1.3.6.1.4.1.6527.3.1.2.2.4.25.1.2";
        }
        leaf tmnxBPGrpAssocActiveBundleID {
          type timetra-port:TmnxBundleID;
          description
            "tmnxBPGrpAssocActiveBundleID identifies the bundle that is considered
             the active bundle. This bundle contains the members that are part of
             the active aps port. A value of zero is given if no bundle is
             considered active.";
          smiv2:max-access "read-only";
          smiv2:oid "1.3.6.1.4.1.6527.3.1.2.2.4.25.1.3";
        }
      }
      config false;
    }
    container tmnxBundleMlpppTable {
      description
        "The tmnxBundleMlpppTable contains MLPPP specific data.";
      smiv2:oid "1.3.6.1.4.1.6527.3.1.2.2.4.26";
      list tmnxBundleMlpppEntry {
        key "tmnxChassisIndex tmnxBundleBundleID";
        description
          "Each row entry contains data on an MLPPP Bundle.";
        smiv2:oid "1.3.6.1.4.1.6527.3.1.2.2.4.26.1";
        leaf tmnxChassisIndex {
          type leafref {
            path "/timetra-chassis:TIMETRA-CHASSIS-MIB/timetra-chassis:tmnxChassisTable/timetra-chassis:tmnxChassisEntry/timetra-chassis:tmnxChassisIndex";
          }
          config true;
        }
        leaf tmnxBundleBundleID {
          type leafref {
            path "/timetra-port:TIMETRA-PORT-MIB/timetra-port:tmnxBundleTable/timetra-port:tmnxBundleEntry/timetra-port:tmnxBundleBundleID";
          }
          config true;
        }
        leaf tmnxBundleMlpppEndpointID {
          type binary {
            length "0..20";
          }
          description
            "tmnxBundleMlpppEndpointID indentifies the Endpoint Discriminator
             identifier value within the specified tmnxBundleMlpppEndpointIDClass.
             The object tmnxPortAdminStatus must be set to 'outOfService' to
             change this value.";
          smiv2:max-access "read-write";
          smiv2:oid "1.3.6.1.4.1.6527.3.1.2.2.4.26.1.1";
          config true;
        }
        leaf tmnxBundleMlpppEndpointIDClass {
          type timetra-port:TmnxMlpppEndpointIdClass;
          description
            "tmnxBundleMlpppEndpointIDClass specifies the Link Control
             Protocol Endpoint Descriminator Class field type of the
             tmnxBundleMlpppEndpointID. The object tmnxPortAdminStatus
             must be set to 'outOfService' to change this value.
             
                        Bundle                     DEFVAL
                Physical MLPPP Bundle           ieee802dot1GlobalMacAddress (3)
                MLPPP Bundle Protection Group   ipAddress (2)";
          smiv2:max-access "read-write";
          smiv2:oid "1.3.6.1.4.1.6527.3.1.2.2.4.26.1.2";
          config true;
        }
        leaf tmnxBundleMlpppClassCount {
          type int32 {
            range "0..16";
          }
          description
            "The value of tmnxBundleMlpppClassCount specifies
             whether Multiclass MLPPP is enabled on
             a bundle with a tmnxBundleType of 'mlppp' and when enabled what is the
             number of classes to be negotiated/supported over the MLPPP bundle.
             
             The value of 0 disables multiclass MLPPP including negotiation in
             the PPP protocol.
             All other values specify the number of classes to be supported
             on a given multiclass bundle and enable Multiclass MLPPP negotiation
             on that bundle.
             
             Non-zero values supported are platform/MDA specific.
             
             The value of tmnxBundleMlpppClassCount must be set to 0 and cannot be
             changed when LFI is enabled on the bundle (see tmnxBundleLFI object
             in tmnxBundleTable).
             
             The value of tmnxBundleMlpppClassCount may be modified only when
             tmnxBundleNumLinks is zero.
             
             To set the value of tmnxBundleMlpppClassCount to a value greater
             than 4, the long sequence format must be enabled on the bundle (see
             tmnxBundleShortSequence object in tmnxBundleTable).
             
             Changing the value of tmnxBundleMlpppClassCount resets the values of
             tmnxBundleMlpppIngQoSProfId and tmnxBundleMlpppEgrQoSProfId to their
             defaults";
          smiv2:defval "0";
          smiv2:max-access "read-write";
          smiv2:oid "1.3.6.1.4.1.6527.3.1.2.2.4.26.1.3";
          config true;
        }
        leaf tmnxBundleMlpppIngQoSProfId {
          type timetra-tc:TMlpppQoSProfileId;
          description
            "tmnxBundleMlpppIngQoSProfId specifies ingress QoS profile
             to be used for the incoming traffic over this MLPPP
             bundle.
             
             The value of tmnxBundleMlpppIngQoSProfId may be modified only
             when the value of tmnxBundleNumLinks is 0.
             
             The value of tmnxBundleMlpppIngQoSProfId of 0 indicates
             a default QoS profile is used as applicable to a given hardware
             and the configured value of tmnxBundleMlpppClassCount.";
          smiv2:defval "0";
          smiv2:max-access "read-write";
          smiv2:oid "1.3.6.1.4.1.6527.3.1.2.2.4.26.1.4";
          config true;
        }
        leaf tmnxBundleMlpppEgrQoSProfId {
          type timetra-tc:TMlpppQoSProfileId;
          description
            "tmnxBundleMlpppEgrQoSProfId specifies egress QoS profile
             to be used for the outgoing traffic over this MLPPP
             bundle.
             
             The value of tmnxBundleMlpppEgrQoSProfId may be modified only
             when tmnxBundleNumLinks is zero.
             
             The value of tmnxBundleMlpppEgrQoSProfId of 0 indicates
             a default profile is used as applicable to a given hardware
             and the configured value of tmnxBundleMlpppClassCount.";
          smiv2:defval "0";
          smiv2:max-access "read-write";
          smiv2:oid "1.3.6.1.4.1.6527.3.1.2.2.4.26.1.5";
          config true;
        }
        leaf tmnxBundleMlpppMagicNumber {
          type timetra-tc:TmnxEnabledDisabled;
          description
            "tmnxBundleMlpppMagicNumber specifies whether or not the bundle will
             detect a loopback scenario on member links and take a looped back
             member links out of service.
             A value of 'enabled (1)' will detect loopbacks.";
          smiv2:defval "disabled";
          smiv2:max-access "read-write";
          smiv2:oid "1.3.6.1.4.1.6527.3.1.2.2.4.26.1.6";
          config true;
        }
        leaf tmnxBundleMlpppStatelessApsSwo {
          type timetra-tc:TmnxEnabledDisabled;
          description
            "tmnxBundleMlpppStatelessApsSwo specifies whether the bundle will
             perform a statefull or a stateless APS switchover.
             
             The value of tmnxBundleMlpppStatelessApsSwo must be set to 'disabled (2)' and
             cannot be changed for normal mlppp bundles.
             
             The value of tmnxBundleMlpppStatelessApsSwo may be changed
             for APS bundle protection groups.
             
             A stateless switchover implies that PPP is renegotiated on  each member
             link after the switchover. PPP negotiations may take a few seconds
             to complete.
             
             A statefull switchover implies that after an APS switchover the PPP
             state of the bundle will be restored based on the bpgrp bundle state
             before the switchover.
             
             A value of 'enabled (1)' will configure stateless APS switchovers.";
          smiv2:defval "disabled";
          smiv2:max-access "read-write";
          smiv2:oid "1.3.6.1.4.1.6527.3.1.2.2.4.26.1.7";
          config true;
        }
        config true;
      }
      config true;
    }
    container tmnxHsmdaPortSchOvrTable {
      description
        "The tmnxHsmdaPortSchOvrTable has an entry for each port-level HSMDA
         scheduler override configured on this system.";
      smiv2:oid "1.3.6.1.4.1.6527.3.1.2.2.4.28";
      list tmnxHsmdaPortSchOvrEntry {
        key "tmnxChassisIndex tmnxPortPortID";
        description
          "Each row represents a particular port-level HSMDA scheduler override.
           Entries are created and deleted by the user.";
        smiv2:oid "1.3.6.1.4.1.6527.3.1.2.2.4.28.1";
        leaf tmnxChassisIndex {
          type leafref {
            path "/timetra-chassis:TIMETRA-CHASSIS-MIB/timetra-chassis:tmnxChassisTable/timetra-chassis:tmnxChassisEntry/timetra-chassis:tmnxChassisIndex";
          }
          config true;
        }
        leaf tmnxPortPortID {
          type leafref {
            path "/timetra-port:TIMETRA-PORT-MIB/timetra-port:tmnxPortTable/timetra-port:tmnxPortEntry/timetra-port:tmnxPortPortID";
          }
          config true;
        }
        leaf tmnxHsmdaPortSchOvrRowStatus {
          type snmpv2-tc:RowStatus;
          description
            "The value of tmnxHsmdaPortSchOvrRowStatus is used for the
             creation and deletion of port-level HSMDA scheduler overrides.
             
             When the tmnxMDAAssignedType of the tmnxPortEntry indexed
             by the same indices of this table is a non-HSMDA MDA Type,
             creation will fail and return a 'noCreation' error.";
          smiv2:max-access "read-write";
          smiv2:oid "1.3.6.1.4.1.6527.3.1.2.2.4.28.1.1";
          config false;
        }
        leaf tmnxHsmdaPortSchOvrLastChanged {
          type yang:timestamp;
          description
            "The value of tmnxHsmdaPortSchOvrLastChanged indicates the sysUpTime
             at the time of the last modification of this entry.
             
             If no changes were made to the entry since the last
             re-initialization of the local network management subsystem,
             then this object contains a zero value.";
          smiv2:max-access "read-only";
          smiv2:oid "1.3.6.1.4.1.6527.3.1.2.2.4.28.1.2";
          config false;
        }
        leaf tmnxHsmdaPortSchOvrMaxRate {
          type timetra-tc:THsmdaPIRMRateOverride;
          units "Mbps";
          description
            "The value of tmnxHsmdaPortSchOvrMaxRate specifies the explicit
             maximum frame based bandwidth limit for this HSMDA port
             scheduler.
             
             A value of -2 indicates no override.
             
             This object overrides TIMETRA-QOS-MIB::tHsmdaSchedulerPlcyMaxRate.";
          smiv2:defval "-2";
          smiv2:max-access "read-write";
          smiv2:oid "1.3.6.1.4.1.6527.3.1.2.2.4.28.1.3";
          config true;
        }
        leaf tmnxHsmdaPortSchOvrGrp1Rate {
          type timetra-tc:THsmdaPIRMRateOverride;
          units "Mbps";
          description
            "The value of tmnxHsmdaPortSchOvrGrp1Rate specifies the explicit
             maximum frame based bandwidth limit, in megabits per second, for
             group 1 for this HSMDA port scheduler.
             
             A value of -2 indicates no override.
             
             This object overrides TIMETRA-QOS-MIB::tHsmdaSchedulerPlcyGrp1Rate.";
          smiv2:defval "-2";
          smiv2:max-access "read-write";
          smiv2:oid "1.3.6.1.4.1.6527.3.1.2.2.4.28.1.4";
          config true;
        }
        leaf tmnxHsmdaPortSchOvrGrp2Rate {
          type timetra-tc:THsmdaPIRMRateOverride;
          units "Mbps";
          description
            "The value of tmnxHsmdaPortSchOvrGrp2Rate specifies the explicit
             maximum frame based bandwidth limit, in megabits per second, for
             group 2 for this HSMDA port scheduler.
             
             A value of -2 indicates no override.
             
             This object overrides TIMETRA-QOS-MIB::tHsmdaSchedulerPlcyGrp2Rate.";
          smiv2:defval "-2";
          smiv2:max-access "read-write";
          smiv2:oid "1.3.6.1.4.1.6527.3.1.2.2.4.28.1.5";
          config true;
        }
        leaf tmnxHsmdaPortSchOvrClass1Rate {
          type timetra-tc:THsmdaPIRMRateOverride;
          units "Mbps";
          description
            "The value of tmnxHsmdaPortSchOvrClass1Rate specifies the explicit
             maximum frame based bandwidth limit, in megabits per second, for
             this HSMDA port scheduler policy level.
             
             A value of -2 indicates no override.
             
             This object overrides TIMETRA-QOS-MIB::tHsmdaSchedulerPlcyLvl1Rate.";
          smiv2:defval "-2";
          smiv2:max-access "read-write";
          smiv2:oid "1.3.6.1.4.1.6527.3.1.2.2.4.28.1.6";
          config true;
        }
        leaf tmnxHsmdaPortSchOvrClass1WtInGp {
          type timetra-tc:THsmdaWeightOverride;
          description
            "The value of tmnxHsmdaPortSchOvrClass1WtInGp specifies the weight
             the HSMDA port scheduler policy should apply to this policy level
             within the group it belongs to.
             
             The value of tmnxHsmdaPortSchOvrClass1WtInGp will only be
             used if this policy level has been assigned to a group
             by setting tHsmdaSchedulerPlcyLvl1GrpId to a non-zero value.
             
             A value of -2 indicates no override.
             
             This object overrides
             TIMETRA-QOS-MIB::tHsmdaSchedulerPlcyLvl1WgtInGrp.";
          smiv2:defval "-2";
          smiv2:max-access "read-write";
          smiv2:oid "1.3.6.1.4.1.6527.3.1.2.2.4.28.1.7";
          config true;
        }
        leaf tmnxHsmdaPortSchOvrClass2Rate {
          type timetra-tc:THsmdaPIRMRateOverride;
          units "Mbps";
          description
            "The value of tmnxHsmdaPortSchOvrClass2Rate specifies the explicit
             maximum frame based bandwidth limit, in megabits per second, for
             this HSMDA port scheduler policy level.
             
             A value of -2 indicates no override.
             
             This object overrides TIMETRA-QOS-MIB::tHsmdaSchedulerPlcyLvl2Rate.";
          smiv2:defval "-2";
          smiv2:max-access "read-write";
          smiv2:oid "1.3.6.1.4.1.6527.3.1.2.2.4.28.1.8";
          config true;
        }
        leaf tmnxHsmdaPortSchOvrClass2WtInGp {
          type timetra-tc:THsmdaWeightOverride;
          description
            "The value of tmnxHsmdaPortSchOvrClass2WtInGp specifies the weight
             the HSMDA port scheduler policy should apply to this policy level
             within the group it belongs to.
             
             The value of tmnxHsmdaPortSchOvrClass2WtInGp will only be
             used if this policy level has been assigned to a group
             by setting tHsmdaSchedulerPlcyLvl2GrpId to a non-zero value.
             
             A value of -2 indicates no override.
             
             This object overrides
             TIMETRA-QOS-MIB::tHsmdaSchedulerPlcyLvl2WgtInGrp.";
          smiv2:defval "-2";
          smiv2:max-access "read-write";
          smiv2:oid "1.3.6.1.4.1.6527.3.1.2.2.4.28.1.9";
          config true;
        }
        leaf tmnxHsmdaPortSchOvrClass3Rate {
          type timetra-tc:THsmdaPIRMRateOverride;
          units "Mbps";
          description
            "The value of tmnxHsmdaPortSchOvrClass3Rate specifies the explicit
             maximum frame based bandwidth limit, in megabits per second, for
             this HSMDA port scheduler policy level.
             
             A value of -2 indicates no override.
             
             This object overrides TIMETRA-QOS-MIB::tHsmdaSchedulerPlcyLvl3Rate.";
          smiv2:defval "-2";
          smiv2:max-access "read-write";
          smiv2:oid "1.3.6.1.4.1.6527.3.1.2.2.4.28.1.10";
          config true;
        }
        leaf tmnxHsmdaPortSchOvrClass3WtInGp {
          type timetra-tc:THsmdaWeightOverride;
          description
            "The value of tmnxHsmdaPortSchOvrClass3WtInGp specifies the weight
             the HSMDA port scheduler policy should apply to this policy level
             within the group it belongs to.
             
             The value of tmnxHsmdaPortSchOvrClass3WtInGp will only be
             used if this policy level has been assigned to a group
             by setting tHsmdaSchedulerPlcyLvl3GrpId to a non-zero value.
             
             A value of -2 indicates no override.
             
             This object overrides
             TIMETRA-QOS-MIB::tHsmdaSchedulerPlcyLvl3WgtInGrp.";
          smiv2:defval "-2";
          smiv2:max-access "read-write";
          smiv2:oid "1.3.6.1.4.1.6527.3.1.2.2.4.28.1.11";
          config true;
        }
        leaf tmnxHsmdaPortSchOvrClass4Rate {
          type timetra-tc:THsmdaPIRMRateOverride;
          units "Mbps";
          description
            "The value of tmnxHsmdaPortSchOvrClass4Rate specifies the explicit
             maximum frame based bandwidth limit, in megabits per second, for
             this HSMDA port scheduler policy level.
             
             A value of -2 indicates no override.
             
             This object overrides TIMETRA-QOS-MIB::tHsmdaSchedulerPlcyLvl4Rate.";
          smiv2:defval "-2";
          smiv2:max-access "read-write";
          smiv2:oid "1.3.6.1.4.1.6527.3.1.2.2.4.28.1.12";
          config true;
        }
        leaf tmnxHsmdaPortSchOvrClass4WtInGp {
          type timetra-tc:THsmdaWeightOverride;
          description
            "The value of tmnxHsmdaPortSchOvrClass4WtInGp specifies the weight
             the HSMDA port scheduler policy should apply to this policy level
             within the group it belongs to.
             
             The value of tmnxHsmdaPortSchOvrClass4WtInGp will only be
             used if this policy level has been assigned to a group
             by setting tHsmdaSchedulerPlcyLvl4GrpId to a non-zero value.
             
             A value of -2 indicates no override.
             
             This object overrides
             TIMETRA-QOS-MIB::tHsmdaSchedulerPlcyLvl4WgtInGrp.";
          smiv2:defval "-2";
          smiv2:max-access "read-write";
          smiv2:oid "1.3.6.1.4.1.6527.3.1.2.2.4.28.1.13";
          config true;
        }
        leaf tmnxHsmdaPortSchOvrClass5Rate {
          type timetra-tc:THsmdaPIRMRateOverride;
          units "Mbps";
          description
            "The value of tmnxHsmdaPortSchOvrClass5Rate specifies the explicit
             maximum frame based bandwidth limit, in megabits per second, for
             this HSMDA port scheduler policy level.
             
             A value of -2 indicates no override.
             
             This object overrides TIMETRA-QOS-MIB::tHsmdaSchedulerPlcyLvl5Rate.";
          smiv2:defval "-2";
          smiv2:max-access "read-write";
          smiv2:oid "1.3.6.1.4.1.6527.3.1.2.2.4.28.1.14";
          config true;
        }
        leaf tmnxHsmdaPortSchOvrClass5WtInGp {
          type timetra-tc:THsmdaWeightOverride;
          description
            "The value of tmnxHsmdaPortSchOvrClass5WtInGp specifies the weight
             the HSMDA port scheduler policy should apply to this policy level
             within the group it belongs to.
             
             The value of tmnxHsmdaPortSchOvrClass5WtInGp will only be
             used if this policy level has been assigned to a group
             by setting tHsmdaSchedulerPlcyLvl5GrpId to a non-zero value.
             
             A value of -2 indicates no override.
             
             This object overrides
             TIMETRA-QOS-MIB::tHsmdaSchedulerPlcyLvl5WgtInGrp.";
          smiv2:defval "-2";
          smiv2:max-access "read-write";
          smiv2:oid "1.3.6.1.4.1.6527.3.1.2.2.4.28.1.15";
          config true;
        }
        leaf tmnxHsmdaPortSchOvrClass6Rate {
          type timetra-tc:THsmdaPIRMRateOverride;
          units "Mbps";
          description
            "The value of tmnxHsmdaPortSchOvrClass6Rate specifies the explicit
             maximum frame based bandwidth limit, in megabits per second, for
             this HSMDA port scheduler policy level.
             
             A value of -2 indicates no override.
             
             This object overrides TIMETRA-QOS-MIB::tHsmdaSchedulerPlcyLvl6Rate.";
          smiv2:defval "-2";
          smiv2:max-access "read-write";
          smiv2:oid "1.3.6.1.4.1.6527.3.1.2.2.4.28.1.16";
          config true;
        }
        leaf tmnxHsmdaPortSchOvrClass6WtInGp {
          type timetra-tc:THsmdaWeightOverride;
          description
            "The value of tmnxHsmdaPortSchOvrClass6WtInGp specifies the weight
             the HSMDA port scheduler policy should apply to this policy level
             within the group it belongs to.
             
             The value of tmnxHsmdaPortSchOvrClass6WtInGp will only be
             used if this policy level has been assigned to a group
             by setting tHsmdaSchedulerPlcyLvl6GrpId to a non-zero value.
             
             A value of -2 indicates no override.
             
             This object overrides
             TIMETRA-QOS-MIB::tHsmdaSchedulerPlcyLvl6WgtInGrp.";
          smiv2:defval "-2";
          smiv2:max-access "read-write";
          smiv2:oid "1.3.6.1.4.1.6527.3.1.2.2.4.28.1.17";
          config true;
        }
        leaf tmnxHsmdaPortSchOvrClass7Rate {
          type timetra-tc:THsmdaPIRMRateOverride;
          units "Mbps";
          description
            "The value of tmnxHsmdaPortSchOvrClass7Rate specifies the explicit
             maximum frame based bandwidth limit, in megabits per second, for
             this HSMDA port scheduler policy level.
             
             A value of -2 indicates no override.
             
             This object overrides TIMETRA-QOS-MIB::tHsmdaSchedulerPlcyLvl7Rate.";
          smiv2:defval "-2";
          smiv2:max-access "read-write";
          smiv2:oid "1.3.6.1.4.1.6527.3.1.2.2.4.28.1.18";
          config true;
        }
        leaf tmnxHsmdaPortSchOvrClass7WtInGp {
          type timetra-tc:THsmdaWeightOverride;
          description
            "The value of tmnxHsmdaPortSchOvrClass7WtInGp specifies the weight
             the HSMDA port scheduler policy should apply to this policy level
             within the group it belongs to.
             
             The value of tmnxHsmdaPortSchOvrClass7WtInGp will only be
             used if this policy level has been assigned to a group
             by setting tHsmdaSchedulerPlcyLvl7GrpId to a non-zero value.
             
             A value of -2 indicates no override.
             
             This object overrides
             TIMETRA-QOS-MIB::tHsmdaSchedulerPlcyLvl7WgtInGrp.";
          smiv2:defval "-2";
          smiv2:max-access "read-write";
          smiv2:oid "1.3.6.1.4.1.6527.3.1.2.2.4.28.1.19";
          config true;
        }
        leaf tmnxHsmdaPortSchOvrClass8Rate {
          type timetra-tc:THsmdaPIRMRateOverride;
          units "Mbps";
          description
            "The value of tmnxHsmdaPortSchOvrClass8Rate specifies the explicit
             maximum frame based bandwidth limit, in megabits per second, for
             this HSMDA port scheduler policy level.
             
             A value of -2 indicates no override.
             
             This object overrides TIMETRA-QOS-MIB::tHsmdaSchedulerPlcyLvl8Rate.";
          smiv2:defval "-2";
          smiv2:max-access "read-write";
          smiv2:oid "1.3.6.1.4.1.6527.3.1.2.2.4.28.1.20";
          config true;
        }
        leaf tmnxHsmdaPortSchOvrClass8WtInGp {
          type timetra-tc:THsmdaWeightOverride;
          description
            "The value of tmnxHsmdaPortSchOvrClass8WtInGp specifies the weight
             the HSMDA port scheduler policy should apply to this policy level
             within the group it belongs to.
             
             The value of tmnxHsmdaPortSchOvrClass8WtInGp will only be
             used if this policy level has been assigned to a group
             by setting tHsmdaSchedulerPlcyLvl8GrpId to a non-zero value.
             
             A value of -2 indicates no override.
             
             This object overrides
             TIMETRA-QOS-MIB::tHsmdaSchedulerPlcyLvl8WgtInGrp.";
          smiv2:defval "-2";
          smiv2:max-access "read-write";
          smiv2:oid "1.3.6.1.4.1.6527.3.1.2.2.4.28.1.21";
          config true;
        }
        config true;
      }
      config true;
    }
    container tmnxPortEgrShaperTable {
      status obsolete;
      description
        "The tmnxPortEgrShaperTable has an entry for each port-level egress
         secondary shaper configured on this system.
         
         This table is obsoleted in 10.0 Release.";
      smiv2:oid "1.3.6.1.4.1.6527.3.1.2.2.4.30";
      list tmnxPortEgrShaperEntry {
        key "tmnxChassisIndex tmnxPortPortID tmnxPortEgrShaperName";
        status obsolete;
        description
          "Each row represents a particular port-level egress secondary shaper.
           Entries are created and deleted by the user.";
        smiv2:oid "1.3.6.1.4.1.6527.3.1.2.2.4.30.1";
        leaf tmnxChassisIndex {
          type leafref {
            path "/timetra-chassis:TIMETRA-CHASSIS-MIB/timetra-chassis:tmnxChassisTable/timetra-chassis:tmnxChassisEntry/timetra-chassis:tmnxChassisIndex";
          }
          config true;
        }
        leaf tmnxPortPortID {
          type leafref {
            path "/timetra-port:TIMETRA-PORT-MIB/timetra-port:tmnxPortTable/timetra-port:tmnxPortEntry/timetra-port:tmnxPortPortID";
          }
          config true;
        }
        leaf tmnxPortEgrShaperName {
          type timetra-tc:TNamedItem;
          status obsolete;
          description
            "The port egress shaper named is used an index to the table entry.";
          smiv2:max-access "not-accessible";
          smiv2:oid "1.3.6.1.4.1.6527.3.1.2.2.4.30.1.1";
          config true;
        }
        leaf tmnxPortEgrShaperRowStatus {
          type snmpv2-tc:RowStatus;
          status obsolete;
          description
            "The value of tmnxPortEgrShaperRowStatus is used for the creation
             and deletion of entries in the tmnxPortEgrShaperTable.";
          smiv2:max-access "read-write";
          smiv2:oid "1.3.6.1.4.1.6527.3.1.2.2.4.30.1.2";
          config false;
        }
        leaf tmnxPortEgrShaperLastChanged {
          type yang:timestamp;
          status obsolete;
          description
            "The value of tmnxPortEgrShaperLastChanged indicates the sysUpTime
             at the time of the last modification of this entry.
             
             If no changes were made to the entry since the last
             re-initialization of the local network management subsystem,
             then this object contains a zero value.";
          smiv2:max-access "read-only";
          smiv2:oid "1.3.6.1.4.1.6527.3.1.2.2.4.30.1.3";
          config false;
        }
        leaf tmnxPortEgrShaperRate {
          type timetra-tc:TSecondaryShaper10GPIRRate;
          units "Mbps";
          status obsolete;
          description
            "The value of tmnxPortEgrShaperRate specifies the explicit maximum
             frame based bandwidth limit, in megabits per second, of this
             egress port secondary shaper policy.";
          smiv2:defval "-1";
          smiv2:max-access "read-write";
          smiv2:oid "1.3.6.1.4.1.6527.3.1.2.2.4.30.1.4";
          config true;
        }
        config true;
      }
      config true;
    }
    container tmnxDigitalDiagMonitorTable {
      description
        "The tmnxDigitalDiagMonitorTable has an entry for each SFF in the
         system that supports Digital Diagnostic Monitoring (DDM). The table is
         indexed by TmnxPortID. Each row in this table is dynamically added
         and removed internally by the system based on the presence or absence
         of DDM capable SFF components.";
      smiv2:oid "1.3.6.1.4.1.6527.3.1.2.2.4.31";
      list tmnxDigitalDiagMonitorEntry {
        key "tmnxChassisIndex tmnxPortPortID";
        description
          "Each row represents a particular SFF that supports Digital
           Diagnostic Monitoring.
           Entries are created and deleted internally by the system.";
        smiv2:oid "1.3.6.1.4.1.6527.3.1.2.2.4.31.1";
        leaf tmnxChassisIndex {
          type leafref {
            path "/timetra-chassis:TIMETRA-CHASSIS-MIB/timetra-chassis:tmnxChassisTable/timetra-chassis:tmnxChassisEntry/timetra-chassis:tmnxChassisIndex";
          }
        }
        leaf tmnxPortPortID {
          type leafref {
            path "/timetra-port:TIMETRA-PORT-MIB/timetra-port:tmnxPortTable/timetra-port:tmnxPortEntry/timetra-port:tmnxPortPortID";
          }
        }
        leaf tmnxDDMTemperature {
          type int32;
          description
            "The value of tmnxDDMTemperature indicates the current temperature
             of the SFF in 1/256th degrees Celsius.
             
             If the SFF is externally calibrated, the objects
             tmnxDDMExtCalTemperatureSlope and tmnxDDMExtCalTemperatureOffset affect
             the temperature calculation.
             
             The formula for translating between the value of tmnxDDMTemperature and
             degrees Celsius is:
                 Internally Calibrated only:
                    tmnxDDMTemperature / 256
                 Externally Calibrated:
                    (tmnxDDMTemperature * (tmnxDDMExtCalTemperatureSlope / 256)
                          + tmnxDDMExtCalTemperatureOffset) / 256
             
             For example (internally calibrated SFP):
             The SNMP value 5734 is 22.4 degrees Celsius.";
          smiv2:max-access "read-only";
          smiv2:oid "1.3.6.1.4.1.6527.3.1.2.2.4.31.1.1";
        }
        leaf tmnxDDMTempLowWarning {
          type int32;
          description
            "The value of tmnxDDMTempLowWarning indicates the temperature
             of the SFF in degrees Celsius that triggers a low-warning.";
          smiv2:max-access "read-only";
          smiv2:oid "1.3.6.1.4.1.6527.3.1.2.2.4.31.1.2";
        }
        leaf tmnxDDMTempLowAlarm {
          type int32;
          description
            "The value of tmnxDDMTempLowAlarm indicates the temperature
             of the SFF in degrees Celsius that triggers a low-alarm.";
          smiv2:max-access "read-only";
          smiv2:oid "1.3.6.1.4.1.6527.3.1.2.2.4.31.1.3";
        }
        leaf tmnxDDMTempHiWarning {
          type int32;
          description
            "The value of tmnxDDMTempHiWarning indicates the temperature
             of the SFF in degrees Celsius that triggers a hi-warning.";
          smiv2:max-access "read-only";
          smiv2:oid "1.3.6.1.4.1.6527.3.1.2.2.4.31.1.4";
        }
        leaf tmnxDDMTempHiAlarm {
          type int32;
          description
            "The value of tmnxDDMTempHiAlarm indicates the temperature
             of the SFF in degrees Celsius that triggers a hi-alarm.";
          smiv2:max-access "read-only";
          smiv2:oid "1.3.6.1.4.1.6527.3.1.2.2.4.31.1.5";
        }
        leaf tmnxDDMSupplyVoltage {
          type int32;
          description
            "The value of tmnxDDMSupplyVoltage indicates the current supply
             voltage of the SFF in 1/10000 of a Volt(V).
             
             If the SFF is externally calibrated, the objects
             tmnxDDMExtCalVoltageSlope and tmnxDDMExtCalVoltageOffset affect
             the voltage calculation.
             
             The formula for translating between the value of tmnxDDMSupplyVoltage
             and Voltage is:
                 Internally Calibrated only:
                    tmnxDDMSupplyVoltage / 10000
                 Externally Calibrated:
                    (tmnxDDMSupplyVoltage * (tmnxDDMExtCalVoltageSlope / 256)
                          + tmnxDDMExtCalVoltageOffset) / 10000
             
             For example (internally calibrated SFP):
             The SNMP value 32851 is 3.2851 Volts (V).";
          smiv2:max-access "read-only";
          smiv2:oid "1.3.6.1.4.1.6527.3.1.2.2.4.31.1.6";
        }
        leaf tmnxDDMSupplyVoltageLowWarning {
          type int32;
          description
            "The value of tmnxDDMSupplyVoltageLowWarning indicates the supply
             voltage of the SFF in micro-Volts (uV) that triggers a
             low-warning.";
          smiv2:max-access "read-only";
          smiv2:oid "1.3.6.1.4.1.6527.3.1.2.2.4.31.1.7";
        }
        leaf tmnxDDMSupplyVoltageLowAlarm {
          type int32;
          description
            "The value of tmnxDDMSupplyVoltageLowAlarm indicates the supply
             voltage of the SFF in micro-Volts (uV) that triggers a low-alarm.";
          smiv2:max-access "read-only";
          smiv2:oid "1.3.6.1.4.1.6527.3.1.2.2.4.31.1.8";
        }
        leaf tmnxDDMSupplyVoltageHiWarning {
          type int32;
          description
            "The value of tmnxDDMSupplyVoltageHiWarning indicates the supply
             voltage of the SFF in micro-Volts (uV) that triggers a hi-warning.";
          smiv2:max-access "read-only";
          smiv2:oid "1.3.6.1.4.1.6527.3.1.2.2.4.31.1.9";
        }
        leaf tmnxDDMSupplyVoltageHiAlarm {
          type int32;
          description
            "The value of tmnxDDMSupplyVoltageHiAlarm indicates the supply
             voltage of the SFF in micro-Volts (uV) that triggers a hi-alarm.";
          smiv2:max-access "read-only";
          smiv2:oid "1.3.6.1.4.1.6527.3.1.2.2.4.31.1.10";
        }
        leaf tmnxDDMTxBiasCurrent {
          type int32;
          description
            "The value of tmnxDDMTxBiasCurrent indicates the current Transmit
             Bias Current of the SFF in 1/500 milliamperes (mA).
             
             If the SFF is externally calibrated, the objects
             tmnxDDMExtCalTxLaserBiasSlope and tmnxDDMExtCalTxLaserBiasOffset affect
             the ampere calculation.
             
             The formula for translating between the value of tmnxDDMTxBiasCurrent
             and amperes is:
                 Internally Calibrated only:
                    tmnxDDMTxBiasCurrent / 500
                 Externally Calibrated:
                    (tmnxDDMTxBiasCurrent * (tmnxDDMExtCalTxLaserBiasSlope / 256)
                          + tmnxDDMExtCalTxLaserBiasOffset) / 500
             
             For example (internally calibrated SFP):
             The SNMP value 2565 is 5.1 milliamperes (mA).";
          smiv2:max-access "read-only";
          smiv2:oid "1.3.6.1.4.1.6527.3.1.2.2.4.31.1.11";
        }
        leaf tmnxDDMTxBiasCurrentLowWarning {
          type int32;
          description
            "The value of tmnxDDMTxBiasCurrentLowWarning indicates the Transmit
             Bias Current of the SFF in micro-Amperes (uA) that triggers a
             low-warning.";
          smiv2:max-access "read-only";
          smiv2:oid "1.3.6.1.4.1.6527.3.1.2.2.4.31.1.12";
        }
        leaf tmnxDDMTxBiasCurrentLowAlarm {
          type int32;
          description
            "The value of tmnxDDMTxBiasCurrentLowAlarm indicates the Transmit
             Bias Current of the SFF in micro-Amperes (uA) that triggers a
             low-alarm.";
          smiv2:max-access "read-only";
          smiv2:oid "1.3.6.1.4.1.6527.3.1.2.2.4.31.1.13";
        }
        leaf tmnxDDMTxBiasCurrentHiWarning {
          type int32;
          description
            "The value of tmnxDDMTxBiasCurrentHiWarning indicates the Transmit
             Bias Current of the SFF in micro-Amperes (uA) that triggers a
             hi-warning.";
          smiv2:max-access "read-only";
          smiv2:oid "1.3.6.1.4.1.6527.3.1.2.2.4.31.1.14";
        }
        leaf tmnxDDMTxBiasCurrentHiAlarm {
          type int32;
          description
            "The value of tmnxDDMTxBiasCurrentHiAlarm indicates the Transmit
             Bias Current of the SFF in micro-Amperes (uA) that triggers a
             hi-alarm.";
          smiv2:max-access "read-only";
          smiv2:oid "1.3.6.1.4.1.6527.3.1.2.2.4.31.1.15";
        }
        leaf tmnxDDMTxOutputPower {
          type int32;
          description
            "The value of tmnxDDMTxOutputPower indicates the current Output
             Power of the SFF in one tenths of a micro-Watt (uW).
             
             For example:
             Using the SNMP value of 790, and using units of tenths of microwatt,
             790 becomes 79 microwatts or 0.079 milliwatts. Converting to dBm:
                   10 x log10(0.079) = -11.0 dBm";
          smiv2:max-access "read-only";
          smiv2:oid "1.3.6.1.4.1.6527.3.1.2.2.4.31.1.16";
        }
        leaf tmnxDDMTxOutputPowerLowWarning {
          type int32;
          description
            "The value of tmnxDDMTxOutputPowerLowWarning indicates the Output Power
             of the SFF in one tenths of a micro-Watt (uW) that triggers a
             low-warning.";
          smiv2:max-access "read-only";
          smiv2:oid "1.3.6.1.4.1.6527.3.1.2.2.4.31.1.17";
        }
        leaf tmnxDDMTxOutputPowerLowAlarm {
          type int32;
          description
            "The value of tmnxDDMTxOutputPowerLowAlarm indicates the Output Power
             of the SFF in one tenths of a micro-Watt (uW) that triggers a
             low-alarm.";
          smiv2:max-access "read-only";
          smiv2:oid "1.3.6.1.4.1.6527.3.1.2.2.4.31.1.18";
        }
        leaf tmnxDDMTxOutputPowerHiWarning {
          type int32;
          description
            "The value of tmnxDDMTxOutputPowerHiWarning indicates the Output Power
             of the SFF in one tenths of a micro-Watt (uW) that triggers a
             hi-warning.";
          smiv2:max-access "read-only";
          smiv2:oid "1.3.6.1.4.1.6527.3.1.2.2.4.31.1.19";
        }
        leaf tmnxDDMTxOutputPowerHiAlarm {
          type int32;
          description
            "The value of tmnxDDMTxOutputPowerHiAlarm indicates the Output Power
             of the SFF in one tenths of a micro-Watt (uW) that triggers a
             hi-alarm.";
          smiv2:max-access "read-only";
          smiv2:oid "1.3.6.1.4.1.6527.3.1.2.2.4.31.1.20";
        }
        leaf tmnxDDMRxOpticalPower {
          type int32;
          description
            "The value of tmnxDDMRxOpticalPower indicates the current Received
             Optical Power of the SFF in one tenths of a micro-Watt (uW).
             
             For example:
             Using the SNMP value of 790, and using units of tenths of microwatt,
             790 becomes 79 microwatts or 0.079 milliwatts. Converting to dBm:
                   10 x log10(0.079) = -11.0 dBm";
          smiv2:max-access "read-only";
          smiv2:oid "1.3.6.1.4.1.6527.3.1.2.2.4.31.1.21";
        }
        leaf tmnxDDMRxOpticalPowerLowWarning {
          type int32;
          description
            "The value of tmnxDDMRxOpticalPowerLowWarning indicates the Received
             Optical Power of the SFF in one tenths of a micro-Watt (uW) that
             triggers a low-warning.";
          smiv2:max-access "read-only";
          smiv2:oid "1.3.6.1.4.1.6527.3.1.2.2.4.31.1.22";
        }
        leaf tmnxDDMRxOpticalPowerLowAlarm {
          type int32;
          description
            "The value of tmnxDDMRxOpticalPowerLowAlarm indicates the Received
             Optical Power of the SFF in one tenths of a micro-Watt (uW) that
             triggers a low-alarm.";
          smiv2:max-access "read-only";
          smiv2:oid "1.3.6.1.4.1.6527.3.1.2.2.4.31.1.23";
        }
        leaf tmnxDDMRxOpticalPowerHiWarning {
          type int32;
          description
            "The value of tmnxDDMRxOpticalPowerHiWarning indicates the Received
             Optical Power of the SFF in one tenths of a micro-Watt (uW) that
             triggers a hi-warning.";
          smiv2:max-access "read-only";
          smiv2:oid "1.3.6.1.4.1.6527.3.1.2.2.4.31.1.24";
        }
        leaf tmnxDDMRxOpticalPowerHiAlarm {
          type int32;
          description
            "The value of tmnxDDMRxOpticalPowerHiAlarm indicates the Received
             Optical Power of the SFF in one tenths of a micro-Watt (uW) that
             triggers a hi-alarm.";
          smiv2:max-access "read-only";
          smiv2:oid "1.3.6.1.4.1.6527.3.1.2.2.4.31.1.25";
        }
        leaf tmnxDDMRxOpticalPowerType {
          type enumeration {
            enum "oma" {
              value 0;
            }
            enum "average" {
              value 1;
            }
          }
          description
            "The value of tmnxDDMRxOpticalPowerType indicates whether the
             tmnxDDMRxOpticalPower was taken as an average, or as an Optical
             Modulation Amplitude (OMA).";
          smiv2:max-access "read-only";
          smiv2:oid "1.3.6.1.4.1.6527.3.1.2.2.4.31.1.26";
        }
        leaf tmnxDDMAux1 {
          type int32;
          description
            "The value of tmnxDDMAux1 indicates the Manufacturer specific
             Auxiliary 1 information of the XFP.";
          smiv2:max-access "read-only";
          smiv2:oid "1.3.6.1.4.1.6527.3.1.2.2.4.31.1.27";
        }
        leaf tmnxDDMAux1LowWarning {
          type int32;
          description
            "The value of tmnxDDMAux1LowWarning indicates the Manufacturer specific
             Auxiliary 1 low-warning threshold for the XFP.";
          smiv2:max-access "read-only";
          smiv2:oid "1.3.6.1.4.1.6527.3.1.2.2.4.31.1.28";
        }
        leaf tmnxDDMAux1LowAlarm {
          type int32;
          description
            "The value of tmnxDDMAux1LowAlarm indicates the Manufacturer specific
             Auxiliary 1 low-alarm threshold for the XFP.";
          smiv2:max-access "read-only";
          smiv2:oid "1.3.6.1.4.1.6527.3.1.2.2.4.31.1.29";
        }
        leaf tmnxDDMAux1HiWarning {
          type int32;
          description
            "The value of tmnxDDMAux1HiWarning indicates the Manufacturer specific
             Auxiliary 1 hi-warning threshold for the XFP.";
          smiv2:max-access "read-only";
          smiv2:oid "1.3.6.1.4.1.6527.3.1.2.2.4.31.1.30";
        }
        leaf tmnxDDMAux1HiAlarm {
          type int32;
          description
            "The value of tmnxDDMAux1HiAlarm indicates the Manufacturer specific
             Auxiliary 1 hi-alarm threshold for the XFP.";
          smiv2:max-access "read-only";
          smiv2:oid "1.3.6.1.4.1.6527.3.1.2.2.4.31.1.31";
        }
        leaf tmnxDDMAux1Type {
          type enumeration {
            enum "none" {
              value 0;
            }
            enum "adp-bias-voltage" {
              value 1;
            }
            enum "reserved-2" {
              value 2;
            }
            enum "tec-current" {
              value 3;
            }
            enum "laser-temp" {
              value 4;
            }
            enum "laser-wavelength" {
              value 5;
            }
            enum "voltage-50" {
              value 6;
            }
            enum "voltage-33" {
              value 7;
            }
            enum "voltage-18" {
              value 8;
            }
            enum "voltage-52" {
              value 9;
            }
            enum "current-50" {
              value 10;
            }
            enum "reserved-11" {
              value 11;
            }
            enum "reserved-12" {
              value 12;
            }
            enum "current-33" {
              value 13;
            }
            enum "current-18" {
              value 14;
            }
            enum "current-52" {
              value 15;
            }
          }
          description
            "The value of tmnxDDMAux1Type indicates the measurement type of
             the Manufacturer specific Auxiliary 1 information of the XFP:
                none             (0)  - not specified.
                adp-bias-voltage (1)  - LSB is 10mV.
                reserved-2       (2)  - reserved for future use.
                tec-current      (3)  - LSB is 100uA.
                laser-temp       (4)  - degrees Celsius(C).
                laser-wavelength (5)  - LSB is 0.05 nm.
                voltage-50       (6)  - 5.0 supply voltage, LSB=100uV.
                voltage-33       (7)  - 3.3 supply voltage, LSB=100uV.
                voltage-18       (8)  - 1.8 supply voltage, LSB=100uV,
                voltage-52       (9)  - -5.2 supply voltage, LSB=100uV.
                current-50      (10)  - 5.0V supply current, LSB=100uA.
                reserved-11     (11)  - reserved for future use.
                reserved-12     (12)  - reserved for future use.
                current-33      (13)  - 3.3V supply current, LSB=100uA.
                current-18      (14)  - 1.8V supply current, LSB=100uA.
                current-52      (15)  - -5.2V supply current, LSB=100uA.";
          smiv2:max-access "read-only";
          smiv2:oid "1.3.6.1.4.1.6527.3.1.2.2.4.31.1.32";
        }
        leaf tmnxDDMAux2 {
          type int32;
          description
            "The value of tmnxDDMAux2 indicates the Manufacturer specific
             Auxiliary 2 information of the SFF.";
          smiv2:max-access "read-only";
          smiv2:oid "1.3.6.1.4.1.6527.3.1.2.2.4.31.1.33";
        }
        leaf tmnxDDMAux2LowWarning {
          type int32;
          description
            "The value of tmnxDDMAux2LowWarning indicates the Manufacturer specific
             Auxiliary 2 low-warning threshold for the XFP.";
          smiv2:max-access "read-only";
          smiv2:oid "1.3.6.1.4.1.6527.3.1.2.2.4.31.1.34";
        }
        leaf tmnxDDMAux2LowAlarm {
          type int32;
          description
            "The value of tmnxDDMAux2LowAlarm indicates the Manufacturer specific
             Auxiliary 2 low-alarm threshold for the XFP.";
          smiv2:max-access "read-only";
          smiv2:oid "1.3.6.1.4.1.6527.3.1.2.2.4.31.1.35";
        }
        leaf tmnxDDMAux2HiWarning {
          type int32;
          description
            "The value of tmnxDDMAux2HiWarning indicates the Manufacturer specific
             Auxiliary 2 hi-warning threshold for the XFP.";
          smiv2:max-access "read-only";
          smiv2:oid "1.3.6.1.4.1.6527.3.1.2.2.4.31.1.36";
        }
        leaf tmnxDDMAux2HiAlarm {
          type int32;
          description
            "The value of tmnxDDMAux2HiAlarm indicates the Manufacturer specific
             Auxiliary 2 hi-alarm threshold for the XFP.";
          smiv2:max-access "read-only";
          smiv2:oid "1.3.6.1.4.1.6527.3.1.2.2.4.31.1.37";
        }
        leaf tmnxDDMAux2Type {
          type enumeration {
            enum "none" {
              value 0;
            }
            enum "adp-bias-voltage" {
              value 1;
            }
            enum "reserved-2" {
              value 2;
            }
            enum "tec-current" {
              value 3;
            }
            enum "laser-temp" {
              value 4;
            }
            enum "laser-wavelength" {
              value 5;
            }
            enum "voltage-50" {
              value 6;
            }
            enum "voltage-33" {
              value 7;
            }
            enum "voltage-18" {
              value 8;
            }
            enum "voltage-52" {
              value 9;
            }
            enum "current-50" {
              value 10;
            }
            enum "reserved-11" {
              value 11;
            }
            enum "reserved-12" {
              value 12;
            }
            enum "current-33" {
              value 13;
            }
            enum "current-18" {
              value 14;
            }
            enum "current-52" {
              value 15;
            }
          }
          description
            "The value of tmnxDDMAux2Type indicates the measurement type of
             the Manufacturer specific Auxiliary 2 information of the XFP:
                none             (0)  - not specified.
                adp-bias-voltage (1)  - LSB is 10mV.
                reserved-2       (2)  - reserved for future use.
                tec-current      (3)  - LSB is 100uA.
                laser-temp       (4)  - degrees Celsius(C).
                laser-wavelength (5)  - LSB is 0.05 nm.
                voltage-50       (6)  - 5.0 supply voltage, LSB=100uV.
                voltage-33       (7)  - 3.3 supply voltage, LSB=100uV.
                voltage-18       (8)  - 1.8 supply voltage, LSB=100uV,
                voltage-52       (9)  - -5.2 supply voltage, LSB=100uV.
                current-50      (10)  - 5.0V supply current, LSB=100uA.
                reserved-11     (11)  - reserved for future use.
                reserved-12     (12)  - reserved for future use.
                current-33      (13)  - 3.3V supply current, LSB=100uA.
                current-18      (14)  - 1.8V supply current, LSB=100uA.
                current-52      (15)  - -5.2V supply current, LSB=100uA.";
          smiv2:max-access "read-only";
          smiv2:oid "1.3.6.1.4.1.6527.3.1.2.2.4.31.1.38";
        }
        leaf tmnxDDMFailedThresholds {
          type timetra-port:TmnxDigitalDiagnosticFailureBits;
          description
            "The value of tmnxDDMFailedThresholds indicates which objects
             of the monitored SFF is in a failed or cleared threshold state.
             A set bit indicates that the specified threshold has been exceeded.";
          smiv2:max-access "read-only";
          smiv2:oid "1.3.6.1.4.1.6527.3.1.2.2.4.31.1.39";
        }
        leaf tmnxDDMExternallyCalibrated {
          type boolean;
          description
            "The value of tmnxDDMExternallyCalibrated indicates whether the
             SFF was externally calibrated (true) or internally calibrated (false).";
          smiv2:max-access "read-only";
          smiv2:oid "1.3.6.1.4.1.6527.3.1.2.2.4.31.1.40";
        }
        leaf tmnxDDMExtCalRxPower4 {
          type uint32;
          description
            "The value of tmnxDDMExtCalRxPower4 indicates the Rx_PWR(4)
             value as specified in Table 3.16 in the SFF Committee Standard's
             document SFF-8472 Rev 10.2.";
          reference "SFF-8472 Rev 10.2";
          smiv2:max-access "read-only";
          smiv2:oid "1.3.6.1.4.1.6527.3.1.2.2.4.31.1.41";
        }
        leaf tmnxDDMExtCalRxPower3 {
          type uint32;
          description
            "The value of tmnxDDMExtCalRxPower3 indicates the Rx_PWR(3)
             value as specified in Table 3.16 in the SFF Committee Standard's
             document SFF-8462 Rev 10.2.";
          reference "SFF-8472 Rev 10.2";
          smiv2:max-access "read-only";
          smiv2:oid "1.3.6.1.4.1.6527.3.1.2.2.4.31.1.42";
        }
        leaf tmnxDDMExtCalRxPower2 {
          type uint32;
          description
            "The value of tmnxDDMExtCalRxPower2 indicates the Rx_PWR(2)
             value as specified in Table 3.16 in the SFF Committee Standard's
             document SFF-8472 Rev 10.2.";
          reference "SFF-8472 Rev 10.2";
          smiv2:max-access "read-only";
          smiv2:oid "1.3.6.1.4.1.6527.3.1.2.2.4.31.1.43";
        }
        leaf tmnxDDMExtCalRxPower1 {
          type uint32;
          description
            "The value of tmnxDDMExtCalRxPower1 indicates the Rx_PWR(1)
             value as specified in Table 3.16 in the SFF Committee Standard's
             document SFF-8472 Rev 10.2.";
          reference "SFF-8472 Rev 10.2";
          smiv2:max-access "read-only";
          smiv2:oid "1.3.6.1.4.1.6527.3.1.2.2.4.31.1.44";
        }
        leaf tmnxDDMExtCalRxPower0 {
          type uint32;
          description
            "The value of tmnxDDMExtCalRxPower0 indicates the Rx_PWR(0)
             value as specified in Table 3.16 in the SFF Committee Standard's
             document SFF-8472 Rev 10.2.";
          reference "SFF-8472 Rev 10.2";
          smiv2:max-access "read-only";
          smiv2:oid "1.3.6.1.4.1.6527.3.1.2.2.4.31.1.45";
        }
        leaf tmnxDDMExtCalTxLaserBiasSlope {
          type uint32 {
            range "0..65535";
          }
          description
            "The value of tmnxDDMExtCalTxLaserBiasSlope indicates the
             Tx_l(Slope) value as specified in Table 3.16 in the SFF
             Committee Standard's document SFF-8472 Rev 10.2.";
          reference "SFF-8472 Rev 10.2";
          smiv2:max-access "read-only";
          smiv2:oid "1.3.6.1.4.1.6527.3.1.2.2.4.31.1.46";
        }
        leaf tmnxDDMExtCalTxLaserBiasOffset {
          type int32 {
            range "-32767..32768";
          }
          description
            "The value of tmnxDDMExtCalTxLaserBiasOffset indicates the
             Tx_l(Offset) value as specified in Table 3.16 in the SFF
             Committee Standard's document SFF-8472 Rev 10.2.";
          reference "SFF-8472 Rev 10.2";
          smiv2:max-access "read-only";
          smiv2:oid "1.3.6.1.4.1.6527.3.1.2.2.4.31.1.47";
        }
        leaf tmnxDDMExtCalTxPowerSlope {
          type uint32 {
            range "0..65535";
          }
          description
            "The value of tmnxDDMExtCalTxPowerSlope indicates the
             Tx_PWR(Slope) value as specified in Table 3.16 in the
             SFF Committee Standard's document SFF-8472 Rev 10.2.";
          reference "SFF-8472 Rev 10.2";
          smiv2:max-access "read-only";
          smiv2:oid "1.3.6.1.4.1.6527.3.1.2.2.4.31.1.48";
        }
        leaf tmnxDDMExtCalTxPowerOffset {
          type int32 {
            range "-32767..32768";
          }
          description
            "The value of tmnxDDMExtCalTxPowerOffset indicates the
             Tx_PWR(Offset) value as specified in Table 3.16 in the
             SFF Committee Standard's document SFF-8472 Rev 10.2.";
          reference "SFF-8472 Rev 10.2";
          smiv2:max-access "read-only";
          smiv2:oid "1.3.6.1.4.1.6527.3.1.2.2.4.31.1.49";
        }
        leaf tmnxDDMExtCalTemperatureSlope {
          type uint32 {
            range "0..65535";
          }
          description
            "The value of tmnxDDMExtCalTemperatureSlope indicates the
             T(Slope) value as specified in Table 3.16 in the SFF
             Committee Standard's document SFF-8472 Rev 10.2.";
          reference "SFF-8472 Rev 10.2";
          smiv2:max-access "read-only";
          smiv2:oid "1.3.6.1.4.1.6527.3.1.2.2.4.31.1.50";
        }
        leaf tmnxDDMExtCalTemperatureOffset {
          type int32 {
            range "-32767..32768";
          }
          description
            "The value of tmnxDDMExtCalTemperatureOffset indicates the
             T(Offset) value as specified in Table 3.16 in the SFF
             Committee Standard's document SFF-8472 Rev 10.2.";
          reference "SFF-8472 Rev 10.2";
          smiv2:max-access "read-only";
          smiv2:oid "1.3.6.1.4.1.6527.3.1.2.2.4.31.1.51";
        }
        leaf tmnxDDMExtCalVoltageSlope {
          type uint32 {
            range "0..65535";
          }
          description
            "The value of tmnxDDMExtCalVoltageSlope indicates the V(Slope)
             value as specified in Table 3.16 in the SFF Committee Standard's
             document SFF-8472 Rev 10.2.";
          reference "SFF-8472 Rev 10.2";
          smiv2:max-access "read-only";
          smiv2:oid "1.3.6.1.4.1.6527.3.1.2.2.4.31.1.52";
        }
        leaf tmnxDDMExtCalVoltageOffset {
          type int32 {
            range "-32767..32768";
          }
          description
            "The value of tmnxDDMExtCalVoltageOffset indicates the V(Slope)
             value as specified in Table 3.16 in the SFF Committee Standard's
             document SFF-8472 Rev 10.2.";
          reference "SFF-8472 Rev 10.2";
          smiv2:max-access "read-only";
          smiv2:oid "1.3.6.1.4.1.6527.3.1.2.2.4.31.1.53";
        }
      }
      config false;
    }
    container tPortAccIngQGrpTable {
      description
        "The value of tPortAccIngQGrpTable defines access Ingress Queue Group
         Table for providing, via SNMP, the capability of defining the port
         specific queue groups from the queue-groups existing in the
         TIMETRA-QOS-MIB::tQosIngQGroupTable.";
      smiv2:oid "1.3.6.1.4.1.6527.3.1.2.2.4.33";
      list tPortAccIngQGrpEntry {
        key "tmnxChassisIndex tmnxPortPortID tPortAccIngQGrpName";
        description
          "The value of tPortAccIngQGrpEntry defines an entry in the
           tPortAccIngQGrpTable.
           
           Entries are created/deleted in this table by SNMP sets to
           tPortAccIngQGrpRowStatus.";
        smiv2:oid "1.3.6.1.4.1.6527.3.1.2.2.4.33.1";
        leaf tmnxChassisIndex {
          type leafref {
            path "/timetra-chassis:TIMETRA-CHASSIS-MIB/timetra-chassis:tmnxChassisTable/timetra-chassis:tmnxChassisEntry/timetra-chassis:tmnxChassisIndex";
          }
          config true;
        }
        leaf tmnxPortPortID {
          type leafref {
            path "/timetra-port:TIMETRA-PORT-MIB/timetra-port:tmnxPortTable/timetra-port:tmnxPortEntry/timetra-port:tmnxPortPortID";
          }
          config true;
        }
        leaf tPortAccIngQGrpName {
          type timetra-tc:TNamedItem;
          description
            "The value of tPortAccIngQGrpName defines the port Ingress
             Queue Group name.  It uniquely identifies a port ingress queue group
             in the managed system.";
          smiv2:max-access "not-accessible";
          smiv2:oid "1.3.6.1.4.1.6527.3.1.2.2.4.33.1.1";
          config true;
        }
        leaf tPortAccIngQGrpRowStatus {
          type snmpv2-tc:RowStatus;
          description
            "The value of tPortAccIngQGrpRowStatus allows entries to be
             created and deleted in the tPortAccIngQGrpTable.
             
             The creation of an entry in this table will succeed only if the
             queue-group being created exists in
             TIMETRA-QOS-MIB::tQosIngQGroupTable.";
          reference
            "See definition of RowStatus in RFC 2579, 'Textual Conventions for
             SMIv2.'";
          smiv2:max-access "read-write";
          smiv2:oid "1.3.6.1.4.1.6527.3.1.2.2.4.33.1.2";
          config false;
        }
        leaf tPortAccIngQGrpLastChgd {
          type yang:timestamp;
          description
            "The value of tPortAccIngQGrpLastChgd indicates the value of
             sysUpTime when the queue entry was last modified.";
          smiv2:max-access "read-only";
          smiv2:oid "1.3.6.1.4.1.6527.3.1.2.2.4.33.1.3";
          config false;
        }
        leaf tPortAccIngQGrpSchedPol {
          type timetra-tc:TNamedItemOrEmpty;
          description
            "The value of tPortAccIngQGrpSchedPol specifies the name of
             the scheduler-policy to be used with this port ingress queue-group.";
          smiv2:defval "";
          smiv2:max-access "read-write";
          smiv2:oid "1.3.6.1.4.1.6527.3.1.2.2.4.33.1.4";
          config true;
        }
        leaf tPortAccIngQGrpAcctgPolId {
          type uint32 {
            range "0..99";
          }
          description
            "The value of tPortAccIngQGrpAcctgPolId specifies the accounting-policy
             to be used with this port ingress queue-group.
             
             A non-zero value indicates the tmnxLogApPolicyId index identifying the
             policy entry in the tmnxLogApTable from the TIMETRA-LOG-MIB which is
             associated with this queue-group.
             
             The value zero indicates that the agent should use the default
             accounting policy, if one exists.";
          smiv2:defval "0";
          smiv2:max-access "read-write";
          smiv2:oid "1.3.6.1.4.1.6527.3.1.2.2.4.33.1.5";
          config true;
        }
        leaf tPortAccIngQGrpCollectStats {
          type boolean;
          description
            "The value of tPortAccIngQGrpCollectStats specifies whether
             statistics should be collected on this port ingress queue-group.";
          smiv2:defval "false";
          smiv2:max-access "read-write";
          smiv2:oid "1.3.6.1.4.1.6527.3.1.2.2.4.33.1.6";
          config true;
        }
        leaf tPortAccIngQGrpDescr {
          type timetra-tc:TItemDescription;
          description
            "The value of tPortAccIngQGrpDescr specifies the description for
             this port queue-group.";
          smiv2:defval "";
          smiv2:max-access "read-write";
          smiv2:oid "1.3.6.1.4.1.6527.3.1.2.2.4.33.1.7";
          config true;
        }
        config true;
      }
      config true;
    }
    container tPortAccIngQOverTable {
      description
        "The tPortAccIngQOverTable has an entry for each access port queue
         override configured on this system.";
      smiv2:oid "1.3.6.1.4.1.6527.3.1.2.2.4.35";
      list tPortAccIngQOverEntry {
        key "tmnxChassisIndex tmnxPortPortID tPortAccIngQGrpName tPortAccIngQOverQueue";
        description
          "Each row represents a particular port-queue override. Entries are
           created and deleted by the user.";
        smiv2:oid "1.3.6.1.4.1.6527.3.1.2.2.4.35.1";
        leaf tmnxChassisIndex {
          type leafref {
            path "/timetra-chassis:TIMETRA-CHASSIS-MIB/timetra-chassis:tmnxChassisTable/timetra-chassis:tmnxChassisEntry/timetra-chassis:tmnxChassisIndex";
          }
          config true;
        }
        leaf tmnxPortPortID {
          type leafref {
            path "/timetra-port:TIMETRA-PORT-MIB/timetra-port:tmnxPortTable/timetra-port:tmnxPortEntry/timetra-port:tmnxPortPortID";
          }
          config true;
        }
        leaf tPortAccIngQGrpName {
          type leafref {
            path "/timetra-port:TIMETRA-PORT-MIB/timetra-port:tPortAccIngQGrpTable/timetra-port:tPortAccIngQGrpEntry/timetra-port:tPortAccIngQGrpName";
          }
          config true;
        }
        leaf tPortAccIngQOverQueue {
          type timetra-tc:TIngressQueueId {
            range "1..32";
          }
          description
            "The value of tPortAccIngQOverQueue specifies the queue ID
             which is used as the fourth index to the table entry.";
          smiv2:max-access "not-accessible";
          smiv2:oid "1.3.6.1.4.1.6527.3.1.2.2.4.35.1.1";
          config true;
        }
        leaf tPortAccIngQOverRowStatus {
          type snmpv2-tc:RowStatus;
          description
            "The value of tPortAccIngQOverRowStatus is used for the creation
             and deletion of port-queue overrides.
             
             Row creation will fail if there is no entry in the
             TIMETRA-QOS-MIB::tQosIngQueueTable with the same index values as the
             last two indices of this table
             (tPortAccIngQGrpName.tPortAccIngQOverQueue).";
          smiv2:max-access "read-write";
          smiv2:oid "1.3.6.1.4.1.6527.3.1.2.2.4.35.1.2";
          config false;
        }
        leaf tPortAccIngQOverLastChanged {
          type yang:timestamp;
          description
            "The value of tPortAccIngQOverLastChanged indicates the value
             of sysUpTime at the time of the most recent management change to
             this row.";
          smiv2:max-access "read-only";
          smiv2:oid "1.3.6.1.4.1.6527.3.1.2.2.4.35.1.3";
          config false;
        }
        leaf tPortAccIngQOverCBS {
          type timetra-tc:TBurstSizeOverride;
          units "kilo-bytes";
          description
            "The value of tPortAccIngQOverCBS specifies the amount of reserved
             buffer space for the queue.";
          smiv2:defval "-2";
          smiv2:max-access "read-write";
          smiv2:oid "1.3.6.1.4.1.6527.3.1.2.2.4.35.1.4";
          config true;
        }
        leaf tPortAccIngQOverMBS {
          type timetra-tc:TBurstSizeOverride;
          units "kilo-bytes";
          status obsolete;
          description
            "The value of tPortAccIngQOverMBS specifies the maximum amount of
             buffer space allowed for the queue.
             
             This object is replaced with tPortAccIngQOverMBSBytes object.";
          smiv2:defval "-2";
          smiv2:max-access "read-write";
          smiv2:oid "1.3.6.1.4.1.6527.3.1.2.2.4.35.1.5";
          config true;
        }
        leaf tPortAccIngQOverHiPrioOnly {
          type timetra-tc:TBurstPercentOrDefaultOverride;
          description
            "The value of tPortAccIngQOverHiPrioOnly specifies the percentage of
             buffer space for the queue, used exclusively by high priority packets.";
          smiv2:defval "-2";
          smiv2:max-access "read-write";
          smiv2:oid "1.3.6.1.4.1.6527.3.1.2.2.4.35.1.6";
          config true;
        }
        leaf tPortAccIngQOverAdminPIR {
          type timetra-tc:TPIRRateOverride;
          units "kbps";
          description
            "The value of tPortAccIngQOverAdminPIR specifies the administrative
             PIR specified by the user.";
          smiv2:defval "-2";
          smiv2:max-access "read-write";
          smiv2:oid "1.3.6.1.4.1.6527.3.1.2.2.4.35.1.7";
          config true;
        }
        leaf tPortAccIngQOverAdminCIR {
          type timetra-tc:TCIRRateOverride;
          units "kbps";
          description
            "The value of tPortAccIngQOverAdminCIR specifies the administrative
             CIR specified by the user.";
          smiv2:defval "-2";
          smiv2:max-access "read-write";
          smiv2:oid "1.3.6.1.4.1.6527.3.1.2.2.4.35.1.8";
          config true;
        }
        leaf tPortAccIngQOverPIRAdaptation {
          type timetra-tc:TAdaptationRuleOverride;
          description
            "The value of tPortAccIngQOverPIRAdaptation specifies the adaptation
             rule to be used while computing the operational PIR
             value. The adaptation rule specifies the rules to compute the
             operational values while maintaining minimum offset.";
          smiv2:defval "noOverride";
          smiv2:max-access "read-write";
          smiv2:oid "1.3.6.1.4.1.6527.3.1.2.2.4.35.1.9";
          config true;
        }
        leaf tPortAccIngQOverCIRAdaptation {
          type timetra-tc:TAdaptationRuleOverride;
          description
            "The value of tPortAccIngQOverCIRAdaptation specifies the adaptation
             rule to be used while computing the operational CIR
             value. The adaptation rule specifies the rules to compute the
             operational values while maintaining minimum offset.";
          smiv2:defval "noOverride";
          smiv2:max-access "read-write";
          smiv2:oid "1.3.6.1.4.1.6527.3.1.2.2.4.35.1.10";
          config true;
        }
        leaf tPortAccIngQOverMBSBytes {
          type timetra-tc:TBurstSizeBytesOverride;
          units "bytes";
          description
            "The value of tPortAccIngQOverMBSBytes specifies the maximum amount of
             buffer space allowed for the queue.";
          smiv2:defval "-2";
          smiv2:max-access "read-write";
          smiv2:oid "1.3.6.1.4.1.6527.3.1.2.2.4.35.1.11";
          config true;
        }
        config true;
      }
      config true;
    }
    container tPortAccEgrQGrpTable {
      description
        "The value of tPortAccEgrQGrpTable defines access Egress Queue Group
         Table for providing, via SNMP, the capability of defining the port
         specific queue groups from the queue-groups existing in the
         TIMETRA-QOS-MIB::tQosEgrQGroupTable.";
      smiv2:oid "1.3.6.1.4.1.6527.3.1.2.2.4.37";
      list tPortAccEgrQGrpEntry {
        key "tmnxChassisIndex tmnxPortPortID tPortAccEgrQGrpName tPortAccEgrQGrpInstanceId";
        description
          "The value of tPortAccEgrQGrpEntry defines an entry in the
           tPortAccEgrQGrpTable.
           
           Entries are created/deleted in this table by SNMP sets to
           tPortAccEgrQGrpRowStatus.";
        smiv2:oid "1.3.6.1.4.1.6527.3.1.2.2.4.37.1";
        leaf tmnxChassisIndex {
          type leafref {
            path "/timetra-chassis:TIMETRA-CHASSIS-MIB/timetra-chassis:tmnxChassisTable/timetra-chassis:tmnxChassisEntry/timetra-chassis:tmnxChassisIndex";
          }
          config true;
        }
        leaf tmnxPortPortID {
          type leafref {
            path "/timetra-port:TIMETRA-PORT-MIB/timetra-port:tmnxPortTable/timetra-port:tmnxPortEntry/timetra-port:tmnxPortPortID";
          }
          config true;
        }
        leaf tPortAccEgrQGrpName {
          type timetra-tc:TNamedItem;
          description
            "The value of tPortAccEgrQGrpName defines the port Egress Queue
             Group name.  It, along with tPortAccEgrQGrpInstanceId, uniquely 
             identifies a port egress queue group in the managed system.";
          smiv2:max-access "not-accessible";
          smiv2:oid "1.3.6.1.4.1.6527.3.1.2.2.4.37.1.1";
          config true;
        }
        leaf tPortAccEgrQGrpRowStatus {
          type snmpv2-tc:RowStatus;
          description
            "The value of tPortAccEgrQGrpRowStatus allows entries to be
             created and deleted in the tPortAccEgrQGrpTable.
             
             The creation of an entry in this table will succeed only if the
             queue-group being created exist in TIMETRA-QOS-MIB::tQosEgrQGroupTable.";
          reference
            "See definition of RowStatus in RFC 2579, 'Textual Conventions for
             SMIv2.'";
          smiv2:max-access "read-write";
          smiv2:oid "1.3.6.1.4.1.6527.3.1.2.2.4.37.1.2";
          config false;
        }
        leaf tPortAccEgrQGrpLastChgd {
          type yang:timestamp;
          description
            "The value of tPortAccEgrQGrpLastChgd indicates the value of
             sysUpTime when the queue entry was last modified.";
          smiv2:max-access "read-only";
          smiv2:oid "1.3.6.1.4.1.6527.3.1.2.2.4.37.1.3";
          config false;
        }
        leaf tPortAccEgrQGrpSchedPol {
          type timetra-tc:TNamedItemOrEmpty;
          description
            "The value of tPortAccEgrQGrpSchedPol specifies the name of the
             scheduler-policy to be used with this port egress queue-group.";
          smiv2:defval "";
          smiv2:max-access "read-write";
          smiv2:oid "1.3.6.1.4.1.6527.3.1.2.2.4.37.1.4";
          config true;
        }
        leaf tPortAccEgrQGrpAggRateLimit {
          type timetra-tc:TPortSchedulerAggRateLimitPIR;
          units "kbps";
          description
            "The value of tPortAccEgrQGrpAggRateLimit specifies the maximum
             total rate of all egress queues in this queue-group. The
             value '-1' means that there is no limit.";
          smiv2:defval "-1";
          smiv2:max-access "read-write";
          smiv2:oid "1.3.6.1.4.1.6527.3.1.2.2.4.37.1.5";
          config true;
        }
        leaf tPortAccEgrQGrpAcctgPolId {
          type uint32 {
            range "0..99";
          }
          description
            "The value of tPortAccEgrQGrpAcctgPolId specifies the accounting-policy
             to be used with this port egress queue-group.
             
             A non-zero value indicates the tmnxLogApPolicyId index identifying the
             policy entry in the tmnxLogApTable from the TIMETRA-LOG-MIB which is
             associated with this queue-group.
             
             The value zero indicates that the agent should use the default
             accounting policy, if one exists.";
          smiv2:defval "0";
          smiv2:max-access "read-write";
          smiv2:oid "1.3.6.1.4.1.6527.3.1.2.2.4.37.1.6";
          config true;
        }
        leaf tPortAccEgrQGrpCollectStats {
          type boolean;
          description
            "The value of tPortAccEgrQGrpCollectStats specifies whether
             statistics should be collected on this port egress queue-group.";
          smiv2:defval "false";
          smiv2:max-access "read-write";
          smiv2:oid "1.3.6.1.4.1.6527.3.1.2.2.4.37.1.7";
          config true;
        }
        leaf tPortAccEgrQGrpFrameBaseActg {
          type boolean;
          description
            "The value of tPortAccEgrQGrpFrameBaseActg specifies whether
             to use frame-based accounting for this port egress queue-group.
             
             If the value is 'false', the default packet-based accounting
             method will be used.";
          smiv2:defval "false";
          smiv2:max-access "read-write";
          smiv2:oid "1.3.6.1.4.1.6527.3.1.2.2.4.37.1.8";
          config true;
        }
        leaf tPortAccEgrQGrpDescr {
          type timetra-tc:TItemDescription;
          description
            "The value of tPortAccEgrQGrpDescr specifies the description for
             this port queue-group.";
          smiv2:defval "";
          smiv2:max-access "read-write";
          smiv2:oid "1.3.6.1.4.1.6527.3.1.2.2.4.37.1.9";
          config true;
        }
        leaf tPortAccEgrQGrpInstanceId {
          type uint32 {
            range "1..65535";
          }
          description
            "The value of tPortAccEgrQGrpInstanceId defines the unique instance of
             the port access egress Queue Group.  It, along with tPortAccEgrQGrpName, 
             uniquely identifies a port access egress queue group in the 
             managed system.";
          smiv2:max-access "not-accessible";
          smiv2:oid "1.3.6.1.4.1.6527.3.1.2.2.4.37.1.10";
          config true;
        }
        leaf tPortAccEgrQGrpHsmdaShaperOvr {
          type timetra-tc:TNamedItemOrEmpty;
          description
            "The value of tPortAccEgrQGrpHsmdaShaperOvr specifies the name of 
             the secondary shaper for this queue-group instance. This value must 
             correspond to an entry in the tmnxPortEgrShaperTable. If an empty 
             string is specified, default secondary shaper will be used.";
          smiv2:defval "";
          smiv2:max-access "read-write";
          smiv2:oid "1.3.6.1.4.1.6527.3.1.2.2.4.37.1.11";
          config true;
        }
        leaf tPortAccEgrQGrpHsmdaPktOffOvr {
          type timetra-tc:TEgrHsmdaPerPacketOffsetOvr;
          units "bytes";
          description
            "The value of tPortAccEgrQGrpHsmdaPktOffOvr specifies the adjustment
             made to the size of each packet for HSMDA queue accounting for this 
             queue-group instance.";
          smiv2:defval "-128";
          smiv2:max-access "read-write";
          smiv2:oid "1.3.6.1.4.1.6527.3.1.2.2.4.37.1.12";
          config true;
        }
        leaf tPortAccEgrQGrpHsmdaWrrPolicyOvr {
          type timetra-tc:TNamedItemOrEmpty;
          description
            "The value of tPortAccEgrQGrpHsmdaWrrPolicyOvr specifies the egress
             hsmda weighted round-robin policy override for this queue group 
             instance. 
             
             When no policy is given, the hsmda weighted round-robin policy
             specified in the queue-group template is honored. When a valid policy
             is given, it overrides the hsmda weighted round-robin policy given in
             the egress queue group template.";
          smiv2:defval "";
          smiv2:max-access "read-write";
          smiv2:oid "1.3.6.1.4.1.6527.3.1.2.2.4.37.1.13";
          config true;
        }
        config true;
      }
      config true;
    }
    container tPortAccEgrQOverTable {
      description
        "The tPortAccEgrQOverTable has an entry for each access port queue
         override configured on this system.";
      smiv2:oid "1.3.6.1.4.1.6527.3.1.2.2.4.39";
      list tPortAccEgrQOverEntry {
        key "tmnxChassisIndex tmnxPortPortID tPortAccEgrQGrpName tPortAccEgrQGrpInstanceId tPortAccEgrQOverQueue";
        description
          "Each row represents a particular port-queue override. Entries
           are created and deleted by the user.";
        smiv2:oid "1.3.6.1.4.1.6527.3.1.2.2.4.39.1";
        leaf tmnxChassisIndex {
          type leafref {
            path "/timetra-chassis:TIMETRA-CHASSIS-MIB/timetra-chassis:tmnxChassisTable/timetra-chassis:tmnxChassisEntry/timetra-chassis:tmnxChassisIndex";
          }
          config true;
        }
        leaf tmnxPortPortID {
          type leafref {
            path "/timetra-port:TIMETRA-PORT-MIB/timetra-port:tmnxPortTable/timetra-port:tmnxPortEntry/timetra-port:tmnxPortPortID";
          }
          config true;
        }
        leaf tPortAccEgrQGrpName {
          type leafref {
            path "/timetra-port:TIMETRA-PORT-MIB/timetra-port:tPortAccEgrQGrpTable/timetra-port:tPortAccEgrQGrpEntry/timetra-port:tPortAccEgrQGrpName";
          }
          config true;
        }
        leaf tPortAccEgrQGrpInstanceId {
          type leafref {
            path "/timetra-port:TIMETRA-PORT-MIB/timetra-port:tPortAccEgrQGrpTable/timetra-port:tPortAccEgrQGrpEntry/timetra-port:tPortAccEgrQGrpInstanceId";
          }
          config true;
        }
        leaf tPortAccEgrQOverQueue {
          type timetra-tc:TEgressQueueId {
            range "1..8";
          }
          description
            "The value of tPortAccEgrQOverQueue specifies the queue ID which is
             used as the fourth index to the table entry.";
          smiv2:max-access "not-accessible";
          smiv2:oid "1.3.6.1.4.1.6527.3.1.2.2.4.39.1.1";
          config true;
        }
        leaf tPortAccEgrQOverRowStatus {
          type snmpv2-tc:RowStatus;
          description
            "The value of tPortAccEgrQOverRowStatus is used for the
             creation and deletion of port-queue overrides.
             
             Row creation will fail if there is no entry in the
             TIMETRA-QOS-MIB::tQosEgrQueueTable with the same index values as the
             last two indices of this table
             (tPortAccEgrQGrpName.tPortAccEgrQOverQueue).";
          smiv2:max-access "read-write";
          smiv2:oid "1.3.6.1.4.1.6527.3.1.2.2.4.39.1.2";
          config false;
        }
        leaf tPortAccEgrQOverLastChanged {
          type yang:timestamp;
          description
            "The value of tPortAccEgrQOverLastChanged indicates the value
             of sysUpTime at the time of the most recent management change to
             this row.";
          smiv2:max-access "read-only";
          smiv2:oid "1.3.6.1.4.1.6527.3.1.2.2.4.39.1.3";
          config false;
        }
        leaf tPortAccEgrQOverCBS {
          type timetra-tc:TBurstSizeOverride;
          units "kilo-bytes";
          description
            "The value of tPortAccEgrQOverCBS specifies the amount of reserved
             buffer space for the queue.";
          smiv2:defval "-2";
          smiv2:max-access "read-write";
          smiv2:oid "1.3.6.1.4.1.6527.3.1.2.2.4.39.1.4";
          config true;
        }
        leaf tPortAccEgrQOverMBS {
          type timetra-tc:TBurstSizeOverride;
          units "kilo-bytes";
          status obsolete;
          description
            "The value of tPortAccEgrQOverMBS specifies the maximum amount of
             buffer space allowed for the queue.
             
             This object is replaced with tPortAccEgrQOverMBSBytes object.";
          smiv2:defval "-2";
          smiv2:max-access "read-write";
          smiv2:oid "1.3.6.1.4.1.6527.3.1.2.2.4.39.1.5";
          config true;
        }
        leaf tPortAccEgrQOverHiPrioOnly {
          type timetra-tc:TBurstPercentOrDefaultOverride;
          description
            "The value of tPortAccEgrQOverHiPrioOnly specifies the percentage of
             buffer space for the queue, used exclusively by high priority packets.";
          smiv2:defval "-2";
          smiv2:max-access "read-write";
          smiv2:oid "1.3.6.1.4.1.6527.3.1.2.2.4.39.1.6";
          config true;
        }
        leaf tPortAccEgrQOverAdminPIR {
          type timetra-tc:TPIRRateOverride;
          units "kbps";
          description
            "The value of tPortAccEgrQOverAdminPIR specifies the administrative
             PIR specified by the user.
             
             An 'inconsistentValue' error is returned if tPortAccEgrQOverAdminPIR  
             is set to non-default value when the object tPortAccEgrQOverRateType is
             set to 'percent'.";
          smiv2:defval "-2";
          smiv2:max-access "read-write";
          smiv2:oid "1.3.6.1.4.1.6527.3.1.2.2.4.39.1.7";
          config true;
        }
        leaf tPortAccEgrQOverAdminCIR {
          type timetra-tc:TCIRRateOverride;
          units "kbps";
          description
            "The value of tPortAccEgrQOverAdminCIR specifies the administrative
             CIR specified by the user.
             
             An 'inconsistentValue' error is returned if tPortAccEgrQOverAdminCIR  
             is set to non-default value when the object tPortAccEgrQOverRateType is
             set to 'percent'.";
          smiv2:defval "-2";
          smiv2:max-access "read-write";
          smiv2:oid "1.3.6.1.4.1.6527.3.1.2.2.4.39.1.8";
          config true;
        }
        leaf tPortAccEgrQOverPIRAdaptation {
          type timetra-tc:TAdaptationRuleOverride;
          description
            "The value of tPortAccEgrQOverPIRAdaptation specifies the adaptation
             rule to be used while computing the operational PIR
             value. The adaptation rule specifies the rules to compute the
             operational values while maintaining minimum offset.";
          smiv2:defval "noOverride";
          smiv2:max-access "read-write";
          smiv2:oid "1.3.6.1.4.1.6527.3.1.2.2.4.39.1.9";
          config true;
        }
        leaf tPortAccEgrQOverCIRAdaptation {
          type timetra-tc:TAdaptationRuleOverride;
          description
            "The value of tPortAccEgrQOverCIRAdaptation specifies the adaptation
             rule to be used while computing the operational CIR
             value. The adaptation rule specifies the rules to compute the
             operational values while maintaining minimum offset.";
          smiv2:defval "noOverride";
          smiv2:max-access "read-write";
          smiv2:oid "1.3.6.1.4.1.6527.3.1.2.2.4.39.1.10";
          config true;
        }
        leaf tPortAccEgrQOverMBSBytes {
          type timetra-tc:TBurstSizeBytesOverride;
          units "bytes";
          description
            "The value of tPortAccEgrQOverMBSBytes specifies the maximum amount of
             buffer space allowed for the queue.";
          smiv2:defval "-2";
          smiv2:max-access "read-write";
          smiv2:oid "1.3.6.1.4.1.6527.3.1.2.2.4.39.1.11";
          config true;
        }
        leaf tPortAccEgrQOverAdminPIRPercent {
          type timetra-tc:TPIRPercentOverride;
          units "hundredths of a percent";
          description
            "The value of tPortAccEgrQOverAdminPIRPercent specifies the administrative
             PIR percentage, in hudredths of a percent.
             
             An 'inconsistentValue' error is returned if tPortAccEgrQOverAdminPIRPercent  
             is set to non-default value when the object tPortAccEgrQOverRateType is set 
             to 'kbps'.";
          smiv2:defval "-2";
          smiv2:max-access "read-write";
          smiv2:oid "1.3.6.1.4.1.6527.3.1.2.2.4.39.1.12";
          config true;
        }
        leaf tPortAccEgrQOverAdminCIRPercent {
          type timetra-tc:TCIRPercentOverride;
          units "hundredths of a percent";
          description
            "The value of tPortAccEgrQOverAdminCIRPercent specifies the administrative
             CIR percentage, in hudredths of a percent.
             
             An 'inconsistentValue' error is returned if tPortAccEgrQOverAdminCIRPercent  
             is set to non-default value when the object tPortAccEgrQOverRateType is set 
             to 'kbps'.";
          smiv2:defval "-2";
          smiv2:max-access "read-write";
          smiv2:oid "1.3.6.1.4.1.6527.3.1.2.2.4.39.1.13";
          config true;
        }
        leaf tPortAccEgrQOverRateType {
          type timetra-tc:TRateType;
          description
            "The value of tPortAccEgrQOverRateType specifies the type of Egress queue
             rate.
             
             When the value of the object is set to 'kbps', the egresss queue rates
             are specified in kbps. The objects  tPortAccEgrQOverAdminPIRPercent and
             tPortAccEgrQOverAdminCIRPercent will be set to their default values.
             
             When the value of the object is set to 'percent', the egress queue rates
             are specified in percentage. The objects tPortAccEgrQOverAdminPIR and 
             tPortAccEgrQOverAdminCIR will be set to their default values.";
          smiv2:defval "kbps";
          smiv2:max-access "read-write";
          smiv2:oid "1.3.6.1.4.1.6527.3.1.2.2.4.39.1.14";
          config true;
        }
        leaf tPortAccEgrQOverWeight {
          type timetra-tc:TWeightOverride;
          description
            "The value of tPortAccEgrQOverWeight specifies the weight that needs 
             to be used by the scheduler to which this queue would be feeding.";
          smiv2:defval "-2";
          smiv2:max-access "read-write";
          smiv2:oid "1.3.6.1.4.1.6527.3.1.2.2.4.39.1.15";
          config true;
        }
        leaf tPortAccEgrQOverCIRWeight {
          type timetra-tc:TWeightOverride;
          description
            "The value of tPortAccEgrQOverCIRWeight specifies the weight that 
             should be assigned to this queue by the parent scheduler among all the
             entities feeding into the parent, when the traffic is conforming to the 
             committed rate.
             
             A value of '0' specifies that the queue will not receive bandwidth for
             the 'within-cir' pass on its parent scheduler.";
          smiv2:defval "-2";
          smiv2:max-access "read-write";
          smiv2:oid "1.3.6.1.4.1.6527.3.1.2.2.4.39.1.16";
          config true;
        }
        config true;
      }
      config true;
    }
    container tPortNetEgrQGrpTable {
      description
        "The value of tPortNetEgrQGrpTable defines network Egress Queue Group
         Table for providing, via SNMP, the capability of defining the port
         specific queue groups from the queue-groups existing in the
         TIMETRA-QOS-MIB::tQosEgrQGroupTable.";
      smiv2:oid "1.3.6.1.4.1.6527.3.1.2.2.4.41";
      list tPortNetEgrQGrpEntry {
        key "tmnxChassisIndex tmnxPortPortID tPortNetEgrQGrpName tPortNetEgrQGrpInstanceId";
        description
          "The value of tPortNetEgrQGrpEntry defines an entry in the
           tPortNetEgrQGrpTable.
           
           Entries are created/deleted in this table by SNMP sets to
           tPortNetEgrQGrpRowStatus.";
        smiv2:oid "1.3.6.1.4.1.6527.3.1.2.2.4.41.1";
        leaf tmnxChassisIndex {
          type leafref {
            path "/timetra-chassis:TIMETRA-CHASSIS-MIB/timetra-chassis:tmnxChassisTable/timetra-chassis:tmnxChassisEntry/timetra-chassis:tmnxChassisIndex";
          }
          config true;
        }
        leaf tmnxPortPortID {
          type leafref {
            path "/timetra-port:TIMETRA-PORT-MIB/timetra-port:tmnxPortTable/timetra-port:tmnxPortEntry/timetra-port:tmnxPortPortID";
          }
          config true;
        }
        leaf tPortNetEgrQGrpName {
          type timetra-tc:TNamedItem;
          description
            "The value of tPortNetEgrQGrpName defines the port Egress Queue
             Group name.  It, along with tPortNetEgrQGrpInstanceId uniquely 
             identifies a port egress queue group in the managed system.";
          smiv2:max-access "not-accessible";
          smiv2:oid "1.3.6.1.4.1.6527.3.1.2.2.4.41.1.1";
          config true;
        }
        leaf tPortNetEgrQGrpRowStatus {
          type snmpv2-tc:RowStatus;
          description
            "The value of tPortNetEgrQGrpRowStatus allows entries to be
             created and deleted in the tPortNetEgrQGrpTable.
             
             The creation of an entry in this table will succeed only if the
             queue-group being created exist in TIMETRA-QOS-MIB::tQosEgrQGroupTable.";
          reference
            "See definition of RowStatus in RFC 2579, 'Textual Conventions for
             SMIv2.'";
          smiv2:max-access "read-write";
          smiv2:oid "1.3.6.1.4.1.6527.3.1.2.2.4.41.1.2";
          config false;
        }
        leaf tPortNetEgrQGrpLastChgd {
          type yang:timestamp;
          description
            "The value of tPortNetEgrQGrpLastChgd indicates the value of
             sysUpTime when the queue entry was last modified.";
          smiv2:max-access "read-only";
          smiv2:oid "1.3.6.1.4.1.6527.3.1.2.2.4.41.1.3";
          config false;
        }
        leaf tPortNetEgrQGrpSchedPol {
          type timetra-tc:TNamedItemOrEmpty;
          description
            "The value of tPortNetEgrQGrpSchedPol specifies the name of the
             scheduler-policy to be used with this port egress queue-group.";
          smiv2:defval "";
          smiv2:max-access "read-write";
          smiv2:oid "1.3.6.1.4.1.6527.3.1.2.2.4.41.1.4";
          config true;
        }
        leaf tPortNetEgrQGrpAggRateLimit {
          type timetra-tc:TPortSchedulerAggRateLimitPIR;
          units "kbps";
          description
            "The value of tPortNetEgrQGrpAggRateLimit specifies the maximum
             total rate of all egress queues in this queue-group. The
             value '-1' means that there is no limit.";
          smiv2:defval "-1";
          smiv2:max-access "read-write";
          smiv2:oid "1.3.6.1.4.1.6527.3.1.2.2.4.41.1.5";
          config true;
        }
        leaf tPortNetEgrQGrpAcctgPolId {
          type uint32 {
            range "0..99";
          }
          description
            "The value of tPortNetEgrQGrpAcctgPolId specifies the accounting-policy
             to be used with this port egress queue-group.
             
             A non-zero value indicates the tmnxLogApPolicyId index identifying the
             policy entry in the tmnxLogApTable from the TIMETRA-LOG-MIB which is
             associated with this queue-group.
             
             The value zero indicates that the agent should use the default
             accounting policy, if one exists.";
          smiv2:defval "0";
          smiv2:max-access "read-write";
          smiv2:oid "1.3.6.1.4.1.6527.3.1.2.2.4.41.1.6";
          config true;
        }
        leaf tPortNetEgrQGrpCollectStats {
          type boolean;
          description
            "The value of tPortNetEgrQGrpCollectStats specifies whether
             statistics should be collected on this port egress queue-group.";
          smiv2:defval "false";
          smiv2:max-access "read-write";
          smiv2:oid "1.3.6.1.4.1.6527.3.1.2.2.4.41.1.7";
          config true;
        }
        leaf tPortNetEgrQGrpFrameBaseActg {
          type boolean;
          description
            "The value of tPortNetEgrQGrpFrameBaseActg specifies whether
             to use frame-based accounting for this port egress queue-group.
             
             If the value is 'false', the default packet-based accounting
             method will be used.";
          smiv2:defval "false";
          smiv2:max-access "read-write";
          smiv2:oid "1.3.6.1.4.1.6527.3.1.2.2.4.41.1.8";
          config true;
        }
        leaf tPortNetEgrQGrpDescr {
          type timetra-tc:TItemDescription;
          description
            "The value of tPortNetEgrQGrpDescr specifies the description for
             this port queue-group.";
          smiv2:defval "";
          smiv2:max-access "read-write";
          smiv2:oid "1.3.6.1.4.1.6527.3.1.2.2.4.41.1.9";
          config true;
        }
        leaf tPortNetEgrQGrpPlcrCntrlPolicy {
          type timetra-tc:TNamedItemOrEmpty;
          description
            "The value of tPortNetEgrQGrpPlcrCntrlPolicy specifies the network
             egress policer control policy applicable to this port egress
             queue-group.";
          smiv2:defval "";
          smiv2:max-access "read-write";
          smiv2:oid "1.3.6.1.4.1.6527.3.1.2.2.4.41.1.10";
          config true;
        }
        leaf tPortNetEgrQGrpInstanceId {
          type uint32 {
            range "1..65535";
          }
          description
            "The value of tPortNetEgrQGrpInstanceId defines the unique instance of
             the port Egress Queue Group.  It, along with tPortNetEgrQGrpName, 
             uniquely identifies a port egress queue group in the managed system.";
          smiv2:max-access "not-accessible";
          smiv2:oid "1.3.6.1.4.1.6527.3.1.2.2.4.41.1.11";
          config true;
        }
        config true;
      }
      config true;
    }
    container tPortNetEgrQOverTable {
      description
        "The tPortNetEgrQOverTable has an entry for each port queue override
         configured on this system.";
      smiv2:oid "1.3.6.1.4.1.6527.3.1.2.2.4.43";
      list tPortNetEgrQOverEntry {
        key "tmnxChassisIndex tmnxPortPortID tPortNetEgrQGrpName tPortNetEgrQGrpInstanceId tPortNetEgrQOverQueue";
        description
          "Each row represents a particular port-queue override. Entries
           are created and deleted by the user.";
        smiv2:oid "1.3.6.1.4.1.6527.3.1.2.2.4.43.1";
        leaf tmnxChassisIndex {
          type leafref {
            path "/timetra-chassis:TIMETRA-CHASSIS-MIB/timetra-chassis:tmnxChassisTable/timetra-chassis:tmnxChassisEntry/timetra-chassis:tmnxChassisIndex";
          }
          config true;
        }
        leaf tmnxPortPortID {
          type leafref {
            path "/timetra-port:TIMETRA-PORT-MIB/timetra-port:tmnxPortTable/timetra-port:tmnxPortEntry/timetra-port:tmnxPortPortID";
          }
          config true;
        }
        leaf tPortNetEgrQGrpName {
          type leafref {
            path "/timetra-port:TIMETRA-PORT-MIB/timetra-port:tPortNetEgrQGrpTable/timetra-port:tPortNetEgrQGrpEntry/timetra-port:tPortNetEgrQGrpName";
          }
          config true;
        }
        leaf tPortNetEgrQGrpInstanceId {
          type leafref {
            path "/timetra-port:TIMETRA-PORT-MIB/timetra-port:tPortNetEgrQGrpTable/timetra-port:tPortNetEgrQGrpEntry/timetra-port:tPortNetEgrQGrpInstanceId";
          }
          config true;
        }
        leaf tPortNetEgrQOverQueue {
          type timetra-tc:TEgressQueueId {
            range "1..8";
          }
          description
            "The value of tPortNetEgrQOverQueue specifies the queue ID which is
             used as the fourth index to the table entry.";
          smiv2:max-access "not-accessible";
          smiv2:oid "1.3.6.1.4.1.6527.3.1.2.2.4.43.1.1";
          config true;
        }
        leaf tPortNetEgrQOverRowStatus {
          type snmpv2-tc:RowStatus;
          description
            "The value of tPortNetEgrQOverRowStatus is used for the
             creation and deletion of port-queue overrides.
             
             Row creation will fail if there is no entry in the
             TIMETRA-QOS-MIB::tQosEgrQueueTable with the same index values as the
             last two indices of this table
             (tPortNetEgrQGrpName.tPortNetEgrQOverQueue).";
          smiv2:max-access "read-write";
          smiv2:oid "1.3.6.1.4.1.6527.3.1.2.2.4.43.1.2";
          config false;
        }
        leaf tPortNetEgrQOverLastChanged {
          type yang:timestamp;
          description
            "The value of tPortNetEgrQOverLastChanged indicates the value
             of sysUpTime at the time of the most recent management change to
             this row.";
          smiv2:max-access "read-only";
          smiv2:oid "1.3.6.1.4.1.6527.3.1.2.2.4.43.1.3";
          config false;
        }
        leaf tPortNetEgrQOverCBS {
          type timetra-tc:TBurstSizeOverride;
          units "kilo-bytes";
          description
            "The value of tPortNetEgrQOverCBS specifies the amount of reserved
             buffer space for the queue.";
          smiv2:defval "-2";
          smiv2:max-access "read-write";
          smiv2:oid "1.3.6.1.4.1.6527.3.1.2.2.4.43.1.4";
          config true;
        }
        leaf tPortNetEgrQOverMBS {
          type timetra-tc:TBurstSizeOverride;
          units "kilo-bytes";
          status obsolete;
          description
            "The value of tPortNetEgrQOverMBS specifies the maximum amount of
             buffer space allowed for the queue.
             
             This object is replaced with tPortNetEgrQOverMBSBytes object.";
          smiv2:defval "-2";
          smiv2:max-access "read-write";
          smiv2:oid "1.3.6.1.4.1.6527.3.1.2.2.4.43.1.5";
          config true;
        }
        leaf tPortNetEgrQOverHiPrioOnly {
          type timetra-tc:TBurstPercentOrDefaultOverride;
          description
            "The value of tPortNetEgrQOverHiPrioOnly specifies the percentage of
             buffer space for the queue, used exclusively by high priority packets.";
          smiv2:defval "-2";
          smiv2:max-access "read-write";
          smiv2:oid "1.3.6.1.4.1.6527.3.1.2.2.4.43.1.6";
          config true;
        }
        leaf tPortNetEgrQOverAdminPIR {
          type timetra-tc:TPIRRateOverride;
          units "kbps";
          description
            "The value of tPortNetEgrQOverAdminPIR specifies the administrative
             PIR specified by the user.
             
             An 'inconsistentValue' error is returned if tPortNetEgrQOverAdminPIR  
             is set to non-default value when the object tPortNetEgrQOverRateType is
             set to 'percent'.";
          smiv2:defval "-2";
          smiv2:max-access "read-write";
          smiv2:oid "1.3.6.1.4.1.6527.3.1.2.2.4.43.1.7";
          config true;
        }
        leaf tPortNetEgrQOverAdminCIR {
          type timetra-tc:TCIRRateOverride;
          units "kbps";
          description
            "The value of tPortNetEgrQOverAdminCIR specifies the administrative
             CIR specified by the user.
             
             An 'inconsistentValue' error is returned if tPortNetEgrQOverAdminCIR  
             is set to non-default value when the object tPortNetEgrQOverRateType is 
             set to 'percent'.";
          smiv2:defval "-2";
          smiv2:max-access "read-write";
          smiv2:oid "1.3.6.1.4.1.6527.3.1.2.2.4.43.1.8";
          config true;
        }
        leaf tPortNetEgrQOverPIRAdaptation {
          type timetra-tc:TAdaptationRuleOverride;
          description
            "The value of tPortNetEgrQOverPIRAdaptation specifies the adaptation
             rule to be used while computing the operational PIR
             value. The adaptation rule specifies the rules to compute the
             operational values while maintaining minimum offset.";
          smiv2:defval "noOverride";
          smiv2:max-access "read-write";
          smiv2:oid "1.3.6.1.4.1.6527.3.1.2.2.4.43.1.9";
          config true;
        }
        leaf tPortNetEgrQOverCIRAdaptation {
          type timetra-tc:TAdaptationRuleOverride;
          description
            "The value of tPortNetEgrQOverCIRAdaptation specifies the adaptation
             rule to be used while computing the operational CIR
             value. The adaptation rule specifies the rules to compute the
             operational values while maintaining minimum offset.";
          smiv2:defval "noOverride";
          smiv2:max-access "read-write";
          smiv2:oid "1.3.6.1.4.1.6527.3.1.2.2.4.43.1.10";
          config true;
        }
        leaf tPortNetEgrQOverMBSBytes {
          type timetra-tc:TBurstSizeBytesOverride;
          units "bytes";
          description
            "The value of tPortNetEgrQOverMBSBytes specifies the maximum amount of
             buffer space allowed for the queue.";
          smiv2:defval "-2";
          smiv2:max-access "read-write";
          smiv2:oid "1.3.6.1.4.1.6527.3.1.2.2.4.43.1.11";
          config true;
        }
        leaf tPortNetEgrQOverAdminPIRPercent {
          type timetra-tc:TPIRPercentOverride;
          units "hundredths of a percent";
          description
            "The value of tPortNetEgrQOverAdminPIRPercent specifies the administrative
             PIR percentage, in hudredths of a percent.
             
             An 'inconsistentValue' error is returned if tPortNetEgrQOverAdminPIRPercent  
             is set to non-default value when the object tPortNetEgrQOverRateType is set 
             to 'kbps'.";
          smiv2:defval "-2";
          smiv2:max-access "read-write";
          smiv2:oid "1.3.6.1.4.1.6527.3.1.2.2.4.43.1.12";
          config true;
        }
        leaf tPortNetEgrQOverAdminCIRPercent {
          type timetra-tc:TCIRPercentOverride;
          units "hundredths of a percent";
          description
            "The value of tQosEgrQueueAdminCIRPercent specifies the administrative
             CIR percentage, in hudredths of a percent.
             
             An 'inconsistentValue' error is returned if tQosEgrQueueAdminCIRPercent  
             is set to non-default value when the object tPortNetEgrQOverRateType is set 
             to 'kbps'.";
          smiv2:defval "-2";
          smiv2:max-access "read-write";
          smiv2:oid "1.3.6.1.4.1.6527.3.1.2.2.4.43.1.13";
          config true;
        }
        leaf tPortNetEgrQOverRateType {
          type timetra-tc:TRateType;
          description
            "The value of tPortNetEgrQOverRateType specifies the type of Egress queue
             rate.
             
             When the value of the object is set to 'kbps', the egresss queue rates
             are specified in kbps. The objects  tPortNetEgrQOverAdminPIRPercent and
             tPortNetEgrQOverAdminCIRPercent will be set to their default values.
             
             When the value of the object is set to 'percent', the egress queue rates
             are specified in percentage. The objects tPortNetEgrQOverAdminPIR and 
             tPortNetEgrQOverAdminCIR will be set to their default values.";
          smiv2:defval "kbps";
          smiv2:max-access "read-write";
          smiv2:oid "1.3.6.1.4.1.6527.3.1.2.2.4.43.1.14";
          config true;
        }
        config true;
      }
      config true;
    }
    container tmnxBundleMlfrTable {
      description
        "The tmnxBundleMlfrTable contains MLFR specific data.";
      smiv2:oid "1.3.6.1.4.1.6527.3.1.2.2.4.44";
      list tmnxBundleMlfrEntry {
        key "tmnxChassisIndex tmnxBundleBundleID";
        description
          "Each row entry contains data on an MLFR Bundle.";
        smiv2:oid "1.3.6.1.4.1.6527.3.1.2.2.4.44.1";
        leaf tmnxChassisIndex {
          type leafref {
            path "/timetra-chassis:TIMETRA-CHASSIS-MIB/timetra-chassis:tmnxChassisTable/timetra-chassis:tmnxChassisEntry/timetra-chassis:tmnxChassisIndex";
          }
          config true;
        }
        leaf tmnxBundleBundleID {
          type leafref {
            path "/timetra-port:TIMETRA-PORT-MIB/timetra-port:tmnxBundleTable/timetra-port:tmnxBundleEntry/timetra-port:tmnxBundleBundleID";
          }
          config true;
        }
        leaf tmnxBundleMlfrBundleId {
          type snmp-framework:SnmpAdminString {
            length "0..49";
          }
          description
            "The value of tmnxBundleMlfrBundleId is the Bundle Identifier
             sent with each Link Integrity Protocol message for each member
             of a tmnxBundleBundleID.
             
             The object tmnxPortAdminStatus must be set to 'outOfService' to
             change this value.";
          smiv2:defval "";
          smiv2:max-access "read-write";
          smiv2:oid "1.3.6.1.4.1.6527.3.1.2.2.4.44.1.1";
          config true;
        }
        leaf tmnxBundleMlfrIngQoSProfId {
          type timetra-tc:TMcFrQoSProfileId;
          description
            "The value of tmnxBundleMlfrIngQoSProfId specifies the ingress
             QoS profile to be used for the incoming traffic over this MLFR
             bundle.
             
             The value of tmnxBundleMlfrIngQoSProfId of 0 indicates
             a default QoS profile is used as applicable to given hardware.";
          smiv2:defval "0";
          smiv2:max-access "read-write";
          smiv2:oid "1.3.6.1.4.1.6527.3.1.2.2.4.44.1.4";
          config true;
        }
        leaf tmnxBundleMlfrEgrQoSProfId {
          type timetra-tc:TMcFrQoSProfileId;
          description
            "The value of tmnxBundleMlfrEgrQoSProfId specifies the egress
             QoS profile to be used for the outgoing traffic over this MLFR
             bundle.
             
             The value of tmnxBundleMlfrEgrQoSProfId of 0 indicates
             a default profile is used as applicable to given hardware.";
          smiv2:defval "0";
          smiv2:max-access "read-write";
          smiv2:oid "1.3.6.1.4.1.6527.3.1.2.2.4.44.1.5";
          config true;
        }
        leaf tmnxBundleMlfrHelloTimer {
          type uint32 {
            range "1..180";
          }
          units "seconds";
          description
            "The value of tmnxBundleMlfrHelloTimer specifies the rate
             at which hello messages are sent across a member link.";
          smiv2:defval "10";
          smiv2:max-access "read-write";
          smiv2:oid "1.3.6.1.4.1.6527.3.1.2.2.4.44.1.6";
          config true;
        }
        leaf tmnxBundleMlfrHelloRetryCount {
          type uint32 {
            range "1..5";
          }
          units "seconds";
          description
            "The value of tmnxBundleMlfrHelloTimer specifies the number
             of times to attempt to resend hello messages when the
             tmnxBundleMlfrAckTimer has expired before taking action.";
          smiv2:defval "2";
          smiv2:max-access "read-write";
          smiv2:oid "1.3.6.1.4.1.6527.3.1.2.2.4.44.1.7";
          config true;
        }
        leaf tmnxBundleMlfrAckTimer {
          type uint32 {
            range "1..10";
          }
          units "seconds";
          description
            "The value of tmnxBundleMlfrAckTimer specifies the length
             of time to wait for acknowledgment of a hello message
             before declaring the hello message has not been received.";
          smiv2:defval "4";
          smiv2:max-access "read-write";
          smiv2:oid "1.3.6.1.4.1.6527.3.1.2.2.4.44.1.8";
          config true;
        }
        leaf tmnxBundleMlfrLastChanged {
          type yang:timestamp;
          description
            "The value of tmnxBundleMlfrLastChanged indicates the value
             of sysUpTime at the time of the most recent management change to
             this row.";
          smiv2:max-access "read-only";
          smiv2:oid "1.3.6.1.4.1.6527.3.1.2.2.4.44.1.9";
          config false;
        }
        config true;
      }
      config true;
    }
    container tmnxPortIngQosQStatTable {
      description
        "A table that contains ingress QoS queue-group queue
         port statistics.";
      smiv2:oid "1.3.6.1.4.1.6527.3.1.2.2.4.45";
      list tmnxPortIngQosQStatEntry {
        key "tmnxChassisIndex tmnxPortPortID tPortAccIngQGrpName tmnxPortIngQosQStatQueueId";
        description
          "Ingress statistics about a specific port's
           QoS queue-group queue.";
        smiv2:oid "1.3.6.1.4.1.6527.3.1.2.2.4.45.1";
        leaf tmnxChassisIndex {
          type leafref {
            path "/timetra-chassis:TIMETRA-CHASSIS-MIB/timetra-chassis:tmnxChassisTable/timetra-chassis:tmnxChassisEntry/timetra-chassis:tmnxChassisIndex";
          }
        }
        leaf tmnxPortPortID {
          type leafref {
            path "/timetra-port:TIMETRA-PORT-MIB/timetra-port:tmnxPortTable/timetra-port:tmnxPortEntry/timetra-port:tmnxPortPortID";
          }
        }
        leaf tPortAccIngQGrpName {
          type leafref {
            path "/timetra-port:TIMETRA-PORT-MIB/timetra-port:tPortAccIngQGrpTable/timetra-port:tPortAccIngQGrpEntry/timetra-port:tPortAccIngQGrpName";
          }
        }
        leaf tmnxPortIngQosQStatQueueId {
          type timetra-tc:TIngressQueueId {
            range "1..32";
          }
          description
            "The value of tmnxPortIngQosQStatQueueId specifies the queue-group
             queue ID which is used as the fourth index to the table entry.";
          smiv2:max-access "not-accessible";
          smiv2:oid "1.3.6.1.4.1.6527.3.1.2.2.4.45.1.1";
        }
        leaf tmnxPortIngQosQStatOffHiPrioPkts {
          type yang:counter64;
          description
            "The value of tmnxPortIngQosQStatOffHiPrioPkts indicates the number of
             high priority packets, as determined by the port ingress QoS
             policy, offered by the Pchip to the Qchip.";
          smiv2:max-access "read-only";
          smiv2:oid "1.3.6.1.4.1.6527.3.1.2.2.4.45.1.2";
        }
        leaf tmnxPortIngQosQStatDpdHiPrioPkts {
          type yang:counter64;
          description
            "The value of tmnxPortIngQosQStatDpdHiPrioPkts indicates the number of
             high priority packets, as determined by the port ingress QoS
             policy, dropped by the Qchip due to: MBS exceeded, buffer pool limit
             exceeded, etc.";
          smiv2:max-access "read-only";
          smiv2:oid "1.3.6.1.4.1.6527.3.1.2.2.4.45.1.3";
        }
        leaf tmnxPortIngQosQStatOffLoPrioPkts {
          type yang:counter64;
          description
            "The value of tmnxPortIngQosQStatOffLoPrioPkts indicates the number of
             low priority packets, as determined by the port ingress QoS
             policy, offered by the Pchip to the Qchip.";
          smiv2:max-access "read-only";
          smiv2:oid "1.3.6.1.4.1.6527.3.1.2.2.4.45.1.4";
        }
        leaf tmnxPortIngQosQStatDpdLoPrioPkts {
          type yang:counter64;
          description
            "The value of tmnxPortIngQosQStatDpdLoPrioPkts indicates the number of
             low priority packets, as determined by the port ingress QoS
             policy, dropped by the Qchip due to: MBS exceeded, buffer pool limit
             exceeded, etc.";
          smiv2:max-access "read-only";
          smiv2:oid "1.3.6.1.4.1.6527.3.1.2.2.4.45.1.5";
        }
        leaf tmnxPortIngQosQStatOffHiPrioOcts {
          type yang:counter64;
          description
            "The value of tmnxPortIngQosQStatOffHiPrioOcts indicates the number of
             high priority octets, as determined by the port ingress QoS
             policy, offered by the Pchip to the Qchip.";
          smiv2:max-access "read-only";
          smiv2:oid "1.3.6.1.4.1.6527.3.1.2.2.4.45.1.6";
        }
        leaf tmnxPortIngQosQStatDpdHiPrioOcts {
          type yang:counter64;
          description
            "The value of tmnxPortIngQosQStatDpdHiPrioOcts indicates the number of
             high priority octets, as determined by the port ingress QoS
             policy, dropped by the Qchip due to: MBS exceeded, buffer pool limit
             exceeded, etc.";
          smiv2:max-access "read-only";
          smiv2:oid "1.3.6.1.4.1.6527.3.1.2.2.4.45.1.7";
        }
        leaf tmnxPortIngQosQStatOffLoPrioOcts {
          type yang:counter64;
          description
            "The value of tmnxPortIngQosQStatOffLoPrioOcts indicates the number of
             low priority octets, as determined by the port ingress QoS
             policy, offered by the Pchip to the Qchip.";
          smiv2:max-access "read-only";
          smiv2:oid "1.3.6.1.4.1.6527.3.1.2.2.4.45.1.8";
        }
        leaf tmnxPortIngQosQStatDpdLoPrioOcts {
          type yang:counter64;
          description
            "The value of tmnxPortIngQosQStatDpdLoPrioOcts indicates the number of
             low priority octets, as determined by the port ingress QoS
             policy, dropped by the Qchip due to: MBS exceeded, buffer pool limit
             exceeded, etc.";
          smiv2:max-access "read-only";
          smiv2:oid "1.3.6.1.4.1.6527.3.1.2.2.4.45.1.9";
        }
        leaf tmnxPortIngQosQStatFwdInProfPkts {
          type yang:counter64;
          description
            "The value of tmnxPortIngQosQStatFwdInProfPkts indicates the number of
             in-profile packets (rate below CIR) forwarded by the ingress Qchip.";
          smiv2:max-access "read-only";
          smiv2:oid "1.3.6.1.4.1.6527.3.1.2.2.4.45.1.10";
        }
        leaf tmnxPortIngQosQStatFwdOutProfPkts {
          type yang:counter64;
          description
            "The value of tmnxPortIngQosQStatFwdOutProfPkts indicates the number of
             out-of-profile packets (rate above CIR) forwarded by the ingress Qchip.";
          smiv2:max-access "read-only";
          smiv2:oid "1.3.6.1.4.1.6527.3.1.2.2.4.45.1.11";
        }
        leaf tmnxPortIngQosQStatFwdInProfOcts {
          type yang:counter64;
          description
            "The value of tmnxPortIngQosQStatFwdInProfOcts indicates the number of
             in-profile octets (rate below CIR) forwarded by the ingress Qchip.";
          smiv2:max-access "read-only";
          smiv2:oid "1.3.6.1.4.1.6527.3.1.2.2.4.45.1.12";
        }
        leaf tmnxPortIngQosQStatFwdOutProfOcts {
          type yang:counter64;
          description
            "The value of tmnxPortIngQosQStatFwdOutProfOcts indicates the number of
             out-of-profile octets (rate above CIR) forwarded by the ingress Qchip.";
          smiv2:max-access "read-only";
          smiv2:oid "1.3.6.1.4.1.6527.3.1.2.2.4.45.1.13";
        }
        leaf tmnxPortIngQosQStatUncolPktsOff {
          type yang:counter64;
          description
            "The value of tmnxPortIngQosQStatUncolPktsOff indicates the number of
             uncolored packets offered to the ingress Qchip.";
          smiv2:max-access "read-only";
          smiv2:oid "1.3.6.1.4.1.6527.3.1.2.2.4.45.1.14";
        }
        leaf tmnxPortIngQosQStatUncolOctsOff {
          type yang:counter64;
          description
            "The value of tmnxPortIngQosQStatUncolOctsOff indicates the number of
             uncolored octets offered to the ingress Qchip.";
          smiv2:max-access "read-only";
          smiv2:oid "1.3.6.1.4.1.6527.3.1.2.2.4.45.1.15";
        }
      }
      config false;
    }
    container tmnxPortEgrQosQStatTable {
      description
        "A table that contains egress QoS queue-group queue
         port statistics.";
      smiv2:oid "1.3.6.1.4.1.6527.3.1.2.2.4.46";
      list tmnxPortEgrQosQStatEntry {
        key "tmnxChassisIndex tmnxPortPortID tPortAccEgrQGrpName tPortAccEgrQGrpInstanceId tmnxPortEgrQosQStatQueueId";
        description
          "Egress statistics about a specific port's
           QoS queue-group queue.
           
           In release 11.0, tPortAccEgrQGrpInstanceId is added as 
           another index before tmnxPortEgrQosQStatQueueId for this 
           tmnxPortEgrQosQStatTable.";
        smiv2:oid "1.3.6.1.4.1.6527.3.1.2.2.4.46.1";
        leaf tmnxChassisIndex {
          type leafref {
            path "/timetra-chassis:TIMETRA-CHASSIS-MIB/timetra-chassis:tmnxChassisTable/timetra-chassis:tmnxChassisEntry/timetra-chassis:tmnxChassisIndex";
          }
        }
        leaf tmnxPortPortID {
          type leafref {
            path "/timetra-port:TIMETRA-PORT-MIB/timetra-port:tmnxPortTable/timetra-port:tmnxPortEntry/timetra-port:tmnxPortPortID";
          }
        }
        leaf tPortAccEgrQGrpName {
          type leafref {
            path "/timetra-port:TIMETRA-PORT-MIB/timetra-port:tPortAccEgrQGrpTable/timetra-port:tPortAccEgrQGrpEntry/timetra-port:tPortAccEgrQGrpName";
          }
        }
        leaf tPortAccEgrQGrpInstanceId {
          type leafref {
            path "/timetra-port:TIMETRA-PORT-MIB/timetra-port:tPortAccEgrQGrpTable/timetra-port:tPortAccEgrQGrpEntry/timetra-port:tPortAccEgrQGrpInstanceId";
          }
        }
        leaf tmnxPortEgrQosQStatQueueId {
          type timetra-tc:TEgressQueueId {
            range "1..8";
          }
          description
            "The value of tmnxPortEgrQosQStatQueueId specifies the queue-group
             queue ID which is used as the fourth index to the table entry.";
          smiv2:max-access "not-accessible";
          smiv2:oid "1.3.6.1.4.1.6527.3.1.2.2.4.46.1.1";
        }
        leaf tmnxPortEgrQosQStatFwdInProfPkts {
          type yang:counter64;
          description
            "The value of tmnxPortEgrQosQStatFwdInProfPkts indicates the number of
             in-profile packets (rate below CIR) forwarded by the egress Qchip.";
          smiv2:max-access "read-only";
          smiv2:oid "1.3.6.1.4.1.6527.3.1.2.2.4.46.1.2";
        }
        leaf tmnxPortEgrQosQStatDpdInProfPkts {
          type yang:counter64;
          description
            "The value of tmnxPortEgrQosQStatDpdInProfPkts indicates the number of
             in-profile packets discarded by the egress Qchip due to: MBS exceeded,
             buffer pool limit exceeded, etc.";
          smiv2:max-access "read-only";
          smiv2:oid "1.3.6.1.4.1.6527.3.1.2.2.4.46.1.3";
        }
        leaf tmnxPortEgrQosQStatFwdOutProfPkts {
          type yang:counter64;
          description
            "The value of tmnxPortEgrQosQStatFwdOutProfPkts indicates the number of
             out-of-profile packets (rate above CIR) forwarded by the egress Qchip.";
          smiv2:max-access "read-only";
          smiv2:oid "1.3.6.1.4.1.6527.3.1.2.2.4.46.1.4";
        }
        leaf tmnxPortEgrQosQStatDpdOutProfPkts {
          type yang:counter64;
          description
            "The value of tmnxPortEgrQosQStatDpdOutProfPkts indicates the number of
             out-of-profile packets discarded by the egress Qchip due to:
             MBS exceeded, buffer pool limit exceeded, etc.";
          smiv2:max-access "read-only";
          smiv2:oid "1.3.6.1.4.1.6527.3.1.2.2.4.46.1.5";
        }
        leaf tmnxPortEgrQosQStatFwdInProfOcts {
          type yang:counter64;
          description
            "The value of tmnxPortEgrQosQStatFwdInProfOcts indicates the number of
             in-profile octets (rate below CIR) forwarded by the egress Qchip.";
          smiv2:max-access "read-only";
          smiv2:oid "1.3.6.1.4.1.6527.3.1.2.2.4.46.1.6";
        }
        leaf tmnxPortEgrQosQStatDpdInProfOcts {
          type yang:counter64;
          description
            "The value of tmnxPortEgrQosQStatDpdInProfOcts indicates the number of
             in-profile octets discarded by the egress Qchip due to:
             MBS exceeded, buffer pool limit exceeded, etc.";
          smiv2:max-access "read-only";
          smiv2:oid "1.3.6.1.4.1.6527.3.1.2.2.4.46.1.7";
        }
        leaf tmnxPortEgrQosQStatFwdOutProfOcts {
          type yang:counter64;
          description
            "The value of tmnxPortEgrQosQStatFwdOutProfOcts indicates the number of
             out-of-profile octets (rate above CIR) forwarded by the egress Qchip.";
          smiv2:max-access "read-only";
          smiv2:oid "1.3.6.1.4.1.6527.3.1.2.2.4.46.1.8";
        }
        leaf tmnxPortEgrQosQStatDpdOutProfOcts {
          type yang:counter64;
          description
            "The value of tmnxPortEgrQosQStatDpdOutProfOcts indicates the number of
             out-of-profile octets discarded by the egress Qchip due to:
             MBS exceeded, buffer pool limit exceeded, etc.";
          smiv2:max-access "read-only";
          smiv2:oid "1.3.6.1.4.1.6527.3.1.2.2.4.46.1.9";
        }
      }
      config false;
    }
    container tmnxBundleMemberMlfrTable {
      description
        "The tmnxBundleMemberMlfrTable has an entry for a
         frame-relay link associated with an MLFR Bundle.";
      smiv2:oid "1.3.6.1.4.1.6527.3.1.2.2.4.47";
      list tmnxBundleMemberMlfrEntry {
        key "tmnxBundleBundleID tmnxPortPortID";
        description
          "Each row entry represents an frame-relay link associated with
           a MLFR Bundle.";
        smiv2:oid "1.3.6.1.4.1.6527.3.1.2.2.4.47.1";
        leaf tmnxBundleBundleID {
          type leafref {
            path "/timetra-port:TIMETRA-PORT-MIB/timetra-port:tmnxBundleTable/timetra-port:tmnxBundleEntry/timetra-port:tmnxBundleBundleID";
          }
        }
        leaf tmnxPortPortID {
          type leafref {
            path "/timetra-port:TIMETRA-PORT-MIB/timetra-port:tmnxPortTable/timetra-port:tmnxPortEntry/timetra-port:tmnxPortPortID";
          }
        }
        leaf tmnxBundleMemberMlfrDownReason {
          type timetra-port:TmnxMlfrLinkDownReason;
          description
            "The value of tmnxBundleMemberMlfrDownReason indicates the reason code
             for marking the MLFR member link of the bundle to down (i.e.
             tmnxBundleMemberActive will be set to false).";
          smiv2:max-access "read-only";
          smiv2:oid "1.3.6.1.4.1.6527.3.1.2.2.4.47.1.1";
        }
      }
      config false;
    }
    container tmnxWaveTrackerTable {
      description
        "The tmnxWaveTrackerTable has an entry for each Wavelength Tracker
         port on each IOM card in each chassis in the TMNX system.";
      smiv2:oid "1.3.6.1.4.1.6527.3.1.2.2.4.48";
      list tmnxWaveTrackerEntry {
        key "tmnxChassisIndex tmnxPortPortID";
        description
          "Each row entry represents a Wave Tracker capable port on a
           IOM card in a chassis in the system. Entries cannot be created
           and deleted via SNMP SET operations. The tmnxWaveTrackerEntry
           contains attributes that are unique to the Wave Tracker capable ports.";
        smiv2:oid "1.3.6.1.4.1.6527.3.1.2.2.4.48.1";
        leaf tmnxChassisIndex {
          type leafref {
            path "/timetra-chassis:TIMETRA-CHASSIS-MIB/timetra-chassis:tmnxChassisTable/timetra-chassis:tmnxChassisEntry/timetra-chassis:tmnxChassisIndex";
          }
          config true;
        }
        leaf tmnxPortPortID {
          type leafref {
            path "/timetra-port:TIMETRA-PORT-MIB/timetra-port:tmnxPortTable/timetra-port:tmnxPortEntry/timetra-port:tmnxPortPortID";
          }
          config true;
        }
        leaf tmnxWaveTrackerPowerCtrlEnable {
          type boolean;
          description
            "The value of tmnxWaveTrackerPowerCtrlEnable specifies whether or not
             the Wavelength Tracker Power Control loop that maintains the
             interface's transmitted optical signal average output power is enabled.
             
             tmnxWaveTrackerPowerCtrlEnable is equivalent to
             'tnWtEncodePortCapabilityProgrammed' of the 1696-Roadm MIBs.";
          smiv2:defval "false";
          smiv2:max-access "read-write";
          smiv2:oid "1.3.6.1.4.1.6527.3.1.2.2.4.48.1.1";
          config true;
        }
        leaf tmnxWaveTrackerEncodeEnable {
          type boolean;
          description
            "the value of tmnxWaveTrackerEncodeEnable specifies whether or not
             the Wavelength Tracker Encoding of Wave Keys on the interface's
             transmitted optical signal is enabled.
             
             tmnxWaveTrackerEncodeEnable is equivalent to
             'tnWaveKeyEncodeTransmitState' of the 1696-Roadm MIBs.";
          smiv2:defval "false";
          smiv2:max-access "read-write";
          smiv2:oid "1.3.6.1.4.1.6527.3.1.2.2.4.48.1.2";
          config true;
        }
        leaf tmnxWaveTrackerInUse {
          type boolean;
          description
            "The value of tmnxWaveTrackerInUse indicates whether or not the
             Wavelength Tracker feature is in use by the system for services.
             
             tmnxWaveTrackerInUse is equivalent to
             'tnWtEncodePortCapabilityInUse' of the 1696-Roadm MIBs.";
          smiv2:defval "false";
          smiv2:max-access "read-only";
          smiv2:oid "1.3.6.1.4.1.6527.3.1.2.2.4.48.1.3";
          config false;
        }
        leaf tmnxWaveTrackerTargetPower {
          type int32 {
            range "-2200..300";
          }
          units "mBm";
          description
            "The value of tmnxWaveTrackerTargetPower specifies the desired average
             output power of the interface's transmitted optical signal when
             tmnxWaveTrackerPowerCtrlEnable is set to 'true (1)'.
             
             The UNITS millibels (mBm) are units of 0.01 decibel relative
             to one milliwatt (0 dBm) or dBm multiplied by 100.
             The mBm is used when integers are required instead of floating point.
             For example: -5.21 dBm is equivalent to -521 mBm.";
          smiv2:defval "-2000";
          smiv2:max-access "read-write";
          smiv2:oid "1.3.6.1.4.1.6527.3.1.2.2.4.48.1.4";
          config true;
        }
        leaf tmnxWaveTrackerWaveKey1 {
          type uint32 {
            range "0..4095";
          }
          description
            "The value of tmnxWaveTrackerWaveKey1 specifies the first Wavelength
             Tracker Key (or Identifier) to be transmitted on the interface's
             optical signal when tmnxWaveTrackerEncodeEnable is set to 'true (1)'.
             
             The following table describes the possible tmnxWaveTrackerWaveKey1
             and tmnxWaveTrackerWaveKey2 values based on ITU channel. Key1 and
             Key2 must also match in modulo 2 with each other.
             
             Index   ITU          Key 1        Key 2
                    channel   First Last      First Last
             -------------------------------------------
                0      61     1548  1548      2032  2032  // 1696 Test Channel
             
                // Original Tropic Channels (index 1 to 32)
                1      59        1    15       545   559
                2      58       18    32       562   576
                3      57       35    49       579   593
                4      56       52    66       596   610
                5      54       69    83       613   627
                6      53       86   100       630   644
                7      52      103   117       647   661
                8      51      120   134       664   678
                9      49      137   151       681   698
               10      48      154   168       698   712
               11      47      171   185       715   729
               12      46      188   202       732   746
               13      44      205   219       749   763
               14      43      222   236       766   780
               15      42      239   253       783   797
               16      41      256   270       800   814
               17      39      273   287       817   831
               18      38      290   304       834   848
               19      37      307   321       851   865
               20      36      324   338       868   882
               21      34      341   355       885   899
               22      33      358   372       902   916
               23      32      375   389       919   933
               24      31      392   406       936   950
               25      29      409   423       953   967
               26      28      426   440       970   984
               27      27      443   457       987  1001
               28      26      460   474      1004  1018
               29      24      477   491      1021  1035
               30      23      494   508      1038  1052
               31      22      511   525      1055  1069
               32      21      528   542      1072  1086
             
               // 1696 Extension 42 channels (index 33 to 42)
               33      60     1089  1103      1573  1587
               34      55     1106  1120      1590  1604
               35      50     1123  1137      1607  1621
               36      45     1140  1154      1624  1638
               37      40     1157  1171      1641  1655
               38      35     1174  1188      1658  1672
               39      30     1191  1205      1675  1689
               40      25     1208  1222      1692  1706
               41      20     1225  1239      1709  1723
               42      19     1242  1256      1726  1740
             
               // 1830 Extension to 44 channels (index 43 and 44)
               43      18     1259  1273      1743  1757
               44      17     1276  1290      1760  1774
               
               // 1830 Extension to 88 channels (index 45 to 88)
               45     595     1293  1307      1777  1791
               46     585     1310  1324      1794  1808
               47     575     1327  1341      1811  1825
               48     565     1344  1358      1828  1842
               49     545     1361  1375      1845  1859
               50     535     1378  1392      1862  1876
               51     525     1395  1409      1879  1893
               52     515     1412  1426      1896  1910
               53     495     1429  1443      1913  1927
               54     485     1446  1460      1930  1944
               55     475     1463  1477      1947  1961
               56     465     1480  1494      1964  1978
               57     445     1497  1511      1981  1995
               58     435     1514  1528      1998  2012
               59     425     1531  1545      2015  2029
               60     415     1548  1562      2032  2046
               61     395     3585  3599      2049  2063
               62     385     3602  3616      2066  2080
               63     375     3619  3633      2083  2097
               64     365     3636  3650      2100  2114
               65     345     3653  3667      2117  2131
               66     335     3670  3684      2134  2148
               67     325     3687  3701      2151  2165
               68     315     3704  3718      2168  2182
               69     295     3721  3735      2185  2199
               70     285     3738  3752      2202  2216
               71     275     3755  3769      2219  2233
               72     265     3772  3786      2236  2250
               73     245     3789  3803      2253  2267
               74     235     3806  3820      2270  2284
               75     225     3823  3837      2287  2301
               76     215     3840  3854      2304  2318
               77     605     3857  3871      2321  2335
               78     555     3874  3888      2338  2352
               79     505     3891  3905      2355  2369
               80     455     3908  3922      2372  2386
               81     405     3434  3448      3946  3960
               82     355     3451  3465      3963  3977
               83     305     3468  3482      3980  3994
               84     255     3485  3499      3997  4011
               85     205     3502  3516      4014  4028
               86     195     3519  3533      4031  4045
               87     185     3536  3550      4048  4062
               88     175     3553  3567      4065  4079
             -------------------------------------------";
          smiv2:defval "0";
          smiv2:max-access "read-write";
          smiv2:oid "1.3.6.1.4.1.6527.3.1.2.2.4.48.1.5";
          config true;
        }
        leaf tmnxWaveTrackerWaveKey2 {
          type uint32 {
            range "0..4095";
          }
          description
            "the value of tmnxWaveTrackerWaveKey2 specifies the second Wavelength
             Tracker Key (or Identifier) to be transmitted on the interface's
             optical signal when tmnxWaveTrackerEncodeEnable is set to 'true (1)'.
             
             Refer to the description of tmnxWaveTrackerWaveKey1 for the valid
             values based on the ITU channel.";
          smiv2:defval "0";
          smiv2:max-access "read-write";
          smiv2:oid "1.3.6.1.4.1.6527.3.1.2.2.4.48.1.6";
          config true;
        }
        leaf tmnxWaveTrackerTrailName {
          type snmp-framework:SnmpAdminString {
            length "0..80";
          }
          description
            "The value of tmnxWaveTrackerTrailName indicates the trail name of the
             encode point. This trail is usually transmitted in the OTU pm-tti.
             
             tmnxWaveTrackerTrailName is equivalent to
             'tnWaveKeyEncodeTrailName' of the 1696-Roadm MIBs.";
          smiv2:max-access "read-only";
          smiv2:oid "1.3.6.1.4.1.6527.3.1.2.2.4.48.1.7";
          config false;
        }
        leaf tmnxWaveTrackerCfgAlarms {
          type timetra-port:TmnxWaveTrackerAlarm;
          description
            "The value of tmnxWaveTrackerCfgAlarms specifies the alarms that are to
             be monitored by the Wavelength Tracker interface. If an alarm bit is
             set, then the corresponding alarm will generate a raise or clear
             notification when its state changes. An unset bit specifies that the
             alarm corresponding with the bit will not report on its state
             transitions.";
          smiv2:defval "{encFail, encDegr, pwrFail, pwrDegr, pwrHigh, pwrLow, missing}";
          smiv2:max-access "read-write";
          smiv2:oid "1.3.6.1.4.1.6527.3.1.2.2.4.48.1.8";
          config true;
        }
        leaf tmnxWaveTrackerAlarmState {
          type timetra-port:TmnxWaveTrackerAlarm;
          description
            "The value of tmnxWaveTrackerAlarmState indicates which monitored alarms
             are raised against the Wavelength Tracker interface.";
          smiv2:max-access "read-only";
          smiv2:oid "1.3.6.1.4.1.6527.3.1.2.2.4.48.1.9";
          config false;
        }
        leaf tmnxWaveTrackerMeasuredPower {
          type int32;
          units "mBm";
          description
            "tmnxWaveTrackerMeasuredPower indicates the current average output
             power of the interface's transmitted optical signal.
             
             The UNITS mBm are units of 0.01 dBm or dBm multiplied by 100.
             The mBm is used when integers are required instead of floating point.
             For example: -5.21 dBm is equivalent to -521 mBm.";
          smiv2:max-access "read-only";
          smiv2:oid "1.3.6.1.4.1.6527.3.1.2.2.4.48.1.10";
          config false;
        }
        leaf tmnxWaveTrackerMaxAttainablePwr {
          type int32;
          units "mBm";
          description
            "tmnxWaveTrackerMaxAttainablePwr indicates the maximum average output
             power of the interface's transmitted optical signal at end of life.
             
             The UNITS mBm are units of 0.01 dBm or dBm multiplied by 100.
             The mBm is used when integers are required instead of floating point.
             For example: -5.21 dBm is equivalent to -521 mBm.";
          smiv2:max-access "read-only";
          smiv2:oid "1.3.6.1.4.1.6527.3.1.2.2.4.48.1.11";
          config false;
        }
        leaf tmnxWaveTrackerMinAttainablePwr {
          type int32;
          units "mBm";
          description
            "tmnxWaveTrackerMinAttainablePwr indicates the minimum average output
             power of the interface's transmitted optical signal at end of life.
             
             The UNITS mBm are units of 0.01 dBm or dBm multiplied by 100.
             The mBm is used when integers are required instead of floating point.
             For example: -5.21 dBm is equivalent to -521 mBm.";
          smiv2:max-access "read-only";
          smiv2:oid "1.3.6.1.4.1.6527.3.1.2.2.4.48.1.12";
          config false;
        }
        leaf tmnxWaveTrackerUpperPowerMargin {
          type uint32;
          units "mB";
          description
            "tmnxWaveTrackerUpperPowerMargin indicates how much the average output
             power of the interface's transmitted optical signal can be increased.
             
             The UNITS millibels (mB) are units of 0.01 dB or dB multiplied by 100.
             The mB is used when integers are required instead of floating point.
             For example: 5.21 dB is equivalent to 521 mB.";
          smiv2:max-access "read-only";
          smiv2:oid "1.3.6.1.4.1.6527.3.1.2.2.4.48.1.13";
          config false;
        }
        leaf tmnxWaveTrackerLowerPowerMargin {
          type uint32;
          units "mB";
          description
            "tmnxWaveTrackerLowerPowerMargin indicates how much the average output
             power of the interface's transmitted optical signal can be decreased.
             
             The UNITS mBm are units of 0.01 dB or dB multiplied by 100.
             The mB is used when integers are required instead of floating point.
             For example: 5.21 dB is equivalent to 521 mB.";
          smiv2:max-access "read-only";
          smiv2:oid "1.3.6.1.4.1.6527.3.1.2.2.4.48.1.14";
          config false;
        }
        leaf tmnxWaveTrackerPortType {
          type enumeration {
            enum "unknown" {
              value 0;
            }
            enum "fixed" {
              value 1;
            }
            enum "pluggable" {
              value 2;
            }
          }
          description
            "The value of tmnxWaveTrackerPortType indicates if the port is fixed or
             if it supports pluggable equipment.";
          smiv2:max-access "read-only";
          smiv2:oid "1.3.6.1.4.1.6527.3.1.2.2.4.48.1.15";
          config false;
        }
        leaf tmnxWaveTrackerSfpVoaEquipped {
          type boolean;
          description
            "The value of tmnxWaveTrackerSfpVoaEquipped indicates whether or not an
             SFP VOA is present.";
          smiv2:max-access "read-only";
          smiv2:oid "1.3.6.1.4.1.6527.3.1.2.2.4.48.1.16";
          config false;
        }
        leaf tmnxWaveTrackerSfpVoaType {
          type enumeration {
            enum "none" {
              value 0;
            }
            enum "fast" {
              value 1;
            }
            enum "slow" {
              value 2;
            }
          }
          description
            "The value of tmnxWaveTrackerSfpVoaType indicates if the SFP VOA is
             fast or slow.";
          smiv2:max-access "read-only";
          smiv2:oid "1.3.6.1.4.1.6527.3.1.2.2.4.48.1.17";
          config false;
        }
        leaf tmnxWaveTrackerSfpVoaSerialNum {
          type timetra-tc:TNamedItemOrEmpty;
          description
            "The value of tmnxWaveTrackerSfpVoaSerialNum indicates the serial
             number information for the SFP VOA.
             
             The string is expected to contain printable ASCII characters, but
             unprintable ASCII characters read from the EEPROM are not
             filtered out.";
          smiv2:max-access "read-only";
          smiv2:oid "1.3.6.1.4.1.6527.3.1.2.2.4.48.1.18";
          config false;
        }
        leaf tmnxWaveTrackerSfpVoaModelNum {
          type timetra-tc:TNamedItemOrEmpty;
          description
            "The value of tmnxWaveTrackerSfpVoaModelNum indicates the model
             information for the SFP VOA.
             
             The string is expected to contain printable ASCII characters, but
             unprintable ASCII characters read from the EEPROM are not
             filtered out.";
          smiv2:max-access "read-only";
          smiv2:oid "1.3.6.1.4.1.6527.3.1.2.2.4.48.1.19";
          config false;
        }
        config true;
      }
      config true;
    }
    container tPortAccEgrQGrpHostMatchTable {
      description
        "The value of tPortAccEgrQGrpHostMatchTable defines a 
         set of string values optionally used by subscriber 
         management to map subscriber's and subscriber host's
         policed traffic to a specific egress port queue group.";
      smiv2:oid "1.3.6.1.4.1.6527.3.1.2.2.4.50";
      list tPortAccEgrQGrpHostMatchEntry {
        key "tmnxChassisIndex tmnxPortPortID tPortAccEgrQGrpName tPortAccEgrQGrpInstanceId tPortAccEgrQGrpHMIntDestId tPortAccEgrQGrpHMOrgString";
        description
          "The value of tPortAccEgrQGrpHostMatchEntry defines an entry in the
           tPortAccEgrQGrpHostMatchTable.
           
           Entries are created/deleted in this table by SNMP sets to
           tPortAccEgrQGrpHMRowStatus.";
        smiv2:oid "1.3.6.1.4.1.6527.3.1.2.2.4.50.1";
        leaf tmnxChassisIndex {
          type leafref {
            path "/timetra-chassis:TIMETRA-CHASSIS-MIB/timetra-chassis:tmnxChassisTable/timetra-chassis:tmnxChassisEntry/timetra-chassis:tmnxChassisIndex";
          }
        }
        leaf tmnxPortPortID {
          type leafref {
            path "/timetra-port:TIMETRA-PORT-MIB/timetra-port:tmnxPortTable/timetra-port:tmnxPortEntry/timetra-port:tmnxPortPortID";
          }
        }
        leaf tPortAccEgrQGrpName {
          type leafref {
            path "/timetra-port:TIMETRA-PORT-MIB/timetra-port:tPortAccEgrQGrpTable/timetra-port:tPortAccEgrQGrpEntry/timetra-port:tPortAccEgrQGrpName";
          }
        }
        leaf tPortAccEgrQGrpInstanceId {
          type leafref {
            path "/timetra-port:TIMETRA-PORT-MIB/timetra-port:tPortAccEgrQGrpTable/timetra-port:tPortAccEgrQGrpEntry/timetra-port:tPortAccEgrQGrpInstanceId";
          }
        }
        leaf tPortAccEgrQGrpHMIntDestId {
          type timetra-tc:TmnxSubMgtIntDestId;
          description
            "The value of tPortAccEgrQGrpHMIntDestId defines the 
             intermediate destination id to match on.";
          smiv2:max-access "not-accessible";
          smiv2:oid "1.3.6.1.4.1.6527.3.1.2.2.4.50.1.1";
        }
        leaf tPortAccEgrQGrpHMOrgString {
          type timetra-tc:TmnxSubMgtOrgStrOrZero;
          description
            "The value of tPortAccEgrQGrpHMOrgString defines the 
             organization string to match on.
             
             If tPortAccEgrQGrpHMOrgString is the empty string (''), 
             every subscriber with an organization string will not 
             match this entry.
             
             If tPortAccEgrQGrpHMOrgString is the wildcard symbol ('*'),
             every subscriber with an organization string will match
             this entry, if the tPortAccEgrQGrpHMIntDestId matches.
             
             Currently only the empty string ('') is accepted.";
          smiv2:max-access "not-accessible";
          smiv2:oid "1.3.6.1.4.1.6527.3.1.2.2.4.50.1.2";
        }
        leaf tPortAccEgrQGrpHMRowStatus {
          type snmpv2-tc:RowStatus;
          description
            "The value of tPortAccEgrQGrpHMRowStatus allows entries to be
             created and deleted in the tPortAccEgrQGrpHostMatchTable.
             
             The creation of an entry in this table will succeed only if the
             queue-group being created exist in TIMETRA-QOS-MIB::tQosEgrQGroupTable.";
          reference
            "See definition of RowStatus in RFC 2579, 'Textual Conventions for
             SMIv2.'";
          smiv2:max-access "read-write";
          smiv2:oid "1.3.6.1.4.1.6527.3.1.2.2.4.50.1.3";
        }
        leaf tPortAccEgrQGrpHMLastChgd {
          type yang:timestamp;
          description
            "The value of tPortAccEgrQGrpHMLastChgd indicates the value of
             sysUpTime when the host match entry was last modified.";
          smiv2:max-access "read-only";
          smiv2:oid "1.3.6.1.4.1.6527.3.1.2.2.4.50.1.4";
        }
      }
      config false;
    }
    container tPortAccIngSchedStatTable {
      description
        "The value of tPortAccIngSchedStatTable defines access Ingress Queue
         Group related statistics per scheduler.";
      smiv2:oid "1.3.6.1.4.1.6527.3.1.2.2.4.51";
      list tPortAccIngSchedStatEntry {
        key "tmnxChassisIndex tmnxPortPortID tPortAccIngQGrpName tPortAccIngSchedStatName";
        description
          "The value of tPortAccIngSchedStatEntry defines an entry in the
           tPortAccIngSchedStatTable. It represents statistics about a 
           specific QoS ingress queue group scheduler on the port specified by
           tPortAccIngSchedStatName on the access side.";
        smiv2:oid "1.3.6.1.4.1.6527.3.1.2.2.4.51.1";
        leaf tmnxChassisIndex {
          type leafref {
            path "/timetra-chassis:TIMETRA-CHASSIS-MIB/timetra-chassis:tmnxChassisTable/timetra-chassis:tmnxChassisEntry/timetra-chassis:tmnxChassisIndex";
          }
        }
        leaf tmnxPortPortID {
          type leafref {
            path "/timetra-port:TIMETRA-PORT-MIB/timetra-port:tmnxPortTable/timetra-port:tmnxPortEntry/timetra-port:tmnxPortPortID";
          }
        }
        leaf tPortAccIngQGrpName {
          type leafref {
            path "/timetra-port:TIMETRA-PORT-MIB/timetra-port:tPortAccIngQGrpTable/timetra-port:tPortAccIngQGrpEntry/timetra-port:tPortAccIngQGrpName";
          }
        }
        leaf tPortAccIngSchedStatName {
          type timetra-tc:TNamedItem;
          description
            "The value of tPortAccEgrSchedStatName indicates the scheduler
             associated with this queue group on this port.";
          smiv2:max-access "not-accessible";
          smiv2:oid "1.3.6.1.4.1.6527.3.1.2.2.4.51.1.1";
        }
        leaf tPortAccIngSchedStatFwdPkts {
          type yang:counter64;
          description
            "The value of tPortAccIngSchedStatFwdPkts indicates the number of 
             forwarded packets by this port on this queue-group using this
             scheduler.";
          smiv2:max-access "read-only";
          smiv2:oid "1.3.6.1.4.1.6527.3.1.2.2.4.51.1.2";
        }
        leaf tPortAccIngSchedStatFwdPktsHi {
          type yang:counter32;
          description
            "The value of tPortAccIngSchedStatFwdPktsHi indicates upper 32 bits of
             tPortAccIngSchedStatFwdPkts object.";
          smiv2:max-access "read-only";
          smiv2:oid "1.3.6.1.4.1.6527.3.1.2.2.4.51.1.3";
        }
        leaf tPortAccIngSchedStatFwdPktsLo {
          type yang:counter32;
          description
            "The value of tPortAccIngSchedStatFwdPktsLo indicates lower 32 bits of
             tPortAccIngSchedStatFwdPkts object.";
          smiv2:max-access "read-only";
          smiv2:oid "1.3.6.1.4.1.6527.3.1.2.2.4.51.1.4";
        }
        leaf tPortAccIngSchedStatFwdOcts {
          type yang:counter64;
          description
            "The value of tPortAccIngSchedStatFwdOcts indicates the number of 
             forwarded octets by this port on this queue-group using this
             scheduler.";
          smiv2:max-access "read-only";
          smiv2:oid "1.3.6.1.4.1.6527.3.1.2.2.4.51.1.5";
        }
        leaf tPortAccIngSchedStatFwdOctsHi {
          type yang:counter32;
          description
            "The value of tPortAccIngSchedStatFwdOctsHi indicates upper 32 bits of
             tPortAccIngSchedStatFwdOcts object.";
          smiv2:max-access "read-only";
          smiv2:oid "1.3.6.1.4.1.6527.3.1.2.2.4.51.1.6";
        }
        leaf tPortAccIngSchedStatFwdOctsLo {
          type yang:counter32;
          description
            "The value of tPortAccIngSchedStatFwdOctsLo indicates lower 32 bits of
             tPortAccIngSchedStatFwdOcts object.";
          smiv2:max-access "read-only";
          smiv2:oid "1.3.6.1.4.1.6527.3.1.2.2.4.51.1.7";
        }
      }
      config false;
    }
    container tPortAccEgrSchedStatTable {
      description
        "The value of tPortAccEgrSchedStatTable defines access Egress Queue
         Group related statistics per scheduler.";
      smiv2:oid "1.3.6.1.4.1.6527.3.1.2.2.4.52";
      list tPortAccEgrSchedStatEntry {
        key "tmnxChassisIndex tmnxPortPortID tPortAccEgrQGrpName tPortAccEgrQGrpInstanceId tPortAccEgrSchedStatName";
        description
          "The value of tPortAccEgrSchedStatEntry defines an entry in the
           tPortAccEgrSchedStatTable. It represents statistics about a 
           specific QoS egress queue group scheduler on the port specified by
           tPortAccEgrSchedStatName on the access side.
           
           In release 11.0, tPortAccEgrQGrpInstanceId is added as another index 
           before tPortAccEgrSchedStatName for this tPortAccEgrSchedStatTable.";
        smiv2:oid "1.3.6.1.4.1.6527.3.1.2.2.4.52.1";
        leaf tmnxChassisIndex {
          type leafref {
            path "/timetra-chassis:TIMETRA-CHASSIS-MIB/timetra-chassis:tmnxChassisTable/timetra-chassis:tmnxChassisEntry/timetra-chassis:tmnxChassisIndex";
          }
        }
        leaf tmnxPortPortID {
          type leafref {
            path "/timetra-port:TIMETRA-PORT-MIB/timetra-port:tmnxPortTable/timetra-port:tmnxPortEntry/timetra-port:tmnxPortPortID";
          }
        }
        leaf tPortAccEgrQGrpName {
          type leafref {
            path "/timetra-port:TIMETRA-PORT-MIB/timetra-port:tPortAccEgrQGrpTable/timetra-port:tPortAccEgrQGrpEntry/timetra-port:tPortAccEgrQGrpName";
          }
        }
        leaf tPortAccEgrQGrpInstanceId {
          type leafref {
            path "/timetra-port:TIMETRA-PORT-MIB/timetra-port:tPortAccEgrQGrpTable/timetra-port:tPortAccEgrQGrpEntry/timetra-port:tPortAccEgrQGrpInstanceId";
          }
        }
        leaf tPortAccEgrSchedStatName {
          type timetra-tc:TNamedItem;
          description
            "The value of tPortAccEgrSchedStatName indicates the scheduler
             associated with this queue group on this port.";
          smiv2:max-access "not-accessible";
          smiv2:oid "1.3.6.1.4.1.6527.3.1.2.2.4.52.1.1";
        }
        leaf tPortAccEgrSchedStatFwdPkts {
          type yang:counter64;
          description
            "The value of tPortAccEgrSchedStatFwdPkts indicates the number of 
             forwarded packets by this port on this queue-group using this
             scheduler.";
          smiv2:max-access "read-only";
          smiv2:oid "1.3.6.1.4.1.6527.3.1.2.2.4.52.1.2";
        }
        leaf tPortAccEgrSchedStatFwdPktsHi {
          type yang:counter32;
          description
            "The value of tPortAccEgrSchedStatFwdPktsHi indicates upper 32 bits of
             tPortAccEgrSchedStatFwdPkts object.";
          smiv2:max-access "read-only";
          smiv2:oid "1.3.6.1.4.1.6527.3.1.2.2.4.52.1.3";
        }
        leaf tPortAccEgrSchedStatFwdPktsLo {
          type yang:counter32;
          description
            "The value of tPortAccEgrSchedStatFwdPktsLo indicates lower 32 bits of
             tPortAccEgrSchedStatFwdPkts object.";
          smiv2:max-access "read-only";
          smiv2:oid "1.3.6.1.4.1.6527.3.1.2.2.4.52.1.4";
        }
        leaf tPortAccEgrSchedStatFwdOcts {
          type yang:counter64;
          description
            "tPortAccEgrSchedStatFwdOcts indicates the number of forwarded octets
             by this port on this queue-group using this scheduler.";
          smiv2:max-access "read-only";
          smiv2:oid "1.3.6.1.4.1.6527.3.1.2.2.4.52.1.5";
        }
        leaf tPortAccEgrSchedStatFwdOctsHi {
          type yang:counter32;
          description
            "The value of tPortAccEgrSchedStatFwdOctsHi indicates upper 32 bits of
             tPortAccEgrSchedStatFwdOcts object.";
          smiv2:max-access "read-only";
          smiv2:oid "1.3.6.1.4.1.6527.3.1.2.2.4.52.1.6";
        }
        leaf tPortAccEgrSchedStatFwdOctsLo {
          type yang:counter32;
          description
            "The value of tPortAccEgrSchedStatFwdOctsLo indicates lower 32 bits of
             tPortAccEgrSchedStatFwdOcts object.";
          smiv2:max-access "read-only";
          smiv2:oid "1.3.6.1.4.1.6527.3.1.2.2.4.52.1.7";
        }
      }
      config false;
    }
    container tPortNetEgrSchedStatTable {
      description
        "The value of tPortNetEgrSchedStatTable defines network Egress Queue
         Group related statistics per scheduler.";
      smiv2:oid "1.3.6.1.4.1.6527.3.1.2.2.4.53";
      list tPortNetEgrSchedStatEntry {
        key "tmnxChassisIndex tmnxPortPortID tPortNetEgrQGrpName tPortNetEgrQGrpInstanceId tPortNetEgrSchedStatName";
        description
          "The value of tPortNetEgrSchedStatEntry defines an entry in the
           tPortNetEgrSchedStatTable. It represents statistics about a 
           specific QoS egress queue group scheduler on the port specified by
           tPortNetEgrSchedStatName on the network side.";
        smiv2:oid "1.3.6.1.4.1.6527.3.1.2.2.4.53.1";
        leaf tmnxChassisIndex {
          type leafref {
            path "/timetra-chassis:TIMETRA-CHASSIS-MIB/timetra-chassis:tmnxChassisTable/timetra-chassis:tmnxChassisEntry/timetra-chassis:tmnxChassisIndex";
          }
        }
        leaf tmnxPortPortID {
          type leafref {
            path "/timetra-port:TIMETRA-PORT-MIB/timetra-port:tmnxPortTable/timetra-port:tmnxPortEntry/timetra-port:tmnxPortPortID";
          }
        }
        leaf tPortNetEgrQGrpName {
          type leafref {
            path "/timetra-port:TIMETRA-PORT-MIB/timetra-port:tPortNetEgrQGrpTable/timetra-port:tPortNetEgrQGrpEntry/timetra-port:tPortNetEgrQGrpName";
          }
        }
        leaf tPortNetEgrQGrpInstanceId {
          type leafref {
            path "/timetra-port:TIMETRA-PORT-MIB/timetra-port:tPortNetEgrQGrpTable/timetra-port:tPortNetEgrQGrpEntry/timetra-port:tPortNetEgrQGrpInstanceId";
          }
        }
        leaf tPortNetEgrSchedStatName {
          type timetra-tc:TNamedItem;
          description
            "The value of tPortAccEgrSchedStatName indicates the scheduler
             associated with this queue group on this port.";
          smiv2:max-access "not-accessible";
          smiv2:oid "1.3.6.1.4.1.6527.3.1.2.2.4.53.1.1";
        }
        leaf tPortNetEgrSchedStatFwdPkts {
          type yang:counter64;
          description
            "The value of tPortNetEgrSchedStatFwdPkts indicates the number of 
             forwarded packets by this port on this queue-group using this
             scheduler.";
          smiv2:max-access "read-only";
          smiv2:oid "1.3.6.1.4.1.6527.3.1.2.2.4.53.1.2";
        }
        leaf tPortNetEgrSchedStatFwdPktsHi {
          type yang:counter32;
          description
            "The value of tPortNetEgrSchedStatFwdPktsHi indicates upper 32 bits of
             tPortNetEgrSchedStatFwdPkts object.";
          smiv2:max-access "read-only";
          smiv2:oid "1.3.6.1.4.1.6527.3.1.2.2.4.53.1.3";
        }
        leaf tPortNetEgrSchedStatFwdPktsLo {
          type yang:counter32;
          description
            "tPortNetEgrSchedStatFwdPktsLo indicates lower 32 bits of
             tPortNetEgrSchedStatFwdPkts object.";
          smiv2:max-access "read-only";
          smiv2:oid "1.3.6.1.4.1.6527.3.1.2.2.4.53.1.4";
        }
        leaf tPortNetEgrSchedStatFwdOcts {
          type yang:counter64;
          description
            "The value of tPortNetEgrSchedStatFwdOcts indicates the number of 
             forwarded octets by this port on this queue-group using this
             scheduler.";
          smiv2:max-access "read-only";
          smiv2:oid "1.3.6.1.4.1.6527.3.1.2.2.4.53.1.5";
        }
        leaf tPortNetEgrSchedStatFwdOctsHi {
          type yang:counter32;
          description
            "tPortNetEgrSchedStatFwdOctsHi indicates upper 32 bits of
             tPortNetEgrSchedStatFwdOcts object.";
          smiv2:max-access "read-only";
          smiv2:oid "1.3.6.1.4.1.6527.3.1.2.2.4.53.1.6";
        }
        leaf tPortNetEgrSchedStatFwdOctsLo {
          type yang:counter32;
          description
            "The value of tPortNetEgrSchedStatFwdOctsLo indicates lower 32 bits of
             tPortNetEgrSchedStatFwdOcts object.";
          smiv2:max-access "read-only";
          smiv2:oid "1.3.6.1.4.1.6527.3.1.2.2.4.53.1.7";
        }
      }
      config false;
    }
    container tPortEgrVPortTable {
      description
        "The tPortEgrVPortTable has an entry for each virtual port
         defined on this port.";
      smiv2:oid "1.3.6.1.4.1.6527.3.1.2.2.4.55";
      list tPortEgrVPortEntry {
        key "tmnxChassisIndex tmnxPortPortID tPortEgrVPortName";
        description
          "Each row entry represents a virtual port defined on the port for the
           chassis in the system.";
        smiv2:oid "1.3.6.1.4.1.6527.3.1.2.2.4.55.1";
        leaf tmnxChassisIndex {
          type leafref {
            path "/timetra-chassis:TIMETRA-CHASSIS-MIB/timetra-chassis:tmnxChassisTable/timetra-chassis:tmnxChassisEntry/timetra-chassis:tmnxChassisIndex";
          }
          config true;
        }
        leaf tmnxPortPortID {
          type leafref {
            path "/timetra-port:TIMETRA-PORT-MIB/timetra-port:tmnxPortTable/timetra-port:tmnxPortEntry/timetra-port:tmnxPortPortID";
          }
          config true;
        }
        leaf tPortEgrVPortName {
          type timetra-tc:TNamedItem;
          description
            "The value of tPortEgrVPortName is the name of the virtual port
             on this port.";
          smiv2:max-access "not-accessible";
          smiv2:oid "1.3.6.1.4.1.6527.3.1.2.2.4.55.1.1";
          config true;
        }
        leaf tPortEgrVPortRowStatus {
          type snmpv2-tc:RowStatus;
          description
            "The value of tPortEgrVPortRowStatus specifies the row-status of
             this entry in this table.";
          smiv2:max-access "read-write";
          smiv2:oid "1.3.6.1.4.1.6527.3.1.2.2.4.55.1.2";
          config false;
        }
        leaf tPortEgrVPortLastChanged {
          type yang:timestamp;
          description
            "The value of tPortEgrVPortLastChanged indicates the time-stamp
             of the last change in this entry.";
          smiv2:max-access "read-only";
          smiv2:oid "1.3.6.1.4.1.6527.3.1.2.2.4.55.1.3";
          config false;
        }
        leaf tPortEgrVPortDescr {
          type timetra-tc:TItemDescription;
          description
            "The value of tPortEgrVPortDescr specifies the description of the
             virtual port.";
          smiv2:defval "";
          smiv2:max-access "read-write";
          smiv2:oid "1.3.6.1.4.1.6527.3.1.2.2.4.55.1.4";
          config true;
        }
        leaf tPortEgrVPortSchedPol {
          type timetra-tc:TNamedItemOrEmpty;
          description
            "The value of tPortEgrVPortSchedPol specifies the name of the
             port scheduler policy assigned to this virtual port.";
          smiv2:defval "";
          smiv2:max-access "read-write";
          smiv2:oid "1.3.6.1.4.1.6527.3.1.2.2.4.55.1.5";
          config true;
        }
        leaf tPortEgrVPortAggRateLimit {
          type timetra-tc:TPortSchedulerAggRateLimitPIR;
          units "kbps";
          description
            "The value of tPortEgrVPortAggRateLimit specifies the maximum
             total rate of all subscribers for this virtual port. 
             
             The value -1 means that there is no limit.";
          smiv2:defval "-1";
          smiv2:max-access "read-write";
          smiv2:oid "1.3.6.1.4.1.6527.3.1.2.2.4.55.1.6";
          config true;
        }
        leaf tPortEgrVPortEgrRateModify {
          type timetra-tc:TmnxEnabledDisabled;
          description
            "The value of tPortEgrVPortEgrRateModify specifies 
             if egress-rate modification is enabled.
             
             Egress-rate-modification takes the egress bandwidth already in use
             for multicast traffic into account while performing rate limiting
             according to the values of tPortEgrVPortAggRateLimit or tPortEgrVPortSchedPol,
             in order to avoid that the sum of unicast and multicast bandwidths would
             exceed the egress aggregate rate limit.";
          smiv2:defval "disabled";
          smiv2:max-access "read-write";
          smiv2:oid "1.3.6.1.4.1.6527.3.1.2.2.4.55.1.12";
          config true;
        }
        leaf tPortEgrVPortEgrRateModifyDelta {
          type int32;
          units "kbps";
          description
            "The value of tPortEgrVPortEgrRateModifyDelta indicates
             the actual bandwidth correction applied while the value
             of the object tPortEgrVPortEgrRateModify is 'enabled'.";
          smiv2:max-access "read-only";
          smiv2:oid "1.3.6.1.4.1.6527.3.1.2.2.4.55.1.13";
          config false;
        }
        config true;
      }
      config true;
    }
    container tPortEgrVPortHostMatchTable {
      description
        "The value of tPortEgrVPortHostMatchTable defines a set of string
         values optionally used by subscriber management to map subscriber's
         and subscriber host's queued traffic to a specific egress port
         virtual port.";
      smiv2:oid "1.3.6.1.4.1.6527.3.1.2.2.4.57";
      list tPortEgrVPortHostMatchEntry {
        key "tmnxChassisIndex tmnxPortPortID tPortEgrVPortName tPortEgrVPortHMIntDestId tPortEgrVPortHMOrgString";
        description
          "The value of tPortEgrVPortHostMatchEntry defines an entry in the
           tPortEgrVPortHostMatchTable.
           
           Entries are created/deleted in this table by SNMP sets to
           tPortEgrVPortHMRowStatus.";
        smiv2:oid "1.3.6.1.4.1.6527.3.1.2.2.4.57.1";
        leaf tmnxChassisIndex {
          type leafref {
            path "/timetra-chassis:TIMETRA-CHASSIS-MIB/timetra-chassis:tmnxChassisTable/timetra-chassis:tmnxChassisEntry/timetra-chassis:tmnxChassisIndex";
          }
        }
        leaf tmnxPortPortID {
          type leafref {
            path "/timetra-port:TIMETRA-PORT-MIB/timetra-port:tmnxPortTable/timetra-port:tmnxPortEntry/timetra-port:tmnxPortPortID";
          }
        }
        leaf tPortEgrVPortName {
          type leafref {
            path "/timetra-port:TIMETRA-PORT-MIB/timetra-port:tPortEgrVPortTable/timetra-port:tPortEgrVPortEntry/timetra-port:tPortEgrVPortName";
          }
        }
        leaf tPortEgrVPortHMIntDestId {
          type timetra-tc:TmnxSubMgtIntDestId;
          description
            "The value of tPortEgrVPortHMIntDestId defines the intermediate
             destination id to match on.";
          smiv2:max-access "not-accessible";
          smiv2:oid "1.3.6.1.4.1.6527.3.1.2.2.4.57.1.1";
        }
        leaf tPortEgrVPortHMOrgString {
          type timetra-tc:TmnxSubMgtOrgStrOrZero;
          description
            "The value of tPortEgrVPortHMOrgString defines the organization
             string to match on.
                 
             If tPortEgrVPortHMOrgString is the empty string (''), every
             subscriber with an organization string will not match this entry.
             
             If tPortEgrVPortHMOrgString is the wildcard symbol ('*'), every
             subscriber with an organization string will match this entry, if
             the tPortEgrVPortHMIntDestId matches.
                 
             Currently only the empty string ('') is accepted.";
          smiv2:max-access "not-accessible";
          smiv2:oid "1.3.6.1.4.1.6527.3.1.2.2.4.57.1.2";
        }
        leaf tPortEgrVPortHMRowStatus {
          type snmpv2-tc:RowStatus;
          description
            "The value of tPortEgrVPortHMRowStatus allows entries to be created
             and deleted in the tPortEgrVPortHostMatchTable.";
          reference
            "See definition of RowStatus in RFC 2579, 'Textual Conventions for
             SMIv2.'";
          smiv2:max-access "read-write";
          smiv2:oid "1.3.6.1.4.1.6527.3.1.2.2.4.57.1.3";
        }
        leaf tPortEgrVPortHMLastChgd {
          type yang:timestamp;
          description
            "The value of tPortEgrVPortHMLastChgd indicates the value of
             sysUpTime when the host match entry was last modified.";
          smiv2:max-access "read-only";
          smiv2:oid "1.3.6.1.4.1.6527.3.1.2.2.4.57.1.4";
        }
      }
      config false;
    }
    container tmnxOpticalPortCfgTable {
      description
        "The tmnxOpticalPortCfgTable has an entry for each DWDM Optical
         port on each IOM card in each chassis in the Alcatel SROS system.";
      smiv2:oid "1.3.6.1.4.1.6527.3.1.2.2.4.58";
      list tmnxOpticalPortCfgEntry {
        key "tmnxChassisIndex tmnxPortPortID";
        description
          "Each row entry represents an Optical port on a IOM card in a
           chassis in the system. Entries cannot be created and deleted via
           SNMP SET operations. The tmnxOpticalPortCfgEntry contains attributes
           that are unique to the Optical ports.";
        smiv2:oid "1.3.6.1.4.1.6527.3.1.2.2.4.58.1";
        leaf tmnxChassisIndex {
          type leafref {
            path "/timetra-chassis:TIMETRA-CHASSIS-MIB/timetra-chassis:tmnxChassisTable/timetra-chassis:tmnxChassisEntry/timetra-chassis:tmnxChassisIndex";
          }
          config true;
        }
        leaf tmnxPortPortID {
          type leafref {
            path "/timetra-port:TIMETRA-PORT-MIB/timetra-port:tmnxPortTable/timetra-port:tmnxPortEntry/timetra-port:tmnxPortPortID";
          }
          config true;
        }
        leaf tmnxOpticalPortAmpCfgAlarms {
          type timetra-port:TmnxOpticalAmpAlarm;
          description
            "The value of tmnxOpticalPortAmpCfgAlarms specifies the alarms that are
             monitored by the optical amplifier interface. If an alarm bit is
             set, then the corresponding alarm will generate a raise or clear
             notification when its state changes. An unset bit specifies that the
             alarm corresponding with the bit will not report on its state
             transitions.";
          smiv2:defval "{ampIld, ampTmp, ampMth, ampMtl, ampLos, ampLop, ampCom}";
          smiv2:max-access "read-write";
          smiv2:oid "1.3.6.1.4.1.6527.3.1.2.2.4.58.1.1";
          config true;
        }
        leaf tmnxOpticalPortTdcmCtrlMode {
          type timetra-port:TmnxOpticalDispCtrlMode;
          description
            "The value of tmnxOpticalPortTdcmCtrlMode specifies the current
             operational mode of the tunable dispersion compensation module.
             
             When tmnxOpticalPortTdcmCtrlMode is set to automatic, the dispersion
             setpoint can be retrieved from tmnxOpticalPortTdcmAutoDisp.
             
             When tmnxOpticalPortTdcmCtrlMode is set to manual, the dispersion
             setpoint can be configured with tmnxOpticalPortTdcmManCfgDisp.";
          smiv2:defval "automatic";
          smiv2:max-access "read-write";
          smiv2:oid "1.3.6.1.4.1.6527.3.1.2.2.4.58.1.2";
          config true;
        }
        leaf tmnxOpticalPortTdcmManCfgDisp {
          type int32 {
            range "-1200..1200";
          }
          units "picoseconds per nanometer";
          description
            "The value of tmnxOpticalPortTdcmManCfgDisp specifies the
             manually configured dispersion of the tunable dispersion
             compensation module. This parameter is valid when the
             tmnxOpticalPortTdcmCtrlMode is manual.
             Dispersion is expressed in pico-seconds per nano-meter (ps/nm).";
          smiv2:defval "0";
          smiv2:max-access "read-write";
          smiv2:oid "1.3.6.1.4.1.6527.3.1.2.2.4.58.1.3";
          config true;
        }
        leaf tmnxOpticalPortTdcmCfgRxChan {
          type timetra-port:TmnxOpticalDwdmChannel;
          description
            "tmnxOpticalPortTdcmCfgRxChan specifies the DWDM ITU channel at which
             the tunable dispersion compensation module should operate.
             
             If a value of zero(0) has been specified,
             tmnxOpticalPortTdcmPresRxChan will be changed by the system to be
             equivalent to tmnxPortDwdmLaserChannel.
             
             tmnxOpticalPortTdcmCfgRxChan should be set to the same value as
             tmnxPortDwdmLaserChannel in most cases, but may be set to a different
             value when the received wavelength is different from the transmitted
             wavelength.";
          smiv2:defval "0";
          smiv2:max-access "read-write";
          smiv2:oid "1.3.6.1.4.1.6527.3.1.2.2.4.58.1.4";
          config true;
        }
        leaf tmnxOpticalPortTdcmCfgAlarms {
          type timetra-port:TmnxOpticalTdcmAlarm;
          description
            "The value of tmnxOpticalPortTdcmCfgAlarms specifies the alarms that
             are monitored by the tunable dispersion compensation module's
             interface. If an alarm bit is set, then the corresponding alarm will
             generate a raise or clear notification when its state changes.
             An unset bit specifies that the alarm corresponding with the bit
             will not report on its state transitions.";
          smiv2:defval "{tdcmNotRdy, tdcmMth, tdcmMtl, tdcmUnLck, tdcmTmpLim, tdcmEprInv, tdcmCom}";
          smiv2:max-access "read-write";
          smiv2:oid "1.3.6.1.4.1.6527.3.1.2.2.4.58.1.5";
          config true;
        }
        leaf tmnxOpticalPortTdcmDispSwpStart {
          type int32 {
            range "-1200..1200";
          }
          units "picoseconds per nanometer";
          description
            "The value of tmnxOpticalPortTdcmDispSwpStart specifies the
             the start value for dispersion sweeping on a tunable dispersion
             compensation module. Dispersion is expressed in pico-seconds per
             nano-meter (ps/nm).";
          smiv2:defval "-1200";
          smiv2:max-access "read-write";
          smiv2:oid "1.3.6.1.4.1.6527.3.1.2.2.4.58.1.6";
          config true;
        }
        leaf tmnxOpticalPortTdcmDispSwpEnd {
          type int32 {
            range "-1200..1200";
          }
          units "picoseconds per nanometer";
          description
            "The value of tmnxOpticalPortTdcmDispSwpEnd specifies the
             the end value for dispersion sweeping on a tunable dispersion
             compensation module. Dispersion is expressed in pico-seconds per
             nano-meter (ps/nm).";
          smiv2:defval "1200";
          smiv2:max-access "read-write";
          smiv2:oid "1.3.6.1.4.1.6527.3.1.2.2.4.58.1.7";
          config true;
        }
        config true;
      }
      config true;
    }
    container tmnxOpticalPortOperTable {
      description
        "The tmnxOpticalPortOperTable has an entry for each DWDM Optical
         port on each IOM card in each chassis in the Alcatel SROS system.";
      smiv2:oid "1.3.6.1.4.1.6527.3.1.2.2.4.59";
      list tmnxOpticalPortOperEntry {
        key "tmnxChassisIndex tmnxPortPortID";
        description
          "Each row entry represents an Optical port on a IOM card in a
           chassis in the system. The tmnxOpticalPortOperEntry contains
           attributes that are unique to the Optical ports.";
        smiv2:oid "1.3.6.1.4.1.6527.3.1.2.2.4.59.1";
        leaf tmnxChassisIndex {
          type leafref {
            path "/timetra-chassis:TIMETRA-CHASSIS-MIB/timetra-chassis:tmnxChassisTable/timetra-chassis:tmnxChassisEntry/timetra-chassis:tmnxChassisIndex";
          }
        }
        leaf tmnxPortPortID {
          type leafref {
            path "/timetra-port:TIMETRA-PORT-MIB/timetra-port:tmnxPortTable/timetra-port:tmnxPortEntry/timetra-port:tmnxPortPortID";
          }
        }
        leaf tmnxOpticalPortHasRxAmplifier {
          type boolean;
          description
            "The value of tmnxOpticalPortHasRxAmplifier indicates whether or not
             the port has an optical amplifier on the receive path.";
          smiv2:max-access "read-only";
          smiv2:oid "1.3.6.1.4.1.6527.3.1.2.2.4.59.1.1";
        }
        leaf tmnxOpticalPortHasRxTdcm {
          type boolean;
          description
            "The value of tmnxOpticalPortHasRxTdcm indicates whether or not
             the port has an optical tunable dispersion compensation module
             on the receive path.";
          smiv2:max-access "read-only";
          smiv2:oid "1.3.6.1.4.1.6527.3.1.2.2.4.59.1.2";
        }
        leaf tmnxOpticalPortAmpPowerIn {
          type int32;
          units "mBm";
          description
            "The value of tmnxOpticalPortAmpPowerIn indicates the received average
             optical power at the input of the optical amplifier.
             
             The UNITS millibels (mBm) are units of 0.01 decibel relative to one
             milliwatt (0 dBm) or dBm multiplied by 100.
             The mBm is used when integers are required instead of floating point.
             For example: -5.21 dBm is equivalent to -521 mBm.";
          smiv2:max-access "read-only";
          smiv2:oid "1.3.6.1.4.1.6527.3.1.2.2.4.59.1.3";
        }
        leaf tmnxOpticalPortAmpGain {
          type uint32;
          units "mB";
          description
            "The value of tmnxOpticalPortAmpGain indicates the gain of the optical
             amplifier. The gain indicates how much the input signal is amplified.
             
             The UNITS millibels (mB) are units of 0.01 dB or dB multiplied by 100.
             The mB is used when integers are required instead of floating point.
             For example: 5.21 dB is equivalent to 521 mB.";
          smiv2:max-access "read-only";
          smiv2:oid "1.3.6.1.4.1.6527.3.1.2.2.4.59.1.4";
        }
        leaf tmnxOpticalPortAmpPowerOut {
          type int32;
          units "mBm";
          description
            "The value of tmnxOpticalPortAmpPowerOut indicates the optical power
             at the output of the optical amplifier.
             
             The UNITS millibels (mBm) are units of 0.01 decibel relative
             to one milliwatt (0 dBm) or dBm multiplied by 100.
             The mBm is used when integers are required instead of floating point.
             For example: -5.21 dBm is equivalent to -521 mBm.";
          smiv2:max-access "read-only";
          smiv2:oid "1.3.6.1.4.1.6527.3.1.2.2.4.59.1.5";
        }
        leaf tmnxOpticalPortAmpPumpTemp {
          type int32;
          units "millidegrees Celsius";
          description
            "The value of tmnxOpticalPortAmpPumpTemp indicates the current
             temperature of the optical amplifier's pump in millidegrees Celsius.";
          smiv2:max-access "read-only";
          smiv2:oid "1.3.6.1.4.1.6527.3.1.2.2.4.59.1.6";
        }
        leaf tmnxOpticalPortAmpModuleTemp {
          type int32;
          units "millidegrees Celsius";
          description
            "The value of tmnxOpticalPortAmpModuleTemp indicates the current
             temperature of the optical amplifier module's case in
             millidegrees Celsius.";
          smiv2:max-access "read-only";
          smiv2:oid "1.3.6.1.4.1.6527.3.1.2.2.4.59.1.7";
        }
        leaf tmnxOpticalPortAmpPumpCurrent {
          type uint32;
          units "microAmperes";
          description
            "The value of tmnxOpticalPortAmpPumpCurrent indicates the amount of
             electical current used by the optical amplifier's pump in
             microAmperes (uA).";
          smiv2:max-access "read-only";
          smiv2:oid "1.3.6.1.4.1.6527.3.1.2.2.4.59.1.8";
        }
        leaf tmnxOpticalPortAmpAlarmState {
          type timetra-port:TmnxOpticalAmpAlarm;
          description
            "The value of tmnxOpticalPortAmpAlarmState indicates which monitored
             alarms are raised against the optical amplifier's interface.";
          smiv2:max-access "read-only";
          smiv2:oid "1.3.6.1.4.1.6527.3.1.2.2.4.59.1.9";
        }
        leaf tmnxOpticalPortAmpSerialNum {
          type snmp-framework:SnmpAdminString {
            length "0..31";
          }
          description
            "The value of tmnxOpticalPortAmpSerialNum indicates the manufacturing
             serial number in ASCII characters as read from the optical amplifier
             module.
               
             An empty string indicates the serial number is unspecified.
             
             The string is expected to contain printable ASCII characters.
             Any unprintable ASCII characters read from the module will be 
             filtered out. The string will be NULL terminated.";
          smiv2:max-access "read-only";
          smiv2:oid "1.3.6.1.4.1.6527.3.1.2.2.4.59.1.10";
        }
        leaf tmnxOpticalPortAmpCtrlState {
          type timetra-port:TmnxOpticalAmpCtrlState;
          description
            "The value of tmnxOpticalPortAmpCtrlState indicates the state of the
             control loop that optimizes the receive optical power of to the
             MSA optics.";
          smiv2:max-access "read-only";
          smiv2:oid "1.3.6.1.4.1.6527.3.1.2.2.4.59.1.11";
        }
        leaf tmnxOpticalPortTdcmPowerIn {
          type int32;
          units "mBm";
          description
            "The value of tmnxOpticalPortTdcmPowerIn indicates the received average
             optical power at the input the tunable dispersion compensation module.
             
             The UNITS millibels (mBm) are units of 0.01 decibel relative
             to one milliwatt (0 dBm) or dBm multiplied by 100.
             The mBm is used when integers are required instead of floating point.
             For example: -5.21 dBm is equivalent to -521 mBm.";
          smiv2:max-access "read-only";
          smiv2:oid "1.3.6.1.4.1.6527.3.1.2.2.4.59.1.12";
        }
        leaf tmnxOpticalPortTdcmLoss {
          type uint32;
          units "mB";
          description
            "The value of tmnxOpticalPortTdcmLoss indicates the optical loss 
             occuring in the tunable dispersion compensation module.
             
             The UNITS millibels (mB) are units of 0.01 dB or dB multiplied by 100.
             The mB is used when integers are required instead of floating point.
             For example: 5.21 dB is equivalent to 521 mB.";
          smiv2:max-access "read-only";
          smiv2:oid "1.3.6.1.4.1.6527.3.1.2.2.4.59.1.13";
        }
        leaf tmnxOpticalPortTdcmPowerOut {
          type int32;
          units "mBm";
          description
            "The value of tmnxOpticalPortTdcmPowerOut indicates the optical power
             at the output of tunable dispersion compensation module.
             
             The UNITS millibels (mBm) are units of 0.01 decibel relative
             to one milliwatt (0 dBm) or dBm multiplied by 100.
             The mBm is used when integers are required instead of floating point.
             For example: -5.21 dBm is equivalent to -521 mBm.";
          smiv2:max-access "read-only";
          smiv2:oid "1.3.6.1.4.1.6527.3.1.2.2.4.59.1.14";
        }
        leaf tmnxOpticalPortTdcmRtd1Temp {
          type int32;
          units "millidegrees Celsius";
          description
            "The value of tmnxOpticalPortTdcmRtd1Temp indicates the current
             temperature of the tunable dispersion compensation module's first
             Resistance Temperature Detector (also known as a thermistor).
             The temperature is in units of millidegrees Celsius.";
          smiv2:max-access "read-only";
          smiv2:oid "1.3.6.1.4.1.6527.3.1.2.2.4.59.1.15";
        }
        leaf tmnxOpticalPortTdcmRtd2Temp {
          type int32;
          units "millidegrees Celsius";
          description
            "The value of tmnxOpticalPortTdcmRtd2Temp indicates the current
             temperature of the tunable dispersion compensation module's second
             Resistance Temperature Detector (also known as a thermistor).
             The temperature is in units of millidegrees Celsius.";
          smiv2:max-access "read-only";
          smiv2:oid "1.3.6.1.4.1.6527.3.1.2.2.4.59.1.16";
        }
        leaf tmnxOpticalPortTdcmRtd3Temp {
          type int32;
          units "millidegrees Celsius";
          description
            "The value of tmnxOpticalPortTdcmRtd3Temp indicates the current
             temperature of the tunable dispersion compensation module's third
             Resistance Temperature Detector (also known as a thermistor).
             The temperature is in units of millidegrees Celsius.";
          smiv2:max-access "read-only";
          smiv2:oid "1.3.6.1.4.1.6527.3.1.2.2.4.59.1.17";
        }
        leaf tmnxOpticalPortTdcmRtd4Temp {
          type int32;
          units "millidegrees Celsius";
          description
            "The value of tmnxOpticalPortTdcmRtd4Temp indicates the current
             temperature of the tunable dispersion compensation module's fourth
             Resistance Temperature Detector (also known as a thermistor).
             The temperature is in units of millidegrees Celsius.";
          smiv2:max-access "read-only";
          smiv2:oid "1.3.6.1.4.1.6527.3.1.2.2.4.59.1.18";
        }
        leaf tmnxOpticalPortTdcmModuleTemp {
          type int32;
          units "millidegrees Celsius";
          description
            "The value of tmnxOpticalPortTdcmModuleTemp indicates the current
             temperature of the tunable dispersion compensation module's case in
             millidegrees Celsius.";
          smiv2:max-access "read-only";
          smiv2:oid "1.3.6.1.4.1.6527.3.1.2.2.4.59.1.19";
        }
        leaf tmnxOpticalPortTdcmMinDisp {
          type int32;
          units "picoseconds per nanometer";
          description
            "The value of tmnxOpticalPortTdcmMinDisp indicates the minimum
             configurable dispersion of the tunable dispersion compensation
             module. Dispersion is expressed in pico-seconds per nano-meter
             (ps/nm).";
          smiv2:max-access "read-only";
          smiv2:oid "1.3.6.1.4.1.6527.3.1.2.2.4.59.1.20";
        }
        leaf tmnxOpticalPortTdcmMaxDisp {
          type int32;
          units "picoseconds per nanometer";
          description
            "The value of tmnxOpticalPortTdcmMaxDisp indicates the maximum
             configurable dispersion of the tunable dispersion compensation
             module. Dispersion is expressed in pico-seconds per nano-meter
             (ps/nm).";
          smiv2:max-access "read-only";
          smiv2:oid "1.3.6.1.4.1.6527.3.1.2.2.4.59.1.21";
        }
        leaf tmnxOpticalPortTdcmAutoDisp {
          type int32;
          units "picoseconds per nanometer";
          description
            "The value of tmnxOpticalPortTdcmAutoDisp indicates the currently
             auto-configured dispersion of the tunable dispersion compensation
             module. Dispersion is expressed in pico-seconds per nano-meter
             (ps/nm).";
          smiv2:max-access "read-only";
          smiv2:oid "1.3.6.1.4.1.6527.3.1.2.2.4.59.1.22";
        }
        leaf tmnxOpticalPortTdcmMeasDisp {
          type int32;
          units "picoseconds per nanometer";
          description
            "The value of tmnxOpticalPortTdcmMeasDisp indicates the dynamically
             measured dispersion of the tunable dispersion compensation
             module. Dispersion is expressed in pico-seconds per nano-meter
             (ps/nm).";
          smiv2:max-access "read-only";
          smiv2:oid "1.3.6.1.4.1.6527.3.1.2.2.4.59.1.23";
        }
        leaf tmnxOpticalPortTdcmPresRxChan {
          type timetra-port:TmnxOpticalDwdmChannel;
          description
            "tmnxOpticalPortTdcmPresRxChan indicates the DWDM ITU channel at which
             the tunable dispersion compensation module is operating.";
          smiv2:max-access "read-only";
          smiv2:oid "1.3.6.1.4.1.6527.3.1.2.2.4.59.1.24";
        }
        leaf tmnxOpticalPortTdcmAlarmState {
          type timetra-port:TmnxOpticalTdcmAlarm;
          description
            "The value of tmnxOpticalPortTdcmAlarmState indicates which monitored
             alarms are raised against the dispersion compensation module's
             interface.";
          smiv2:max-access "read-only";
          smiv2:oid "1.3.6.1.4.1.6527.3.1.2.2.4.59.1.25";
        }
        leaf tmnxOpticalPortTdcmSerialNum {
          type snmp-framework:SnmpAdminString {
            length "0..31";
          }
          description
            "The value of tmnxOpticalPortTdcmSerialNum indicates the
             manufacturing serial number in ASCII characters as read from the
             tunable dispersion compensation module.
             
             An empty string indicates the serial number is unspecified.
             
             The string is expected to contain printable ASCII characters.
             Any unprintable ASCII characters read from the module will be 
             filtered out. The string will be NULL terminated.";
          smiv2:max-access "read-only";
          smiv2:oid "1.3.6.1.4.1.6527.3.1.2.2.4.59.1.26";
        }
        leaf tmnxOpticalPortTdcmCtrlState {
          type timetra-port:TmnxOpticalTdcmCtrlState;
          description
            "The TmnxOpticalTdcmCtrlState indicates the state of the control loop
             that optimizes the dispersion by tuning the dispersion compensation
             module to the set point at which the FEC corrected error rate is the
             lowest.";
          smiv2:max-access "read-only";
          smiv2:oid "1.3.6.1.4.1.6527.3.1.2.2.4.59.1.27";
        }
        leaf tmnxOpticalPortDwdmChannelMin {
          type timetra-port:TmnxOpticalDwdmChannel;
          description
            "tmnxOpticalPortDwdmChannelMin indicates the minimum DWDM ITU channel
             supported by a tunable optical interface.";
          smiv2:max-access "read-only";
          smiv2:oid "1.3.6.1.4.1.6527.3.1.2.2.4.59.1.28";
        }
        leaf tmnxOpticalPortDwdmChannelMax {
          type timetra-port:TmnxOpticalDwdmChannel;
          description
            "tmnxOpticalPortDwdmChannelMax indicates the maximum DWDM ITU channel
             supported by a tunable optical interface.";
          smiv2:max-access "read-only";
          smiv2:oid "1.3.6.1.4.1.6527.3.1.2.2.4.59.1.29";
        }
        leaf tmnxOpticalPortLaserTunability {
          type enumeration {
            enum "unequipped" {
              value 0;
            }
            enum "notTunable" {
              value 1;
            }
            enum "fullyTunable" {
              value 2;
            }
          }
          description
            "tmnxOpticalPortLaserTunability indicates if the optical interface
             laser is tunable or fixed. Value 'unequipped(0)' indicates that the
             optical interface is not equipped with a laser.";
          smiv2:max-access "read-only";
          smiv2:oid "1.3.6.1.4.1.6527.3.1.2.2.4.59.1.30";
        }
      }
      config false;
    }
    container tmnxPortEgrExpShaperTable {
      description
        "The tmnxPortEgrExpShaperTable contains the information of each 
         egress expanded shaper at the port level configured on this system.";
      smiv2:oid "1.3.6.1.4.1.6527.3.1.2.2.4.61";
      list tmnxPortEgrExpShaperEntry {
        key "tmnxChassisIndex tmnxPortPortID tmnxPortEgrExpShaperName";
        description
          "Each row in tmnxPortEgrExpShaperEntry represents a particular 
           egress expanded secondary shaper at the port level specified by 
           tmnxPortEgrExpShaperName.";
        smiv2:oid "1.3.6.1.4.1.6527.3.1.2.2.4.61.1";
        leaf tmnxChassisIndex {
          type leafref {
            path "/timetra-chassis:TIMETRA-CHASSIS-MIB/timetra-chassis:tmnxChassisTable/timetra-chassis:tmnxChassisEntry/timetra-chassis:tmnxChassisIndex";
          }
          config true;
        }
        leaf tmnxPortPortID {
          type leafref {
            path "/timetra-port:TIMETRA-PORT-MIB/timetra-port:tmnxPortTable/timetra-port:tmnxPortEntry/timetra-port:tmnxPortPortID";
          }
          config true;
        }
        leaf tmnxPortEgrExpShaperName {
          type timetra-tc:TNamedItem;
          description
            "The value of tmnxPortEgrExpShaperName specifies the expanded shaper 
             name on the egress side of this port.";
          smiv2:max-access "not-accessible";
          smiv2:oid "1.3.6.1.4.1.6527.3.1.2.2.4.61.1.1";
          config true;
        }
        leaf tmnxPortEgrExpShaperRowStatus {
          type snmpv2-tc:RowStatus;
          description
            "The value of tmnxPortEgrExpShaperRowStatus specifies the row-status of
             this entry in this table.";
          smiv2:max-access "read-write";
          smiv2:oid "1.3.6.1.4.1.6527.3.1.2.2.4.61.1.2";
          config false;
        }
        leaf tmnxPortEgrExpShaperRate {
          type timetra-tc:TExpSecondaryShaperPIRRate;
          units "Kbps";
          description
            "The value of tmnxPortEgrExpShaperRate specifies the explicit
             maximum frame based bandwidth limit, in kilobits per second, of this
             egress port expanded secondary shaper as a whole.";
          smiv2:defval "-1";
          smiv2:max-access "read-write";
          smiv2:oid "1.3.6.1.4.1.6527.3.1.2.2.4.61.1.3";
          config true;
        }
        leaf tmnxPortEgrExpShaperClass1Rate {
          type timetra-tc:TExpSecondaryShaperClassRate;
          units "Kbps";
          description
            "The value of tmnxPortEgrExpShaperClass1Rate specifies the explicit
             maximum frame based bandwidth limit, in kilobits per second, of the
             Class 1 traffic using this egress port expanded secondary shaper.";
          smiv2:defval "-1";
          smiv2:max-access "read-write";
          smiv2:oid "1.3.6.1.4.1.6527.3.1.2.2.4.61.1.4";
          config true;
        }
        leaf tmnxPortEgrExpShaperClass2Rate {
          type timetra-tc:TExpSecondaryShaperClassRate;
          units "Kbps";
          description
            "The value of tmnxPortEgrExpShaperClass2Rate specifies the explicit
             maximum frame based bandwidth limit, in kilobits per second, of the
             Class 2 traffic using this egress port expanded secondary shaper.";
          smiv2:defval "-1";
          smiv2:max-access "read-write";
          smiv2:oid "1.3.6.1.4.1.6527.3.1.2.2.4.61.1.5";
          config true;
        }
        leaf tmnxPortEgrExpShaperClass3Rate {
          type timetra-tc:TExpSecondaryShaperClassRate;
          units "Kbps";
          description
            "The value of tmnxPortEgrExpShaperClass3Rate specifies the explicit
             maximum frame based bandwidth limit, in kilobits per second, of the
             Class 3 traffic using this egress port expanded secondary shaper.";
          smiv2:defval "-1";
          smiv2:max-access "read-write";
          smiv2:oid "1.3.6.1.4.1.6527.3.1.2.2.4.61.1.6";
          config true;
        }
        leaf tmnxPortEgrExpShaperClass4Rate {
          type timetra-tc:TExpSecondaryShaperClassRate;
          units "Kbps";
          description
            "The value of tmnxPortEgrExpShaperClass4Rate specifies the explicit
             maximum frame based bandwidth limit, in kilobits per second, of the
             Class 4 traffic using this egress port expanded secondary shaper.";
          smiv2:defval "-1";
          smiv2:max-access "read-write";
          smiv2:oid "1.3.6.1.4.1.6527.3.1.2.2.4.61.1.7";
          config true;
        }
        leaf tmnxPortEgrExpShaperClass5Rate {
          type timetra-tc:TExpSecondaryShaperClassRate;
          units "Kbps";
          description
            "The value of tmnxPortEgrExpShaperClass5Rate specifies the explicit
             maximum frame based bandwidth limit, in kilobits per second, of the
             Class 5 traffic using this egress port expanded secondary shaper.";
          smiv2:defval "-1";
          smiv2:max-access "read-write";
          smiv2:oid "1.3.6.1.4.1.6527.3.1.2.2.4.61.1.8";
          config true;
        }
        leaf tmnxPortEgrExpShaperClass6Rate {
          type timetra-tc:TExpSecondaryShaperClassRate;
          units "Kbps";
          description
            "The value of tmnxPortEgrExpShaperClass6Rate specifies the explicit
             maximum frame based bandwidth limit, in kilobits per second, of the
             Class 6 traffic using this egress port expanded secondary shaper.";
          smiv2:defval "-1";
          smiv2:max-access "read-write";
          smiv2:oid "1.3.6.1.4.1.6527.3.1.2.2.4.61.1.9";
          config true;
        }
        leaf tmnxPortEgrExpShaperClass7Rate {
          type timetra-tc:TExpSecondaryShaperClassRate;
          units "Kbps";
          description
            "The value of tmnxPortEgrExpShaperClass7Rate specifies the explicit
             maximum frame based bandwidth limit, in kilobits per second, of the
             Class 7 traffic using this egress port expanded secondary shaper.";
          smiv2:defval "-1";
          smiv2:max-access "read-write";
          smiv2:oid "1.3.6.1.4.1.6527.3.1.2.2.4.61.1.10";
          config true;
        }
        leaf tmnxPortEgrExpShaperClass8Rate {
          type timetra-tc:TExpSecondaryShaperClassRate;
          units "Kbps";
          description
            "The value of tmnxPortEgrExpShaperClass8Rate specifies the explicit
             maximum frame based bandwidth limit, in kilobits per second, of the
             Class 8 traffic using this egress port expanded secondary shaper.";
          smiv2:defval "-1";
          smiv2:max-access "read-write";
          smiv2:oid "1.3.6.1.4.1.6527.3.1.2.2.4.61.1.11";
          config true;
        }
        leaf tmnxPortEgrExpShaperLastChanged {
          type yang:timestamp;
          description
            "The value of tmnxPortEgrExpShaperLastChanged indicates the value of
             sysUpTime when the egress expanded shaper entry was last modified.";
          smiv2:max-access "read-only";
          smiv2:oid "1.3.6.1.4.1.6527.3.1.2.2.4.61.1.12";
          config false;
        }
        leaf tmnxPortEgrExpShaperLoBrstMaxCls {
          type uint32 {
            range "1..8";
          }
          description
            "The value of tmnxPortEgrExpShaperLoBrstMaxCls specifies which class
             should use the low priority burst threshold.
             
             All classes starting from 1, up to and including that specified by
             tmnxPortEgrExpShaperLoBrstMaxCls use the low priority burst threshold.
             
             All classes greater than the value of tmnxPortEgrExpShaperLoBrstMaxCls
             up to and including class 8 use the high priority burst threshold.";
          smiv2:defval "8";
          smiv2:max-access "read-write";
          smiv2:oid "1.3.6.1.4.1.6527.3.1.2.2.4.61.1.13";
          config true;
        }
        leaf tmnxPortEgrExpShaperClass1Thresh {
          type int32 {
            range "-1..8190";
          }
          units "kbytes";
          description
            "The tmnxPortEgrExpShaperClass1Thresh specifies the monitoring
             non-conformance burst threshold for the exp-secondary-shaper class-1.
             When set to default value '-1', the system will adopt a suitable
             default setting for this threshold.";
          smiv2:defval "-1";
          smiv2:max-access "read-write";
          smiv2:oid "1.3.6.1.4.1.6527.3.1.2.2.4.61.1.14";
          config true;
        }
        leaf tmnxPortEgrExpShaperClass2Thresh {
          type int32 {
            range "-1..8190";
          }
          units "kbytes";
          description
            "The tmnxPortEgrExpShaperClass2Thresh specifies the monitoring
             non-conformance burst threshold for the exp-secondary-shaper class-2.
             When set to default value '-1', the system will adopt a suitable
             default setting for this threshold.";
          smiv2:defval "-1";
          smiv2:max-access "read-write";
          smiv2:oid "1.3.6.1.4.1.6527.3.1.2.2.4.61.1.15";
          config true;
        }
        leaf tmnxPortEgrExpShaperClass3Thresh {
          type int32 {
            range "-1..8190";
          }
          units "kbytes";
          description
            "The tmnxPortEgrExpShaperClass3Thresh specifies the monitoring
             non-conformance burst threshold for the exp-secondary-shaper class-3.
             When set to default value '-1', the system will adopt a suitable
             default setting for this threshold.";
          smiv2:defval "-1";
          smiv2:max-access "read-write";
          smiv2:oid "1.3.6.1.4.1.6527.3.1.2.2.4.61.1.16";
          config true;
        }
        leaf tmnxPortEgrExpShaperClass4Thresh {
          type int32 {
            range "-1..8190";
          }
          units "kbytes";
          description
            "The tmnxPortEgrExpShaperClass4Thresh specifies the monitoring
             non-conformance burst threshold for the exp-secondary-shaper class-4.
             When set to default value '-1', the system will adopt a suitable
             default setting for this threshold.";
          smiv2:defval "-1";
          smiv2:max-access "read-write";
          smiv2:oid "1.3.6.1.4.1.6527.3.1.2.2.4.61.1.17";
          config true;
        }
        leaf tmnxPortEgrExpShaperClass5Thresh {
          type int32 {
            range "-1..8190";
          }
          units "kbytes";
          description
            "The tmnxPortEgrExpShaperClass5Thresh specifies the monitoring
             non-conformance burst threshold for the exp-secondary-shaper class-5.
             When set to default value '-1', the system will adopt a suitable
             default setting for this threshold.";
          smiv2:defval "-1";
          smiv2:max-access "read-write";
          smiv2:oid "1.3.6.1.4.1.6527.3.1.2.2.4.61.1.18";
          config true;
        }
        leaf tmnxPortEgrExpShaperClass6Thresh {
          type int32 {
            range "-1..8190";
          }
          units "kbytes";
          description
            "The tmnxPortEgrExpShaperClass6Thresh specifies the monitoring
             non-conformance burst threshold for the exp-secondary-shaper class-6.
             When set to default value '-1', the system will adopt a suitable
             default setting for this threshold.";
          smiv2:defval "-1";
          smiv2:max-access "read-write";
          smiv2:oid "1.3.6.1.4.1.6527.3.1.2.2.4.61.1.19";
          config true;
        }
        leaf tmnxPortEgrExpShaperClass7Thresh {
          type int32 {
            range "-1..8190";
          }
          units "kbytes";
          description
            "The tmnxPortEgrExpShaperClass7Thresh specifies the monitoring
             non-conformance burst threshold for the exp-secondary-shaper class-7.
             When set to default value '-1', the system will adopt a suitable
             default setting for this threshold.";
          smiv2:defval "-1";
          smiv2:max-access "read-write";
          smiv2:oid "1.3.6.1.4.1.6527.3.1.2.2.4.61.1.20";
          config true;
        }
        leaf tmnxPortEgrExpShaperClass8Thresh {
          type int32 {
            range "-1..8190";
          }
          units "kbytes";
          description
            "The tmnxPortEgrExpShaperClass8Thresh specifies the monitoring
             non-conformance burst threshold for the exp-secondary-shaper class-8.
             When set to default value '-1', the system will adopt a suitable
             default setting for this threshold.";
          smiv2:defval "-1";
          smiv2:max-access "read-write";
          smiv2:oid "1.3.6.1.4.1.6527.3.1.2.2.4.61.1.21";
          config true;
        }
        leaf tmnxPortEgrExpShaperThresh {
          type int32 {
            range "-1..8190";
          }
          units "kbytes";
          description
            "The tmnxPortEgrExpShaperThresh specifies the monitoring non-conformance
             burst threshold for the aggregate exp-secondary-shaper.  When set to 
             default value '-1', the system will adopt a suitable default setting 
             for this threshold.";
          smiv2:defval "-1";
          smiv2:max-access "read-write";
          smiv2:oid "1.3.6.1.4.1.6527.3.1.2.2.4.61.1.22";
          config true;
        }
        leaf tmnxPortEgrExpShaperLoBurstLimit {
          type timetra-tc:TClassBurstLimit;
          units "bytes";
          description
            "The tmnxPortEgrExpShaperLoBurstLimit specifies the number of bytes to 
             be used as the low burst threshold for the aggregate rate of the 
             classes pertaining to the low burst threshold in the expanded secondary
             shaper.";
          smiv2:defval "-1";
          smiv2:max-access "read-write";
          smiv2:oid "1.3.6.1.4.1.6527.3.1.2.2.4.61.1.23";
          config true;
        }
        leaf tmnxPortEgrExpShaperHiBurstInc {
          type int32 {
            range "-1..65528";
          }
          units "bytes";
          description
            "The tmnxPortEgrExpShaperHiBurstInc specifies the incremental number of
             bytes above the low burst limit to be used as the high burst threshold 
             for the aggregate rate of the classes pertaining to the high burst 
             threshold in the expanded secondary shaper. When set to the default 
             value '-1', the system will default to a value of '4000' bytes.";
          smiv2:defval "-1";
          smiv2:max-access "read-write";
          smiv2:oid "1.3.6.1.4.1.6527.3.1.2.2.4.61.1.24";
          config true;
        }
        leaf tmnxPortEgrExpShaperCl1BrstLimit {
          type timetra-tc:TClassBurstLimit;
          units "bytes";
          description
            "The value of tmnxPortEgrExpShaperCl1BrstLimit specifies the explicit 
             shaping burst size of the class.";
          smiv2:defval "-1";
          smiv2:max-access "read-write";
          smiv2:oid "1.3.6.1.4.1.6527.3.1.2.2.4.61.1.25";
          config true;
        }
        leaf tmnxPortEgrExpShaperCl2BrstLimit {
          type timetra-tc:TClassBurstLimit;
          units "bytes";
          description
            "The value of tmnxPortEgrExpShaperCl2BrstLimit specifies the explicit 
             shaping burst size of the class.";
          smiv2:defval "-1";
          smiv2:max-access "read-write";
          smiv2:oid "1.3.6.1.4.1.6527.3.1.2.2.4.61.1.26";
          config true;
        }
        leaf tmnxPortEgrExpShaperCl3BrstLimit {
          type timetra-tc:TClassBurstLimit;
          units "bytes";
          description
            "The value of tmnxPortEgrExpShaperCl3BrstLimit specifies the explicit 
             shaping burst size of the class.";
          smiv2:defval "-1";
          smiv2:max-access "read-write";
          smiv2:oid "1.3.6.1.4.1.6527.3.1.2.2.4.61.1.27";
          config true;
        }
        leaf tmnxPortEgrExpShaperCl4BrstLimit {
          type timetra-tc:TClassBurstLimit;
          units "bytes";
          description
            "The value of tmnxPortEgrExpShaperCl4BrstLimit specifies the explicit 
             shaping burst size of the class.";
          smiv2:defval "-1";
          smiv2:max-access "read-write";
          smiv2:oid "1.3.6.1.4.1.6527.3.1.2.2.4.61.1.28";
          config true;
        }
        leaf tmnxPortEgrExpShaperCl5BrstLimit {
          type timetra-tc:TClassBurstLimit;
          units "bytes";
          description
            "The value of tmnxPortEgrExpShaperCl5BrstLimit specifies the explicit 
             shaping burst size of the class.";
          smiv2:defval "-1";
          smiv2:max-access "read-write";
          smiv2:oid "1.3.6.1.4.1.6527.3.1.2.2.4.61.1.29";
          config true;
        }
        leaf tmnxPortEgrExpShaperCl6BrstLimit {
          type timetra-tc:TClassBurstLimit;
          units "bytes";
          description
            "The value of tmnxPortEgrExpShaperCl6BrstLimit specifies the explicit 
             shaping burst size of the class.";
          smiv2:defval "-1";
          smiv2:max-access "read-write";
          smiv2:oid "1.3.6.1.4.1.6527.3.1.2.2.4.61.1.30";
          config true;
        }
        leaf tmnxPortEgrExpShaperCl7BrstLimit {
          type timetra-tc:TClassBurstLimit;
          units "bytes";
          description
            "The value of tmnxPortEgrExpShaperCl7BrstLimit specifies the explicit 
             shaping burst size of the class.";
          smiv2:defval "-1";
          smiv2:max-access "read-write";
          smiv2:oid "1.3.6.1.4.1.6527.3.1.2.2.4.61.1.31";
          config true;
        }
        leaf tmnxPortEgrExpShaperCl8BrstLimit {
          type timetra-tc:TClassBurstLimit;
          units "bytes";
          description
            "The value of tmnxPortEgrExpShaperCl8BrstLimit specifies the explicit 
             shaping burst size of the class.";
          smiv2:defval "-1";
          smiv2:max-access "read-write";
          smiv2:oid "1.3.6.1.4.1.6527.3.1.2.2.4.61.1.32";
          config true;
        }
        config true;
      }
      config true;
    }
    container tPortEgrExpShaperStatsTable {
      description
        "The tPortEgrExpShaperStatsTable contains the statistics of each 
         egress expanded shaper at the port level configured on this system.
         Most objects are represented in 64 bit. 32-bit version of the objects
         are available in tPortEgrExpShaperStatsHLTable.";
      smiv2:oid "1.3.6.1.4.1.6527.3.1.2.2.4.62";
      list tPortEgrExpShaperStatsEntry {
        key "tmnxChassisIndex tmnxPortPortID tmnxPortEgrExpShaperName";
        description
          "Each row in tPortEgrExpShaperStatsEntry represents a particular 
           egress expanded secondary shaper statistics at the port level specified
           by tmnxPortEgrExpShaperName.";
        smiv2:oid "1.3.6.1.4.1.6527.3.1.2.2.4.62.1";
        leaf tmnxChassisIndex {
          type leafref {
            path "/timetra-chassis:TIMETRA-CHASSIS-MIB/timetra-chassis:tmnxChassisTable/timetra-chassis:tmnxChassisEntry/timetra-chassis:tmnxChassisIndex";
          }
        }
        leaf tmnxPortPortID {
          type leafref {
            path "/timetra-port:TIMETRA-PORT-MIB/timetra-port:tmnxPortTable/timetra-port:tmnxPortEntry/timetra-port:tmnxPortPortID";
          }
        }
        leaf tmnxPortEgrExpShaperName {
          type leafref {
            path "/timetra-port:TIMETRA-PORT-MIB/timetra-port:tmnxPortEgrExpShaperTable/timetra-port:tmnxPortEgrExpShaperEntry/timetra-port:tmnxPortEgrExpShaperName";
          }
        }
        leaf tPortEgrExpShaperStLstClrdTime {
          type yang:timestamp;
          description
            "The value of tPortEgrExpShaperStLstClrdTime indicates the sysUpTime
             when the counters in this table were last cleared.";
          smiv2:max-access "read-only";
          smiv2:oid "1.3.6.1.4.1.6527.3.1.2.2.4.62.1.1";
        }
        leaf tPortEgrExpShaperCls1StFwdPkts {
          type yang:counter64;
          description
            "The value of tPortEgrExpShaperCls1StFwdPkts indicates the number of 
             packets forwarded by the class '1' egress expanded shaper.";
          smiv2:max-access "read-only";
          smiv2:oid "1.3.6.1.4.1.6527.3.1.2.2.4.62.1.2";
        }
        leaf tPortEgrExpShaperCls1StFwdOcts {
          type yang:counter64;
          description
            "The value of tPortEgrExpShaperCls1StFwdOcts indicates the number of 
             octets forwarded by the class '1' egress expanded shaper.";
          smiv2:max-access "read-only";
          smiv2:oid "1.3.6.1.4.1.6527.3.1.2.2.4.62.1.3";
        }
        leaf tPortEgrExpShaperCls1StMonOvrOct {
          type yang:counter64;
          description
            "The value of tPortEgrExpShaperCls1StMonOvrOct indicates the number of 
             octets above the configured monitor-threshold (since last read) by 
             the class '1' egress expanded shaper.";
          smiv2:max-access "read-only";
          smiv2:oid "1.3.6.1.4.1.6527.3.1.2.2.4.62.1.4";
        }
        leaf tPortEgrExpShaperCls2StFwdPkts {
          type yang:counter64;
          description
            "The value of tPortEgrExpShaperCls2StFwdPkts indicates the number of 
             packets forwarded by the class '2' egress expanded shaper.";
          smiv2:max-access "read-only";
          smiv2:oid "1.3.6.1.4.1.6527.3.1.2.2.4.62.1.5";
        }
        leaf tPortEgrExpShaperCls2StFwdOcts {
          type yang:counter64;
          description
            "The value of tPortEgrExpShaperCls2StFwdOcts indicates the number of 
             octets forwarded by the class '2' egress expanded shaper.";
          smiv2:max-access "read-only";
          smiv2:oid "1.3.6.1.4.1.6527.3.1.2.2.4.62.1.6";
        }
        leaf tPortEgrExpShaperCls2StMonOvrOct {
          type yang:counter64;
          description
            "The value of tPortEgrExpShaperCls2StMonOvrOct indicates the number of 
             octets above the configured monitor-threshold (since last read) by 
             the class '2' egress expanded shaper.";
          smiv2:max-access "read-only";
          smiv2:oid "1.3.6.1.4.1.6527.3.1.2.2.4.62.1.7";
        }
        leaf tPortEgrExpShaperCls3StFwdPkts {
          type yang:counter64;
          description
            "The value of tPortEgrExpShaperCls3StFwdPkts indicates the number of 
             packets forwarded by the class '3' egress expanded shaper.";
          smiv2:max-access "read-only";
          smiv2:oid "1.3.6.1.4.1.6527.3.1.2.2.4.62.1.8";
        }
        leaf tPortEgrExpShaperCls3StFwdOcts {
          type yang:counter64;
          description
            "The value of tPortEgrExpShaperCls3StFwdOcts indicates the number of 
             octets forwarded by the class '3' egress expanded shaper.";
          smiv2:max-access "read-only";
          smiv2:oid "1.3.6.1.4.1.6527.3.1.2.2.4.62.1.9";
        }
        leaf tPortEgrExpShaperCls3StMonOvrOct {
          type yang:counter64;
          description
            "The value of tPortEgrExpShaperCls3StMonOvrOct indicates the number of 
             octets above the configured monitor-threshold (since last read) by 
             the class '3' egress expanded shaper.";
          smiv2:max-access "read-only";
          smiv2:oid "1.3.6.1.4.1.6527.3.1.2.2.4.62.1.10";
        }
        leaf tPortEgrExpShaperCls4StFwdPkts {
          type yang:counter64;
          description
            "The value of tPortEgrExpShaperCls4StFwdPkts indicates the number of 
             packets forwarded by the class '4' egress expanded shaper.";
          smiv2:max-access "read-only";
          smiv2:oid "1.3.6.1.4.1.6527.3.1.2.2.4.62.1.11";
        }
        leaf tPortEgrExpShaperCls4StFwdOcts {
          type yang:counter64;
          description
            "The value of tPortEgrExpShaperCls4StFwdOcts indicates the number of 
             octets forwarded by the class '4' egress expanded shaper.";
          smiv2:max-access "read-only";
          smiv2:oid "1.3.6.1.4.1.6527.3.1.2.2.4.62.1.12";
        }
        leaf tPortEgrExpShaperCls4StMonOvrOct {
          type yang:counter64;
          description
            "The value of tPortEgrExpShaperCls4StMonOvrOct indicates the number of 
             octets above the configured monitor-threshold (since last read) by 
             the class '4' egress expanded shaper.";
          smiv2:max-access "read-only";
          smiv2:oid "1.3.6.1.4.1.6527.3.1.2.2.4.62.1.13";
        }
        leaf tPortEgrExpShaperCls5StFwdPkts {
          type yang:counter64;
          description
            "The value of tPortEgrExpShaperCls5StFwdPkts indicates the number of 
             packets forwarded by the class '5' egress expanded shaper.";
          smiv2:max-access "read-only";
          smiv2:oid "1.3.6.1.4.1.6527.3.1.2.2.4.62.1.14";
        }
        leaf tPortEgrExpShaperCls5StFwdOcts {
          type yang:counter64;
          description
            "The value of tPortEgrExpShaperCls5StFwdOcts indicates the number of 
             octets forwarded by the class '5' egress expanded shaper.";
          smiv2:max-access "read-only";
          smiv2:oid "1.3.6.1.4.1.6527.3.1.2.2.4.62.1.15";
        }
        leaf tPortEgrExpShaperCls5StMonOvrOct {
          type yang:counter64;
          description
            "The value of tPortEgrExpShaperCls5StMonOvrOct indicates the number of 
             octets above the configured monitor-threshold (since last read) by 
             the class '5' egress expanded shaper.";
          smiv2:max-access "read-only";
          smiv2:oid "1.3.6.1.4.1.6527.3.1.2.2.4.62.1.16";
        }
        leaf tPortEgrExpShaperCls6StFwdPkts {
          type yang:counter64;
          description
            "The value of tPortEgrExpShaperCls6StFwdPkts indicates the number of 
             packets forwarded by the class '6' egress expanded shaper.";
          smiv2:max-access "read-only";
          smiv2:oid "1.3.6.1.4.1.6527.3.1.2.2.4.62.1.17";
        }
        leaf tPortEgrExpShaperCls6StFwdOcts {
          type yang:counter64;
          description
            "The value of tPortEgrExpShaperCls6StFwdOcts indicates the number of 
             octets forwarded by the class '6' egress expanded shaper.";
          smiv2:max-access "read-only";
          smiv2:oid "1.3.6.1.4.1.6527.3.1.2.2.4.62.1.18";
        }
        leaf tPortEgrExpShaperCls6StMonOvrOct {
          type yang:counter64;
          description
            "The value of tPortEgrExpShaperCls6StMonOvrOct indicates the number of 
             octets above the configured monitor-threshold (since last read) by 
             the class '6' egress expanded shaper.";
          smiv2:max-access "read-only";
          smiv2:oid "1.3.6.1.4.1.6527.3.1.2.2.4.62.1.19";
        }
        leaf tPortEgrExpShaperCls7StFwdPkts {
          type yang:counter64;
          description
            "The value of tPortEgrExpShaperCls7StFwdPkts indicates the number of 
             packets forwarded by the class '7' egress expanded shaper.";
          smiv2:max-access "read-only";
          smiv2:oid "1.3.6.1.4.1.6527.3.1.2.2.4.62.1.20";
        }
        leaf tPortEgrExpShaperCls7StFwdOcts {
          type yang:counter64;
          description
            "The value of tPortEgrExpShaperCls7StFwdOcts indicates the number of 
             octets forwarded by the class '7' egress expanded shaper.";
          smiv2:max-access "read-only";
          smiv2:oid "1.3.6.1.4.1.6527.3.1.2.2.4.62.1.21";
        }
        leaf tPortEgrExpShaperCls7StMonOvrOct {
          type yang:counter64;
          description
            "The value of tPortEgrExpShaperCls7StMonOvrOct indicates the number of 
             octets above the configured monitor-threshold (since last read) by 
             the class '7' egress expanded shaper.";
          smiv2:max-access "read-only";
          smiv2:oid "1.3.6.1.4.1.6527.3.1.2.2.4.62.1.22";
        }
        leaf tPortEgrExpShaperCls8StFwdPkts {
          type yang:counter64;
          description
            "The value of tPortEgrExpShaperCls8StFwdPkts indicates the number of 
             packets forwarded by the class '8' egress expanded shaper.";
          smiv2:max-access "read-only";
          smiv2:oid "1.3.6.1.4.1.6527.3.1.2.2.4.62.1.23";
        }
        leaf tPortEgrExpShaperCls8StFwdOcts {
          type yang:counter64;
          description
            "The value of tPortEgrExpShaperCls8StFwdOcts indicates the number of 
             octets forwarded by the class '8' egress expanded shaper.";
          smiv2:max-access "read-only";
          smiv2:oid "1.3.6.1.4.1.6527.3.1.2.2.4.62.1.24";
        }
        leaf tPortEgrExpShaperCls8StMonOvrOct {
          type yang:counter64;
          description
            "The value of tPortEgrExpShaperCls8StMonOvrOct indicates the number of 
             octets above the configured monitor-threshold (since last read) by 
             the class '8' egress expanded shaper.";
          smiv2:max-access "read-only";
          smiv2:oid "1.3.6.1.4.1.6527.3.1.2.2.4.62.1.25";
        }
        leaf tPortEgrExpShaperAggStFwdPkts {
          type yang:counter64;
          description
            "The value of tPortEgrExpShaperAggStFwdPkts indicates the aggregate 
             number of packets forwarded by all of the classes of this egress 
             expanded shaper.";
          smiv2:max-access "read-only";
          smiv2:oid "1.3.6.1.4.1.6527.3.1.2.2.4.62.1.26";
        }
        leaf tPortEgrExpShaperAggStFwdOcts {
          type yang:counter64;
          description
            "The value of tPortEgrExpShaperAggStFwdOcts indicates the aggregate 
             number of octets forwarded by all of the classes of this egress 
             expanded shaper.";
          smiv2:max-access "read-only";
          smiv2:oid "1.3.6.1.4.1.6527.3.1.2.2.4.62.1.27";
        }
        leaf tPortEgrExpShaperAggStMonOvrOct {
          type yang:counter64;
          description
            "The value of tPortEgrExpShaperAggStMonOvrOct indicates the aggregate
             number of octets above the configured monitor-threshold 
             (since last read) by all of the classes of this egress expanded
             shaper.";
          smiv2:max-access "read-only";
          smiv2:oid "1.3.6.1.4.1.6527.3.1.2.2.4.62.1.28";
        }
      }
      config false;
    }
    container tPortEgrExpShaperStatsHLTable {
      description
        "The tPortEgrExpShaperStatsHLTable contains the statistics of each 
         egress expanded shaper at the port level configured on this system
         represented in higher 32 and lower 32 bit objects.";
      smiv2:oid "1.3.6.1.4.1.6527.3.1.2.2.4.63";
      list tPortEgrExpShaperStatsHLEntry {
        key "tmnxChassisIndex tmnxPortPortID tmnxPortEgrExpShaperName";
        description
          "Each row in tPortEgrExpShaperStatsHLEntry represents a particular 
           egress expanded secondary shaper statistics at the port level specified
           by tmnxPortEgrExpShaperName.";
        smiv2:oid "1.3.6.1.4.1.6527.3.1.2.2.4.63.1";
        leaf tmnxChassisIndex {
          type leafref {
            path "/timetra-chassis:TIMETRA-CHASSIS-MIB/timetra-chassis:tmnxChassisTable/timetra-chassis:tmnxChassisEntry/timetra-chassis:tmnxChassisIndex";
          }
        }
        leaf tmnxPortPortID {
          type leafref {
            path "/timetra-port:TIMETRA-PORT-MIB/timetra-port:tmnxPortTable/timetra-port:tmnxPortEntry/timetra-port:tmnxPortPortID";
          }
        }
        leaf tmnxPortEgrExpShaperName {
          type leafref {
            path "/timetra-port:TIMETRA-PORT-MIB/timetra-port:tmnxPortEgrExpShaperTable/timetra-port:tmnxPortEgrExpShaperEntry/timetra-port:tmnxPortEgrExpShaperName";
          }
        }
        leaf tPortEgrExpShaperCls1StFwdPktsL {
          type yang:counter32;
          description
            "The value of tPortEgrExpShaperCls1StFwdPktsL indicates the lower 32
             bits of the value of tPortEgrExpShaperCls1StFwdPkts.";
          smiv2:max-access "read-only";
          smiv2:oid "1.3.6.1.4.1.6527.3.1.2.2.4.63.1.1";
        }
        leaf tPortEgrExpShaperCls1StFwdPktsH {
          type yang:counter32;
          description
            "The value of tPortEgrExpShaperCls1StFwdPktsH indicates the higher 32
             bits of the value of tPortEgrExpShaperCls1StFwdPkts.";
          smiv2:max-access "read-only";
          smiv2:oid "1.3.6.1.4.1.6527.3.1.2.2.4.63.1.2";
        }
        leaf tPortEgrExpShaperCls1StFwdOctsL {
          type yang:counter32;
          description
            "The value of tPortEgrExpShaperCls1StFwdOctsL indicates the lower 32 
             bits of the value of tPortEgrExpShaperCls1StFwdOcts.";
          smiv2:max-access "read-only";
          smiv2:oid "1.3.6.1.4.1.6527.3.1.2.2.4.63.1.3";
        }
        leaf tPortEgrExpShaperCls1StFwdOctsH {
          type yang:counter32;
          description
            "The value of tPortEgrExpShaperCls1StFwdOctsH indicates the higher 32
             bits of the value of tPortEgrExpShaperCls1StFwdOcts.";
          smiv2:max-access "read-only";
          smiv2:oid "1.3.6.1.4.1.6527.3.1.2.2.4.63.1.4";
        }
        leaf tPortEgrExpShaperCls1StMonOvrOL {
          type yang:counter32;
          description
            "The value of tPortEgrExpShaperCls1StMonOvrOL indicates the lower 32 
             bits of the value of tPortEgrExpShaperCls1StMonOvrOct.";
          smiv2:max-access "read-only";
          smiv2:oid "1.3.6.1.4.1.6527.3.1.2.2.4.63.1.5";
        }
        leaf tPortEgrExpShaperCls1StMonOvrOH {
          type yang:counter32;
          description
            "The value of tPortEgrExpShaperCls1StMonOvrOH indicates the higher 32
             bits of the value of tPortEgrExpShaperCls1StMonOvrOct.";
          smiv2:max-access "read-only";
          smiv2:oid "1.3.6.1.4.1.6527.3.1.2.2.4.63.1.6";
        }
        leaf tPortEgrExpShaperCls2StFwdPktsL {
          type yang:counter32;
          description
            "The value of tPortEgrExpShaperCls2StFwdPktsL indicates the lower 32
             bits of the value of tPortEgrExpShaperCls2StFwdPkts.";
          smiv2:max-access "read-only";
          smiv2:oid "1.3.6.1.4.1.6527.3.1.2.2.4.63.1.7";
        }
        leaf tPortEgrExpShaperCls2StFwdPktsH {
          type yang:counter32;
          description
            "The value of tPortEgrExpShaperCls2StFwdPktsH indicates the higher 32
             bits of the value of tPortEgrExpShaperCls2StFwdPkts.";
          smiv2:max-access "read-only";
          smiv2:oid "1.3.6.1.4.1.6527.3.1.2.2.4.63.1.8";
        }
        leaf tPortEgrExpShaperCls2StFwdOctsL {
          type yang:counter32;
          description
            "The value of tPortEgrExpShaperCls2StFwdOctsL indicates the lower 32
             bits of the value of tPortEgrExpShaperCls2StFwdOcts.";
          smiv2:max-access "read-only";
          smiv2:oid "1.3.6.1.4.1.6527.3.1.2.2.4.63.1.9";
        }
        leaf tPortEgrExpShaperCls2StFwdOctsH {
          type yang:counter32;
          description
            "The value of tPortEgrExpShaperCls2StFwdOctsH indicates the higher 32
             bits of the value of tPortEgrExpShaperCls2StFwdOcts.";
          smiv2:max-access "read-only";
          smiv2:oid "1.3.6.1.4.1.6527.3.1.2.2.4.63.1.10";
        }
        leaf tPortEgrExpShaperCls2StMonOvrOL {
          type yang:counter32;
          description
            "The value of tPortEgrExpShaperCls2StMonOvrOL indicates the lower 32 
             bits of the value of tPortEgrExpShaperCls2StMonOvrOct.";
          smiv2:max-access "read-only";
          smiv2:oid "1.3.6.1.4.1.6527.3.1.2.2.4.63.1.11";
        }
        leaf tPortEgrExpShaperCls2StMonOvrOH {
          type yang:counter32;
          description
            "The value of tPortEgrExpShaperCls2StMonOvrOH indicates the higher 32
             bits of the value of tPortEgrExpShaperCls2StMonOvrOct.";
          smiv2:max-access "read-only";
          smiv2:oid "1.3.6.1.4.1.6527.3.1.2.2.4.63.1.12";
        }
        leaf tPortEgrExpShaperCls3StFwdPktsL {
          type yang:counter32;
          description
            "The value of tPortEgrExpShaperCls3StFwdPktsL indicates the lower 32  
             bits of the value of tPortEgrExpShaperCls3StFwdPkts.";
          smiv2:max-access "read-only";
          smiv2:oid "1.3.6.1.4.1.6527.3.1.2.2.4.63.1.13";
        }
        leaf tPortEgrExpShaperCls3StFwdPktsH {
          type yang:counter32;
          description
            "The value of tPortEgrExpShaperCls3StFwdPktsH indicates the higher 32 
             bits of the value of tPortEgrExpShaperCls3StFwdPkts.";
          smiv2:max-access "read-only";
          smiv2:oid "1.3.6.1.4.1.6527.3.1.2.2.4.63.1.14";
        }
        leaf tPortEgrExpShaperCls3StFwdOctsL {
          type yang:counter32;
          description
            "The value of tPortEgrExpShaperCls3StFwdOctsL indicates the lower 32 
             bits of the value of tPortEgrExpShaperCls3StFwdOcts.";
          smiv2:max-access "read-only";
          smiv2:oid "1.3.6.1.4.1.6527.3.1.2.2.4.63.1.15";
        }
        leaf tPortEgrExpShaperCls3StFwdOctsH {
          type yang:counter32;
          description
            "The value of tPortEgrExpShaperCls3StFwdOctsH indicates the higher 32 
             bits of the value of tPortEgrExpShaperCls3StFwdOcts.";
          smiv2:max-access "read-only";
          smiv2:oid "1.3.6.1.4.1.6527.3.1.2.2.4.63.1.16";
        }
        leaf tPortEgrExpShaperCls3StMonOvrOL {
          type yang:counter32;
          description
            "The value of tPortEgrExpShaperCls3StMonOvrOL indicates the lower 32 
             bits of the value of tPortEgrExpShaperCls3StMonOvrOct.";
          smiv2:max-access "read-only";
          smiv2:oid "1.3.6.1.4.1.6527.3.1.2.2.4.63.1.17";
        }
        leaf tPortEgrExpShaperCls3StMonOvrOH {
          type yang:counter32;
          description
            "The value of tPortEgrExpShaperCls3StMonOvrOH indicates the higher 32
             bits of the value of tPortEgrExpShaperCls3StMonOvrOct.";
          smiv2:max-access "read-only";
          smiv2:oid "1.3.6.1.4.1.6527.3.1.2.2.4.63.1.18";
        }
        leaf tPortEgrExpShaperCls4StFwdPktsL {
          type yang:counter32;
          description
            "The value of tPortEgrExpShaperCls4StFwdPktsL indicates the lower 32  
             bits of the value of tPortEgrExpShaperCls4StFwdPkts.";
          smiv2:max-access "read-only";
          smiv2:oid "1.3.6.1.4.1.6527.3.1.2.2.4.63.1.19";
        }
        leaf tPortEgrExpShaperCls4StFwdPktsH {
          type yang:counter32;
          description
            "The value of tPortEgrExpShaperCls4StFwdPktsH indicates the higher 32 
             bits of the value of tPortEgrExpShaperCls4StFwdPkts.";
          smiv2:max-access "read-only";
          smiv2:oid "1.3.6.1.4.1.6527.3.1.2.2.4.63.1.20";
        }
        leaf tPortEgrExpShaperCls4StFwdOctsL {
          type yang:counter32;
          description
            "The value of tPortEgrExpShaperCls4StFwdOctsL indicates the lower 32 
             bits of the value of tPortEgrExpShaperCls4StFwdOcts.";
          smiv2:max-access "read-only";
          smiv2:oid "1.3.6.1.4.1.6527.3.1.2.2.4.63.1.21";
        }
        leaf tPortEgrExpShaperCls4StFwdOctsH {
          type yang:counter32;
          description
            "The value of tPortEgrExpShaperCls4StFwdOctsH indicates the higher 32 
             bits of the value of tPortEgrExpShaperCls4StFwdOcts.";
          smiv2:max-access "read-only";
          smiv2:oid "1.3.6.1.4.1.6527.3.1.2.2.4.63.1.22";
        }
        leaf tPortEgrExpShaperCls4StMonOvrOL {
          type yang:counter32;
          description
            "The value of tPortEgrExpShaperCls4StMonOvrOL indicates the lower 32 
             bits of the value of tPortEgrExpShaperCls4StMonOvrOct.";
          smiv2:max-access "read-only";
          smiv2:oid "1.3.6.1.4.1.6527.3.1.2.2.4.63.1.23";
        }
        leaf tPortEgrExpShaperCls4StMonOvrOH {
          type yang:counter32;
          description
            "The value of tPortEgrExpShaperCls4StMonOvrOH indicates the higher 32
             bits of the value of tPortEgrExpShaperCls4StMonOvrOct.";
          smiv2:max-access "read-only";
          smiv2:oid "1.3.6.1.4.1.6527.3.1.2.2.4.63.1.24";
        }
        leaf tPortEgrExpShaperCls5StFwdPktsL {
          type yang:counter32;
          description
            "The value of tPortEgrExpShaperCls5StFwdPktsL indicates the lower 32  
             bits of the value of tPortEgrExpShaperCls5StFwdPkts.";
          smiv2:max-access "read-only";
          smiv2:oid "1.3.6.1.4.1.6527.3.1.2.2.4.63.1.25";
        }
        leaf tPortEgrExpShaperCls5StFwdPktsH {
          type yang:counter32;
          description
            "The value of tPortEgrExpShaperCls5StFwdPktsH indicates the higher 32 
             bits of the value of tPortEgrExpShaperCls5StFwdPkts.";
          smiv2:max-access "read-only";
          smiv2:oid "1.3.6.1.4.1.6527.3.1.2.2.4.63.1.26";
        }
        leaf tPortEgrExpShaperCls5StFwdOctsL {
          type yang:counter32;
          description
            "The value of tPortEgrExpShaperCls5StFwdOctsL indicates the lower 32 
             bits of the value of tPortEgrExpShaperCls5StFwdOcts.";
          smiv2:max-access "read-only";
          smiv2:oid "1.3.6.1.4.1.6527.3.1.2.2.4.63.1.27";
        }
        leaf tPortEgrExpShaperCls5StFwdOctsH {
          type yang:counter32;
          description
            "The value of tPortEgrExpShaperCls5StFwdOctsH indicates the higher 32 
             bits of the value of tPortEgrExpShaperCls5StFwdOcts.";
          smiv2:max-access "read-only";
          smiv2:oid "1.3.6.1.4.1.6527.3.1.2.2.4.63.1.28";
        }
        leaf tPortEgrExpShaperCls5StMonOvrOL {
          type yang:counter32;
          description
            "The value of tPortEgrExpShaperCls5StMonOvrOL indicates the lower 32 
             bits of the value of tPortEgrExpShaperCls5StMonOvrOct.";
          smiv2:max-access "read-only";
          smiv2:oid "1.3.6.1.4.1.6527.3.1.2.2.4.63.1.29";
        }
        leaf tPortEgrExpShaperCls5StMonOvrOH {
          type yang:counter32;
          description
            "The value of tPortEgrExpShaperCls5StMonOvrOH indicates the higher 32
             bits of the value of tPortEgrExpShaperCls5StMonOvrOct.";
          smiv2:max-access "read-only";
          smiv2:oid "1.3.6.1.4.1.6527.3.1.2.2.4.63.1.30";
        }
        leaf tPortEgrExpShaperCls6StFwdPktsL {
          type yang:counter32;
          description
            "The value of tPortEgrExpShaperCls6StFwdPktsL indicates the lower 32  
             bits of the value of tPortEgrExpShaperCls6StFwdPkts.";
          smiv2:max-access "read-only";
          smiv2:oid "1.3.6.1.4.1.6527.3.1.2.2.4.63.1.31";
        }
        leaf tPortEgrExpShaperCls6StFwdPktsH {
          type yang:counter32;
          description
            "The value of tPortEgrExpShaperCls6StFwdPktsH indicates the higher 32 
             bits of the value of tPortEgrExpShaperCls6StFwdPkts.";
          smiv2:max-access "read-only";
          smiv2:oid "1.3.6.1.4.1.6527.3.1.2.2.4.63.1.32";
        }
        leaf tPortEgrExpShaperCls6StFwdOctsL {
          type yang:counter32;
          description
            "The value of tPortEgrExpShaperCls6StFwdOctsL indicates the lower 32 
             bits of the value of tPortEgrExpShaperCls6StFwdOcts.";
          smiv2:max-access "read-only";
          smiv2:oid "1.3.6.1.4.1.6527.3.1.2.2.4.63.1.33";
        }
        leaf tPortEgrExpShaperCls6StFwdOctsH {
          type yang:counter32;
          description
            "The value of tPortEgrExpShaperCls6StFwdOctsH indicates the higher 32 
             bits of the value of tPortEgrExpShaperCls6StFwdOcts.";
          smiv2:max-access "read-only";
          smiv2:oid "1.3.6.1.4.1.6527.3.1.2.2.4.63.1.34";
        }
        leaf tPortEgrExpShaperCls6StMonOvrOL {
          type yang:counter32;
          description
            "The value of tPortEgrExpShaperCls6StMonOvrOL indicates the lower 32 
             bits of the value of tPortEgrExpShaperCls6StMonOvrOct.";
          smiv2:max-access "read-only";
          smiv2:oid "1.3.6.1.4.1.6527.3.1.2.2.4.63.1.35";
        }
        leaf tPortEgrExpShaperCls6StMonOvrOH {
          type yang:counter32;
          description
            "The value of tPortEgrExpShaperCls6StMonOvrOH indicates the higher 32
             bits of the value of tPortEgrExpShaperCls6StMonOvrOct.";
          smiv2:max-access "read-only";
          smiv2:oid "1.3.6.1.4.1.6527.3.1.2.2.4.63.1.36";
        }
        leaf tPortEgrExpShaperCls7StFwdPktsL {
          type yang:counter32;
          description
            "The value of tPortEgrExpShaperCls7StFwdPktsL indicates the lower 32  
             bits of the value of tPortEgrExpShaperCls7StFwdPkts.";
          smiv2:max-access "read-only";
          smiv2:oid "1.3.6.1.4.1.6527.3.1.2.2.4.63.1.37";
        }
        leaf tPortEgrExpShaperCls7StFwdPktsH {
          type yang:counter32;
          description
            "The value of tPortEgrExpShaperCls7StFwdPktsH indicates the higher 32 
             bits of the value of tPortEgrExpShaperCls7StFwdPkts.";
          smiv2:max-access "read-only";
          smiv2:oid "1.3.6.1.4.1.6527.3.1.2.2.4.63.1.38";
        }
        leaf tPortEgrExpShaperCls7StFwdOctsL {
          type yang:counter32;
          description
            "The value of tPortEgrExpShaperCls7StFwdOctsL indicates the lower 32 
             bits of the value of tPortEgrExpShaperCls7StFwdOcts.";
          smiv2:max-access "read-only";
          smiv2:oid "1.3.6.1.4.1.6527.3.1.2.2.4.63.1.39";
        }
        leaf tPortEgrExpShaperCls7StFwdOctsH {
          type yang:counter32;
          description
            "The value of tPortEgrExpShaperCls7StFwdOctsH indicates the higher 32 
             bits of the value of tPortEgrExpShaperCls7StFwdOcts.";
          smiv2:max-access "read-only";
          smiv2:oid "1.3.6.1.4.1.6527.3.1.2.2.4.63.1.40";
        }
        leaf tPortEgrExpShaperCls7StMonOvrOL {
          type yang:counter32;
          description
            "The value of tPortEgrExpShaperCls7StMonOvrOL indicates the lower 32 
             bits of the value of tPortEgrExpShaperCls7StMonOvrOct.";
          smiv2:max-access "read-only";
          smiv2:oid "1.3.6.1.4.1.6527.3.1.2.2.4.63.1.41";
        }
        leaf tPortEgrExpShaperCls7StMonOvrOH {
          type yang:counter32;
          description
            "The value of tPortEgrExpShaperCls7StMonOvrOH indicates the higher 32
             bits of the value of tPortEgrExpShaperCls7StMonOvrOct.";
          smiv2:max-access "read-only";
          smiv2:oid "1.3.6.1.4.1.6527.3.1.2.2.4.63.1.42";
        }
        leaf tPortEgrExpShaperCls8StFwdPktsL {
          type yang:counter32;
          description
            "The value of tPortEgrExpShaperCls8StFwdPktsL indicates the lower 32  
             bits of the value of tPortEgrExpShaperCls8StFwdPkts.";
          smiv2:max-access "read-only";
          smiv2:oid "1.3.6.1.4.1.6527.3.1.2.2.4.63.1.43";
        }
        leaf tPortEgrExpShaperCls8StFwdPktsH {
          type yang:counter32;
          description
            "The value of tPortEgrExpShaperCls8StFwdPktsH indicates the higher 32 
             bits of the value of tPortEgrExpShaperCls8StFwdPkts.";
          smiv2:max-access "read-only";
          smiv2:oid "1.3.6.1.4.1.6527.3.1.2.2.4.63.1.44";
        }
        leaf tPortEgrExpShaperCls8StFwdOctsL {
          type yang:counter32;
          description
            "The value of tPortEgrExpShaperCls8StFwdOctsL indicates the lower 32 
             bits of the value of tPortEgrExpShaperCls8StFwdOcts.";
          smiv2:max-access "read-only";
          smiv2:oid "1.3.6.1.4.1.6527.3.1.2.2.4.63.1.45";
        }
        leaf tPortEgrExpShaperCls8StFwdOctsH {
          type yang:counter32;
          description
            "The value of tPortEgrExpShaperCls8StFwdOctsH indicates the higher 32 
             bits of the value of tPortEgrExpShaperCls8StFwdOcts.";
          smiv2:max-access "read-only";
          smiv2:oid "1.3.6.1.4.1.6527.3.1.2.2.4.63.1.46";
        }
        leaf tPortEgrExpShaperCls8StMonOvrOL {
          type yang:counter32;
          description
            "The value of tPortEgrExpShaperCls8StMonOvrOL indicates the lower 32 
             bits of the value of tPortEgrExpShaperCls8StMonOvrOct.";
          smiv2:max-access "read-only";
          smiv2:oid "1.3.6.1.4.1.6527.3.1.2.2.4.63.1.47";
        }
        leaf tPortEgrExpShaperCls8StMonOvrOH {
          type yang:counter32;
          description
            "The value of tPortEgrExpShaperCls8StMonOvrOH indicates the higher 32
             bits of the value of tPortEgrExpShaperCls8StMonOvrOct.";
          smiv2:max-access "read-only";
          smiv2:oid "1.3.6.1.4.1.6527.3.1.2.2.4.63.1.48";
        }
        leaf tPortEgrExpShaperAggStFwdPktsL {
          type yang:counter32;
          description
            "The value of tPortEgrExpShaperAggStFwdPktsL indicates the lower 32 
             bits of the value of tPortEgrExpShaperAggStFwdPkts.";
          smiv2:max-access "read-only";
          smiv2:oid "1.3.6.1.4.1.6527.3.1.2.2.4.63.1.49";
        }
        leaf tPortEgrExpShaperAggStFwdPktsH {
          type yang:counter32;
          description
            "The value of tPortEgrExpShaperAggStFwdPktsH indicates the higher 32 
             bits of the value of tPortEgrExpShaperAggStFwdPkts.";
          smiv2:max-access "read-only";
          smiv2:oid "1.3.6.1.4.1.6527.3.1.2.2.4.63.1.50";
        }
        leaf tPortEgrExpShaperAggStFwdOctsL {
          type yang:counter32;
          description
            "The value of tPortEgrExpShaperAggStFwdOctsL indicates the lower 32 
             bits of the value of tPortEgrExpShaperAggStFwdOcts.";
          smiv2:max-access "read-only";
          smiv2:oid "1.3.6.1.4.1.6527.3.1.2.2.4.63.1.51";
        }
        leaf tPortEgrExpShaperAggStFwdOctsH {
          type yang:counter32;
          description
            "The value of tPortEgrExpShaperAggStFwdOctsH indicates the higher 32 
             bits of the value of tPortEgrExpShaperAggStFwdOcts.";
          smiv2:max-access "read-only";
          smiv2:oid "1.3.6.1.4.1.6527.3.1.2.2.4.63.1.52";
        }
        leaf tPortEgrExpShaperAggStMonOvrOL {
          type yang:counter32;
          description
            "The value of tPortEgrExpShaperAggStMonOvrOL indicates the lower 32 
             bits of the value of tPortEgrExpShaperAggStMonOvrOct.";
          smiv2:max-access "read-only";
          smiv2:oid "1.3.6.1.4.1.6527.3.1.2.2.4.63.1.53";
        }
        leaf tPortEgrExpShaperAggStMonOvrOH {
          type yang:counter32;
          description
            "The value of tPortEgrExpShaperAggStMonOvrOH indicates the higher 32 
             bits of the value of tPortEgrExpShaperAggStMonOvrOct.";
          smiv2:max-access "read-only";
          smiv2:oid "1.3.6.1.4.1.6527.3.1.2.2.4.63.1.54";
        }
      }
      config false;
    }
    container tPortEgrVPortAggStatsTable {
      description
        "The tPortEgrVPortAggStatsTable contains the statistics of each 
         virtual port at the port egress level configured on this system.
         Most objects are represented in 64 bit. 32-bit version of the objects
         are available in tPortEgrVPortAggStatsHLTable.";
      smiv2:oid "1.3.6.1.4.1.6527.3.1.2.2.4.64";
      list tPortEgrVPortAggStatsEntry {
        key "tmnxChassisIndex tmnxPortPortID tPortEgrVPortName tPortEgrVPStLvl";
        description
          "Each row in tPortEgrVPortAggStatsEntry represents a particular 
           virtual port at the port egress level specified  by tPortEgrVPortName
           and tPortEgrVPStLvl.";
        smiv2:oid "1.3.6.1.4.1.6527.3.1.2.2.4.64.1";
        leaf tmnxChassisIndex {
          type leafref {
            path "/timetra-chassis:TIMETRA-CHASSIS-MIB/timetra-chassis:tmnxChassisTable/timetra-chassis:tmnxChassisEntry/timetra-chassis:tmnxChassisIndex";
          }
        }
        leaf tmnxPortPortID {
          type leafref {
            path "/timetra-port:TIMETRA-PORT-MIB/timetra-port:tmnxPortTable/timetra-port:tmnxPortEntry/timetra-port:tmnxPortPortID";
          }
        }
        leaf tPortEgrVPortName {
          type leafref {
            path "/timetra-port:TIMETRA-PORT-MIB/timetra-port:tPortEgrVPortTable/timetra-port:tPortEgrVPortEntry/timetra-port:tPortEgrVPortName";
          }
        }
        leaf tPortEgrVPStLvl {
          type uint32 {
            range "1..8|4294967295";
          }
          description
            "The value of tPortEgrVPStLvl indicates the priority level
             for the port scheduler to which a subscriber host queue can be 
             port-parented. When the value of tPortEgrVPStLvl is specified as
             '0xffffffff H', snmp GET on this table returns aggregate statistics.";
          smiv2:max-access "not-accessible";
          smiv2:oid "1.3.6.1.4.1.6527.3.1.2.2.4.64.1.1";
        }
        leaf tPortEgrVPStLstClrdTime {
          type yang:timestamp;
          description
            "The value of tPortEgrVPStLstClrdTime indicates the sysUpTime
             when the counters in this table were last cleared.";
          smiv2:max-access "read-only";
          smiv2:oid "1.3.6.1.4.1.6527.3.1.2.2.4.64.1.2";
        }
        leaf tPortEgrVPStLvlFwdPkt {
          type yang:counter64;
          description
            "The value of tPortEgrVPStLvlFwdPkt indicates the number of 
             packets forwarded by the virtual port for the priority level 
             specified by tPortEgrVPStLvl.";
          smiv2:max-access "read-only";
          smiv2:oid "1.3.6.1.4.1.6527.3.1.2.2.4.64.1.3";
        }
        leaf tPortEgrVPStLvlFwdOct {
          type yang:counter64;
          description
            "The value of tPortEgrVPStLvlFwdOct indicates the number of 
             octets forwarded by the virtual port for the priority level 
             specified by tPortEgrVPStLvl.";
          smiv2:max-access "read-only";
          smiv2:oid "1.3.6.1.4.1.6527.3.1.2.2.4.64.1.4";
        }
        leaf tPortEgrVPStLvlDpdPkt {
          type yang:counter64;
          description
            "The value of tPortEgrVPStLvlDpdPkt indicates the number of 
             packets dropped by the virtual port for the priority level 
             specified by tPortEgrVPStLvl.";
          smiv2:max-access "read-only";
          smiv2:oid "1.3.6.1.4.1.6527.3.1.2.2.4.64.1.5";
        }
        leaf tPortEgrVPStLvlDpdOct {
          type yang:counter64;
          description
            "The value of tPortEgrVPStLvlDpdOct indicates the number of 
             octets dropped by the virtual port for the priority level 
             specified by tPortEgrVPStLvl.";
          smiv2:max-access "read-only";
          smiv2:oid "1.3.6.1.4.1.6527.3.1.2.2.4.64.1.6";
        }
      }
      config false;
    }
    container tPortEgrVPortAggStatsHLTable {
      description
        "The tPortEgrVPortAggStatsHLTable contains the statistics of each 
         virtual port at the port egress level configured on this system
         represented in higher 32 and lower 32 bit objects.";
      smiv2:oid "1.3.6.1.4.1.6527.3.1.2.2.4.65";
      list tPortEgrVPortAggStatsHLEntry {
        key "tmnxChassisIndex tmnxPortPortID tPortEgrVPortName tPortEgrVPStLvl";
        description
          "Each row in tPortEgrVPortAggStatsHLEntry represents a particular 
           virtual port statistics at the port egress level specified
           by tPortEgrVPortName and tPortEgrVPStLvl.";
        smiv2:oid "1.3.6.1.4.1.6527.3.1.2.2.4.65.1";
        leaf tmnxChassisIndex {
          type leafref {
            path "/timetra-chassis:TIMETRA-CHASSIS-MIB/timetra-chassis:tmnxChassisTable/timetra-chassis:tmnxChassisEntry/timetra-chassis:tmnxChassisIndex";
          }
        }
        leaf tmnxPortPortID {
          type leafref {
            path "/timetra-port:TIMETRA-PORT-MIB/timetra-port:tmnxPortTable/timetra-port:tmnxPortEntry/timetra-port:tmnxPortPortID";
          }
        }
        leaf tPortEgrVPortName {
          type leafref {
            path "/timetra-port:TIMETRA-PORT-MIB/timetra-port:tPortEgrVPortTable/timetra-port:tPortEgrVPortEntry/timetra-port:tPortEgrVPortName";
          }
        }
        leaf tPortEgrVPStLvl {
          type leafref {
            path "/timetra-port:TIMETRA-PORT-MIB/timetra-port:tPortEgrVPortAggStatsTable/timetra-port:tPortEgrVPortAggStatsEntry/timetra-port:tPortEgrVPStLvl";
          }
        }
        leaf tPortEgrVPStLvlFwdPktL {
          type yang:counter32;
          description
            "The value of tPortEgrVPStLvlFwdPktL indicates the lower 32
             bits of the value of tPortEgrVPStLvlFwdPkt.";
          smiv2:max-access "read-only";
          smiv2:oid "1.3.6.1.4.1.6527.3.1.2.2.4.65.1.1";
        }
        leaf tPortEgrVPStLvlFwdPktH {
          type yang:counter32;
          description
            "The value of tPortEgrVPStLvlFwdPktH indicates the higher 32
             bits of the value of tPortEgrVPStLvlFwdPkt.";
          smiv2:max-access "read-only";
          smiv2:oid "1.3.6.1.4.1.6527.3.1.2.2.4.65.1.2";
        }
        leaf tPortEgrVPStLvlFwdOctL {
          type yang:counter32;
          description
            "The value of tPortEgrVPStLvlFwdOctL indicates the lower 32 
             bits of the value of tPortEgrVPStLvlFwdOct.";
          smiv2:max-access "read-only";
          smiv2:oid "1.3.6.1.4.1.6527.3.1.2.2.4.65.1.3";
        }
        leaf tPortEgrVPStLvlFwdOctH {
          type yang:counter32;
          description
            "The value of tPortEgrVPStLvlFwdOctH indicates the higher 32
             bits of the value of tPortEgrVPStLvlFwdOct.";
          smiv2:max-access "read-only";
          smiv2:oid "1.3.6.1.4.1.6527.3.1.2.2.4.65.1.4";
        }
        leaf tPortEgrVPStLvlDpdPktL {
          type yang:counter32;
          description
            "The value of tPortEgrVPStLvlDpdPktL indicates the lower 32
             bits of the value of tPortEgrVPStLvlDpdPkt.";
          smiv2:max-access "read-only";
          smiv2:oid "1.3.6.1.4.1.6527.3.1.2.2.4.65.1.5";
        }
        leaf tPortEgrVPStLvlDpdPktH {
          type yang:counter32;
          description
            "The value of tPortEgrVPStLvlDpdPktH indicates the higher 32
             bits of the value of tPortEgrVPStLvlDpdPkt.";
          smiv2:max-access "read-only";
          smiv2:oid "1.3.6.1.4.1.6527.3.1.2.2.4.65.1.6";
        }
        leaf tPortEgrVPStLvlDpdOctL {
          type yang:counter32;
          description
            "The value of tPortEgrVPStLvlDpdOctL indicates the lower 32 
             bits of the value of tPortEgrVPStLvlDpdOct.";
          smiv2:max-access "read-only";
          smiv2:oid "1.3.6.1.4.1.6527.3.1.2.2.4.65.1.7";
        }
        leaf tPortEgrVPStLvlDpdOctH {
          type yang:counter32;
          description
            "The value of tPortEgrVPStLvlDpdOctH indicates the higher 32
             bits of the value of tPortEgrVPStLvlDpdOct.";
          smiv2:max-access "read-only";
          smiv2:oid "1.3.6.1.4.1.6527.3.1.2.2.4.65.1.8";
        }
      }
      config false;
    }
    container tmnxDDMLaneTable {
      description
        "The tmnxDDMLaneTable has an entry for each CFP/QSFP in the system that
         supports Lane Digital Diagnostic Monitoring (DDM). The table is
         indexed by tmnxPortPortID and tmnxDDMLaneId. Each row in this table is
         dynamically added and removed internally by the system based on the
         presence or absence of DDM capable CFP/QSFP components.";
      smiv2:oid "1.3.6.1.4.1.6527.3.1.2.2.4.66";
      list tmnxDDMLaneEntry {
        key "tmnxChassisIndex tmnxPortPortID tmnxDDMLaneId";
        description
          "Each row represents a particular CFP/QSFP that supports Digital
           Diagnostic Monitoring Lanes.
           Entries are created and deleted internally by the system.";
        smiv2:oid "1.3.6.1.4.1.6527.3.1.2.2.4.66.1";
        leaf tmnxChassisIndex {
          type leafref {
            path "/timetra-chassis:TIMETRA-CHASSIS-MIB/timetra-chassis:tmnxChassisTable/timetra-chassis:tmnxChassisEntry/timetra-chassis:tmnxChassisIndex";
          }
        }
        leaf tmnxPortPortID {
          type leafref {
            path "/timetra-port:TIMETRA-PORT-MIB/timetra-port:tmnxPortTable/timetra-port:tmnxPortEntry/timetra-port:tmnxPortPortID";
          }
        }
        leaf tmnxDDMLaneId {
          type uint32 {
            range "1..16";
          }
          description
            "The value of tmnxDDMLaneId specifies the Optical Lane ID for the row.
             The maximum ID for a given port is restricted to the value of
             tmnxPortSFPNumLanes for the given port. ";
          smiv2:max-access "not-accessible";
          smiv2:oid "1.3.6.1.4.1.6527.3.1.2.2.4.66.1.1";
        }
        leaf tmnxDDMLaneTemperature {
          type int32;
          description
            "The value of tmnxDDMLaneTemperature indicates the current temperature
             of the CFP/QSFP in 1/256th degrees Celsius.
             
             The formula for translating between the value of tmnxDDMLaneTemperature
             and degrees Celsius is:
                    tmnxDDMLaneTemperature / 256
             
             For example:
             The SNMP value 5734 is 22.4 degrees Celsius.";
          smiv2:max-access "read-only";
          smiv2:oid "1.3.6.1.4.1.6527.3.1.2.2.4.66.1.2";
        }
        leaf tmnxDDMLaneTempLowWarn {
          type int32;
          description
            "The value of tmnxDDMLaneTempLowWarn indicates the temperature
             of the CFP/QSFP in degrees Celsius that triggers a low-Warning.";
          smiv2:max-access "read-only";
          smiv2:oid "1.3.6.1.4.1.6527.3.1.2.2.4.66.1.3";
        }
        leaf tmnxDDMLaneTempLowAlarm {
          type int32;
          description
            "The value of tmnxDDMLaneTempLowAlarm indicates the temperature
             of the CFP/QSFP in degrees Celsius that triggers a low-alarm.";
          smiv2:max-access "read-only";
          smiv2:oid "1.3.6.1.4.1.6527.3.1.2.2.4.66.1.4";
        }
        leaf tmnxDDMLaneTempHiWarn {
          type int32;
          description
            "The value of tmnxDDMLaneTempHiWarn indicates the temperature
             of the CFP/QSFP in degrees Celsius that triggers a hi-Warning.";
          smiv2:max-access "read-only";
          smiv2:oid "1.3.6.1.4.1.6527.3.1.2.2.4.66.1.5";
        }
        leaf tmnxDDMLaneTempHiAlarm {
          type int32;
          description
            "The value of tmnxDDMLaneTempHiAlarm indicates the temperature
             of the CFP/QSFP in degrees Celsius that triggers a hi-alarm.";
          smiv2:max-access "read-only";
          smiv2:oid "1.3.6.1.4.1.6527.3.1.2.2.4.66.1.6";
        }
        leaf tmnxDDMLaneTxBiasCurrent {
          type int32;
          description
            "The value of tmnxDDMLaneTxBiasCurrent indicates the current Transmit
             Bias Current of the CFP/QSFP in 1/500 milliamperes (mA).
             
             The formula for translating between the value of
             tmnxDDMLaneTxBiasCurrent and amperes is:
                    tmnxDDMLaneTxBiasCurrent / 500
             
             For example:
             The SNMP value 2565 is 5.1 milliamperes (mA).";
          smiv2:max-access "read-only";
          smiv2:oid "1.3.6.1.4.1.6527.3.1.2.2.4.66.1.7";
        }
        leaf tmnxDDMLaneTxBiasCurrentLowWarn {
          type int32;
          description
            "The value of tmnxDDMLaneTxBiasCurrentLowWarn indicates the Transmit
             Bias Current of the CFP/QSFP in micro-Amperes (uA) that triggers a
             low-Warning.";
          smiv2:max-access "read-only";
          smiv2:oid "1.3.6.1.4.1.6527.3.1.2.2.4.66.1.8";
        }
        leaf tmnxDDMLaneTxBiasCurrentLowAlarm {
          type int32;
          description
            "The value of tmnxDDMLaneTxBiasCurrentLowAlarm indicates the Transmit
             Bias Current of the CFP/QSFP in micro-Amperes (uA) that triggers a
             low-alarm.";
          smiv2:max-access "read-only";
          smiv2:oid "1.3.6.1.4.1.6527.3.1.2.2.4.66.1.9";
        }
        leaf tmnxDDMLaneTxBiasCurrentHiWarn {
          type int32;
          description
            "The value of tmnxDDMLaneTxBiasCurrentHiWarn indicates the Transmit
             Bias Current of the CFP/QSFP in micro-Amperes (uA) that triggers a
             hi-Warning.";
          smiv2:max-access "read-only";
          smiv2:oid "1.3.6.1.4.1.6527.3.1.2.2.4.66.1.10";
        }
        leaf tmnxDDMLaneTxBiasCurrentHiAlarm {
          type int32;
          description
            "The value of tmnxDDMLaneTxBiasCurrentHiAlarm indicates the Transmit
             Bias Current of the CFP/QSFP in micro-Amperes (uA) that triggers a
             hi-alarm.";
          smiv2:max-access "read-only";
          smiv2:oid "1.3.6.1.4.1.6527.3.1.2.2.4.66.1.11";
        }
        leaf tmnxDDMLaneTxOutputPower {
          type int32;
          description
            "The value of tmnxDDMLaneTxOutputPower indicates the current Output
             Power of the CFP/QSFP in one tenths of a micro-Watt (uW).
             
             For example:
             Using the SNMP value of 790, and using units of tenths of microwatt,
             790 becomes 79 microwatts or 0.079 milliwatts. Converting to dBm:
                   10 x log10(0.079) = -11.0 dBm";
          smiv2:max-access "read-only";
          smiv2:oid "1.3.6.1.4.1.6527.3.1.2.2.4.66.1.12";
        }
        leaf tmnxDDMLaneTxOutputPowerLowWarn {
          type int32;
          description
            "The value of tmnxDDMLaneTxOutputPowerLowWarn indicates the Output Power
             of the CFP/QSFP in one tenths of a micro-Watt (uW) that triggers a
             low-Warning.";
          smiv2:max-access "read-only";
          smiv2:oid "1.3.6.1.4.1.6527.3.1.2.2.4.66.1.13";
        }
        leaf tmnxDDMLaneTxOutputPowerLowAlarm {
          type int32;
          description
            "The value of tmnxDDMLaneTxOutputPowerLowAlarm indicates the Output
             Power of the CFP/QSFP in one tenths of a micro-Watt (uW) that triggers
             a low-alarm.";
          smiv2:max-access "read-only";
          smiv2:oid "1.3.6.1.4.1.6527.3.1.2.2.4.66.1.14";
        }
        leaf tmnxDDMLaneTxOutputPowerHiWarn {
          type int32;
          description
            "The value of tmnxDDMLaneTxOutputPowerHiWarn indicates the Output Power
             of the CFP/QSFP in one tenths of a micro-Watt (uW) that triggers a
             hi-warning.";
          smiv2:max-access "read-only";
          smiv2:oid "1.3.6.1.4.1.6527.3.1.2.2.4.66.1.15";
        }
        leaf tmnxDDMLaneTxOutputPowerHiAlarm {
          type int32;
          description
            "The value of tmnxDDMLaneTxOutputPowerHiAlarm indicates the Output Power
             of the CFP/QSFP in one tenths of a micro-Watt (uW) that triggers a
             hi-alarm.";
          smiv2:max-access "read-only";
          smiv2:oid "1.3.6.1.4.1.6527.3.1.2.2.4.66.1.16";
        }
        leaf tmnxDDMLaneRxOpticalPower {
          type int32;
          description
            "The value of tmnxDDMLaneRxOpticalPower indicates the current Received
             Optical Power of the CFP/QSFP in one tenths of a micro-Watt (uW).
             
             For example:
             Using the SNMP value of 790, and using units of tenths of microwatt,
             790 becomes 79 microwatts or 0.079 milliwatts. Converting to dBm:
                   10 x log10(0.079) = -11.0 dBm";
          smiv2:max-access "read-only";
          smiv2:oid "1.3.6.1.4.1.6527.3.1.2.2.4.66.1.17";
        }
        leaf tmnxDDMLaneRxOpticalPwrLowWarn {
          type int32;
          description
            "The value of tmnxDDMLaneRxOpticalPwrLowWarn indicates the Received
             Optical Power of the CFP/QSFP in one tenths of a micro-Watt (uW) that
             triggers a low-Warning.";
          smiv2:max-access "read-only";
          smiv2:oid "1.3.6.1.4.1.6527.3.1.2.2.4.66.1.18";
        }
        leaf tmnxDDMLaneRxOpticalPwrLowAlarm {
          type int32;
          description
            "The value of tmnxDDMLaneRxOpticalPwrLowAlarm indicates the Received
             Optical Power of the CFP/QSFP in one tenths of a micro-Watt (uW) that
             triggers a low-alarm.";
          smiv2:max-access "read-only";
          smiv2:oid "1.3.6.1.4.1.6527.3.1.2.2.4.66.1.19";
        }
        leaf tmnxDDMLaneRxOpticalPwrHiWarn {
          type int32;
          description
            "The value of tmnxDDMLaneRxOpticalPwrHiWarn indicates the Received
             Optical Power of the CFP/QSFP in one tenths of a micro-Watt (uW) that
             triggers a hi-Warning.";
          smiv2:max-access "read-only";
          smiv2:oid "1.3.6.1.4.1.6527.3.1.2.2.4.66.1.20";
        }
        leaf tmnxDDMLaneRxOpticalPwrHiAlarm {
          type int32;
          description
            "The value of tmnxDDMLaneRxOpticalPwrHiAlarm indicates the Received
             Optical Power of the CFP/QSFP in one tenths of a micro-Watt (uW) that
             triggers a hi-alarm.";
          smiv2:max-access "read-only";
          smiv2:oid "1.3.6.1.4.1.6527.3.1.2.2.4.66.1.21";
        }
        leaf tmnxDDMLaneRxOpticalPowerType {
          type enumeration {
            enum "oma" {
              value 0;
            }
            enum "average" {
              value 1;
            }
          }
          description
            "The value of tmnxDDMLaneRxOpticalPowerType indicates whether the
             tmnxDDMLaneRxOpticalPower was taken as an average, or as an Optical
             Modulation Amplitude (OMA).";
          smiv2:max-access "read-only";
          smiv2:oid "1.3.6.1.4.1.6527.3.1.2.2.4.66.1.22";
        }
        leaf tmnxDDMLaneFailedThresholds {
          type timetra-port:TmnxDigitalDiagnosticFailureBits;
          description
            "The value of tmnxDDMLaneFailedThresholds indicates which objects
             of the monitored CFP/QSFP is in a failed or cleared threshold state.
             A set bit indicates that the specified threshold has been exceeded.";
          smiv2:max-access "read-only";
          smiv2:oid "1.3.6.1.4.1.6527.3.1.2.2.4.66.1.23";
        }
      }
      config false;
    }
    container tmnxPortPlcyTable {
      description
        "The tmnxPortPlcyTable allows configuration of 
         port policies.
         
         A port policy has port parameters that can be applied
         to applicable ports associated with such a policy.";
      smiv2:oid "1.3.6.1.4.1.6527.3.1.2.2.4.67.2";
      list tmnxPortPlcyEntry {
        key "tmnxPortPlcyName";
        smiv2:implied "tmnxPortPlcyName";
        description
          "Each row represents the configuration
           of a specific port policy.
           
           Rows in this table can be created and deleted via SNMP SET
           operations to tmnxPortPlcyRowStatus.";
        smiv2:oid "1.3.6.1.4.1.6527.3.1.2.2.4.67.2.1";
        leaf tmnxPortPlcyName {
          type timetra-tc:TNamedItem;
          description
            "The value of tmnxPortPlcyName specifies 
             the identifier of a port policy.";
          smiv2:max-access "not-accessible";
          smiv2:oid "1.3.6.1.4.1.6527.3.1.2.2.4.67.2.1.1";
          config true;
        }
        leaf tmnxPortPlcyRowStatus {
          type snmpv2-tc:RowStatus;
          description
            "The value of tmnxPortPlcyRowStatus controls the creation and
             deletion of rows in the table.";
          smiv2:max-access "read-write";
          smiv2:oid "1.3.6.1.4.1.6527.3.1.2.2.4.67.2.1.2";
          config false;
        }
        leaf tmnxPortPlcyLastCh {
          type yang:timestamp;
          description
            "The value of tmnxPortPlcyLastCh indicates the sysUpTime at
             the time of the most recent management-initiated change to this
             policy.";
          smiv2:max-access "read-only";
          smiv2:oid "1.3.6.1.4.1.6527.3.1.2.2.4.67.2.1.3";
          config false;
        }
        leaf tmnxPortPlcyDescription {
          type timetra-tc:TItemDescription;
          description
            "The value of tmnxPortPlcyDescription specifies the user provided
             description of this policy.";
          smiv2:defval "";
          smiv2:max-access "read-write";
          smiv2:oid "1.3.6.1.4.1.6527.3.1.2.2.4.67.2.1.4";
          config true;
        }
        leaf tmnxPortPlcyEgrPortSchedPlcy {
          type timetra-tc:TNamedItemOrEmpty;
          description
            "The value of tmnxPortPlcyEgrPortSchedPlcy specifies
             the egress QoS port-scheduler policy. 
             
             This object must correspond to the index 
             of a row in TIMETRA-QOS-MIB::tPortSchedulerPlcyTable.";
          smiv2:defval "";
          smiv2:max-access "read-write";
          smiv2:oid "1.3.6.1.4.1.6527.3.1.2.2.4.67.2.1.5";
          config true;
        }
        config true;
      }
      config true;
    }
    container tPortNetEgrQGrpArbitStatTable {
      description
        "The value of tPortNetEgrQGrpArbitStatTable contains egress QoS queue
         group arbiter statistics on network side.";
      smiv2:oid "1.3.6.1.4.1.6527.3.1.2.2.4.68";
      list tPortNetEgrQGrpArbitStatEntry {
        key "tmnxChassisIndex tmnxPortPortID tPortNetEgrQGrpName tPortNetEgrQGrpInstanceId tPortNetEgrQGrpArbitStatName";
        description
          "The value of tPortNetEgrQGrpArbitStatEntry defines an entry in the
           tPortNetEgrQGrpArbitStatTable. It represents statistics about a 
           specific QoS egress queue group arbiter.";
        smiv2:oid "1.3.6.1.4.1.6527.3.1.2.2.4.68.1";
        leaf tmnxChassisIndex {
          type leafref {
            path "/timetra-chassis:TIMETRA-CHASSIS-MIB/timetra-chassis:tmnxChassisTable/timetra-chassis:tmnxChassisEntry/timetra-chassis:tmnxChassisIndex";
          }
        }
        leaf tmnxPortPortID {
          type leafref {
            path "/timetra-port:TIMETRA-PORT-MIB/timetra-port:tmnxPortTable/timetra-port:tmnxPortEntry/timetra-port:tmnxPortPortID";
          }
        }
        leaf tPortNetEgrQGrpName {
          type leafref {
            path "/timetra-port:TIMETRA-PORT-MIB/timetra-port:tPortNetEgrQGrpTable/timetra-port:tPortNetEgrQGrpEntry/timetra-port:tPortNetEgrQGrpName";
          }
        }
        leaf tPortNetEgrQGrpInstanceId {
          type leafref {
            path "/timetra-port:TIMETRA-PORT-MIB/timetra-port:tPortNetEgrQGrpTable/timetra-port:tPortNetEgrQGrpEntry/timetra-port:tPortNetEgrQGrpInstanceId";
          }
        }
        leaf tPortNetEgrQGrpArbitStatName {
          type timetra-tc:TNamedItem;
          description
            "The value of tPortNetEgrQGrpArbitStatName specifies the name of the 
             egress QoS arbiter of this port network queue group.";
          smiv2:max-access "not-accessible";
          smiv2:oid "1.3.6.1.4.1.6527.3.1.2.2.4.68.1.1";
        }
        leaf tPortNetEgrQGrpArbitStatFwdPkts {
          type yang:counter64;
          description
            "The value of tPortNetEgrQGrpArbitStatFwdPkts indicates the number of 
             fowrwarded packets by the egress queue group arbiter Pchip.";
          smiv2:max-access "read-only";
          smiv2:oid "1.3.6.1.4.1.6527.3.1.2.2.4.68.1.2";
        }
        leaf tPortNetEgrQGrpArbitStatFwdPktsL {
          type yang:counter32;
          description
            "The value of tPortNetEgrQGrpArbitStatFwdPktsL indicates the lower 32
             bits of tPortNetEgrQGrpArbitStatFwdPkts.";
          smiv2:max-access "read-only";
          smiv2:oid "1.3.6.1.4.1.6527.3.1.2.2.4.68.1.3";
        }
        leaf tPortNetEgrQGrpArbitStatFwdPktsH {
          type yang:counter32;
          description
            "The value of tPortNetEgrQGrpArbitStatFwdPktsH indicates the upper 32
             bits of tPortNetEgrQGrpArbitStatFwdPkts.";
          smiv2:max-access "read-only";
          smiv2:oid "1.3.6.1.4.1.6527.3.1.2.2.4.68.1.4";
        }
        leaf tPortNetEgrQGrpArbitStatFwdOcts {
          type yang:counter64;
          description
            "The value of tPortNetEgrQGrpArbitStatFwdOcts indicates the number of 
             fowrwarded octets by the egress queue group arbiter Pchip.";
          smiv2:max-access "read-only";
          smiv2:oid "1.3.6.1.4.1.6527.3.1.2.2.4.68.1.5";
        }
        leaf tPortNetEgrQGrpArbitStatFwdOctsL {
          type yang:counter32;
          description
            "The value of tPortNetEgrQGrpArbitStatFwdOctsL indicates the lower 32
             bits of tPortNetEgrQGrpArbitStatFwdOcts.";
          smiv2:max-access "read-only";
          smiv2:oid "1.3.6.1.4.1.6527.3.1.2.2.4.68.1.6";
        }
        leaf tPortNetEgrQGrpArbitStatFwdOctsH {
          type yang:counter32;
          description
            "The value of tPortNetEgrQGrpArbitStatFwdOctsH indicates the upper 32
             bits of tPortNetEgrQGrpArbitStatFwdOcts.";
          smiv2:max-access "read-only";
          smiv2:oid "1.3.6.1.4.1.6527.3.1.2.2.4.68.1.7";
        }
      }
      config false;
    }
    container tmnxPwPortTable {
      description
        "A table that contains pseudo-wire port information in the system.";
      smiv2:oid "1.3.6.1.4.1.6527.3.1.2.2.4.70";
      list tmnxPwPortEntry {
        key "tmnxPwPortId";
        description
          "A row-entry that contains port specific pseudo-wire information.";
        smiv2:oid "1.3.6.1.4.1.6527.3.1.2.2.4.70.1";
        leaf tmnxPwPortId {
          type uint32 {
            range "1..10239";
          }
          description
            "This value of the object tmnxPwPortId specifies the pseudo-wire
             port in the system.";
          smiv2:max-access "not-accessible";
          smiv2:oid "1.3.6.1.4.1.6527.3.1.2.2.4.70.1.1";
          config true;
        }
        leaf tmnxPwPortRowStatus {
          type snmpv2-tc:RowStatus;
          description
            "This value of the object tmnxPwPortRowStatus specifies the
             status of this row.";
          smiv2:max-access "read-write";
          smiv2:oid "1.3.6.1.4.1.6527.3.1.2.2.4.70.1.2";
          config false;
        }
        leaf tmnxPwPortLastChgd {
          type yang:timestamp;
          description
            "The value of tmnxPwPortLastChgd indicates the timestamp of last
             change to this row in tmnxPwPortTable.";
          smiv2:max-access "read-only";
          smiv2:oid "1.3.6.1.4.1.6527.3.1.2.2.4.70.1.3";
          config false;
        }
        leaf tmnxPwPortEncapType {
          type enumeration {
            enum "dot1q" {
              value 2;
            }
            enum "qinq" {
              value 10;
            }
          }
          description
            "The value of tmnxPwPortEncapType specifies the encapsulation type
             of this pseudo-wire port entry.";
          smiv2:defval "dot1q";
          smiv2:max-access "read-write";
          smiv2:oid "1.3.6.1.4.1.6527.3.1.2.2.4.70.1.4";
          config true;
        }
        config true;
      }
      config true;
    }
    container tmnxCohOptPortCfgTable {
      description
        "The tmnxCohOptPortCfgTable contains information pertaining to the
         configuration of DWDM coherent optical ports in the Alcatel-Lucent
         SROS system.";
      smiv2:oid "1.3.6.1.4.1.6527.3.1.2.2.4.71";
      list tmnxCohOptPortCfgEntry {
        key "tmnxChassisIndex tmnxPortPortID";
        description
          "Each row entry represents the configuration for a DWDM coherent
           optical port in the system. Entries cannot be created or deleted via
           SNMP SET operations.";
        smiv2:oid "1.3.6.1.4.1.6527.3.1.2.2.4.71.1";
        leaf tmnxChassisIndex {
          type leafref {
            path "/timetra-chassis:TIMETRA-CHASSIS-MIB/timetra-chassis:tmnxChassisTable/timetra-chassis:tmnxChassisEntry/timetra-chassis:tmnxChassisIndex";
          }
          config true;
        }
        leaf tmnxPortPortID {
          type leafref {
            path "/timetra-port:TIMETRA-PORT-MIB/timetra-port:tmnxPortTable/timetra-port:tmnxPortEntry/timetra-port:tmnxPortPortID";
          }
          config true;
        }
        leaf tmnxCohOptPortCfgAlarms {
          type timetra-port:TmnxCoherentOpticalAlarm;
          description
            "The value of tmnxCohOptPortCfgAlarms specifies the alarms that are
             monitored by the coherent optical interface. If an alarm bit is
             set, then the corresponding alarm will generate a raise or clear
             notification when its state changes. An unset bit specifies that the
             alarm corresponding to the bit will not report on its state
             transitions.";
          smiv2:defval "{moduleFault, module, netRx, netTx, hostTx}";
          smiv2:max-access "read-write";
          smiv2:oid "1.3.6.1.4.1.6527.3.1.2.2.4.71.1.1";
          config true;
        }
        leaf tmnxCohOptPortCfgRxChan {
          type timetra-port:TmnxOpticalDwdmChannel;
          description
            "The value of tmnxCohOptPortCfgRxChan specifies the DWDM ITU channel at
             which the tunable coherent optical module should operate.
             
             If a value of zero(0) has been specified, tmnxCohOptPortPresRxChan
             will be changed by the system to be equivalent to
             tmnxPortDwdmLaserChannel.
             
             tmnxCohOptPortCfgRxChan should be set to the same value as
             tmnxPortDwdmLaserChannel in most cases, but may be set to a different
             value when the received wavelength is different from the transmitted
             wavelength.";
          smiv2:defval "0";
          smiv2:max-access "read-write";
          smiv2:oid "1.3.6.1.4.1.6527.3.1.2.2.4.71.1.2";
          config true;
        }
        leaf tmnxCohOptPortDispCtrlMode {
          type timetra-port:TmnxOpticalDispCtrlMode;
          description
            "The value of tmnxCohOptPortDispCtrlMode specifies the current
             dispersion compensation mode of the coherent optical module.
             
             When tmnxCohOptPortDispCtrlMode is set to 'automatic(0)', the
             dispersion setpoint is automatically determined but under the
             constraints specified by tmnxCohOptPortDispSwpStart and
             tmnxCohOptPortDispSwpEnd.
             
             When tmnxCohOptPortDispCtrlMode is set to 'manual(1)', the dispersion
             setpoint is fixed to the value specified by tmnxCohOptPortManCfgDisp.";
          smiv2:defval "automatic";
          smiv2:max-access "read-write";
          smiv2:oid "1.3.6.1.4.1.6527.3.1.2.2.4.71.1.3";
          config true;
        }
        leaf tmnxCohOptPortManCfgDisp {
          type int32 {
            range "-50000..50000";
          }
          units "picoseconds per nanometer";
          description
            "The value of tmnxCohOptPortManCfgDisp specifies the manually
             configured dispersion of the coherent optical module. This parameter
             is valid when the tmnxCohOptPortDispCtrlMode is 'manual(1)'.";
          smiv2:defval "0";
          smiv2:max-access "read-write";
          smiv2:oid "1.3.6.1.4.1.6527.3.1.2.2.4.71.1.4";
          config true;
        }
        leaf tmnxCohOptPortDispSwpStart {
          type int32 {
            range "-50000..50000";
          }
          units "picoseconds per nanometer";
          description
            "The value of tmnxCohOptPortDispSwpStart specifies the start value for
             dispersion sweeping on a coherent optical module.";
          smiv2:defval "-25500";
          smiv2:max-access "read-write";
          smiv2:oid "1.3.6.1.4.1.6527.3.1.2.2.4.71.1.5";
          config true;
        }
        leaf tmnxCohOptPortDispSwpEnd {
          type int32 {
            range "-50000..50000";
          }
          units "picoseconds per nanometer";
          description
            "The value of tmnxCohOptPortDispSwpEnd specifies the end value for
             dispersion sweeping on a coherent optical module.";
          smiv2:defval "2000";
          smiv2:max-access "read-write";
          smiv2:oid "1.3.6.1.4.1.6527.3.1.2.2.4.71.1.6";
          config true;
        }
        leaf tmnxCohOptPortCfgTxPower {
          type int32 {
            range "-2000..300";
          }
          units "mBm";
          description
            "The value of tmnxCohOptPortCfgTxPower specifies the desired average
             output power of the interface's transmitted optical signal when the
             port is enabled.
             
             The UNITS millibels (mBm) are units of 0.01 decibel relative to one
             milliwatt (0 dBm) or dBm multiplied by 100. The mBm is used when an
             integer is required. For example -5.21 dBm is equivalent to -521 mBm.";
          smiv2:defval "100";
          smiv2:max-access "read-write";
          smiv2:oid "1.3.6.1.4.1.6527.3.1.2.2.4.71.1.7";
          config true;
        }
        leaf tmnxCohOptPortCfgCprWinSize {
          type uint32 {
            range "2|4|8|16|32|64";
          }
          units "symbols";
          description
            "The value of tmnxCohOptPortCfgCprWinSize specifies the manually
             configured Carrier Phase Recovery (CPR) window size.
             
             The configured CPR window size is independent of the optimal window
             size, tmnxCohOptPortCprWnSzSrchResult, found by a search using
             tmnxCohOptPortCprWinSizeSearch. Once the network manager has found an
             optimal window size in tmnxCohOptPortCprWnSzSrchResult, the network
             manager has the option to use it for tmnxCohOptPortCfgCprWinSize.";
          smiv2:defval "32";
          smiv2:max-access "read-write";
          smiv2:oid "1.3.6.1.4.1.6527.3.1.2.2.4.71.1.8";
          config true;
        }
        leaf tmnxCohOptPortCfgRxLosThresh {
          type int32 {
            range "-2400..-1300";
          }
          units "mBm";
          description
            "The value of tmnxCohOptPortCfgRxLosThresh specifies the desired
             average input power LOS (Loss Of Signal) threshold of the interface's
             received optical signal.
             
             The UNITS millibels (mBm) are units of 0.01 decibel relative to one
             milliwatt (0 dBm) or dBm multiplied by 100. The mBm is used when an
             integer is required. For example -15.21 dBm is equivalent to -1521
             mBm.";
          smiv2:defval "-2300";
          smiv2:max-access "read-write";
          smiv2:oid "1.3.6.1.4.1.6527.3.1.2.2.4.71.1.9";
          config true;
        }
        leaf tmnxCohOptPortRxLosReaction {
          type timetra-port:TmnxPortLosReaction;
          description
            "The value of tmnxCohOptPortRxLosReaction specifies the type of
             action that is taken in the event of an RX Loss Of Signal (LOS). The
             valid modes are as follows:
             
                    - none     - Specifies that the interface not be taken down on
                                 crossing the optical RX LOS threshold, to allow
                                 the FEC to keep correcting as much as it can.
                    - squelch  - Specifies that the interface be taken down on
                                 crossing the optical RX LOS threshold.";
          smiv2:defval "squelch";
          smiv2:max-access "read-write";
          smiv2:oid "1.3.6.1.4.1.6527.3.1.2.2.4.71.1.10";
          config true;
        }
        config true;
      }
      config true;
    }
    container tmnxCohOptPortOperTable {
      description
        "The tmnxCohOptPortOperTable contains information pertaining to the
         operational state of DWDM coherent optical ports in the Alcatel-Lucent
         SROS system.";
      smiv2:oid "1.3.6.1.4.1.6527.3.1.2.2.4.73";
      list tmnxCohOptPortOperEntry {
        key "tmnxChassisIndex tmnxPortPortID";
        description
          "Each row entry represents the operational state for a DWDM coherent
           optical port in the system. Entries cannot be created or deleted via
           SNMP SET operations.";
        smiv2:oid "1.3.6.1.4.1.6527.3.1.2.2.4.73.1";
        leaf tmnxChassisIndex {
          type leafref {
            path "/timetra-chassis:TIMETRA-CHASSIS-MIB/timetra-chassis:tmnxChassisTable/timetra-chassis:tmnxChassisEntry/timetra-chassis:tmnxChassisIndex";
          }
        }
        leaf tmnxPortPortID {
          type leafref {
            path "/timetra-port:TIMETRA-PORT-MIB/timetra-port:tmnxPortTable/timetra-port:tmnxPortEntry/timetra-port:tmnxPortPortID";
          }
        }
        leaf tmnxCohOptPortAlarmState {
          type timetra-port:TmnxCoherentOpticalAlarm;
          description
            "The value of tmnxCohOptPortAlarmState indicates the coherent optical
             alarms currently active on the port.";
          smiv2:max-access "read-only";
          smiv2:oid "1.3.6.1.4.1.6527.3.1.2.2.4.73.1.1";
        }
        leaf tmnxCohOptPortDefectPoints {
          type timetra-port:TmnxCoherentOpticalDefectPoint;
          description
            "The value of tmnxCohOptPortDefectPoints indicates the coherent optical
             defect points currently active on the port.";
          smiv2:max-access "read-only";
          smiv2:oid "1.3.6.1.4.1.6527.3.1.2.2.4.73.1.2";
        }
        leaf tmnxCohOptPortPresRxChan {
          type timetra-port:TmnxOpticalDwdmChannel;
          description
            "The value of tmnxCohOptPortPresRxChan indicates the DWDM ITU channel
             at which the coherent optical module is operating.";
          smiv2:max-access "read-only";
          smiv2:oid "1.3.6.1.4.1.6527.3.1.2.2.4.73.1.3";
        }
        leaf tmnxCohOptPortModState {
          type enumeration {
            enum "reset" {
              value 0;
            }
            enum "init" {
              value 1;
            }
            enum "lowPower" {
              value 2;
            }
            enum "highPowerUp" {
              value 3;
            }
            enum "highPowerDown" {
              value 4;
            }
            enum "txOff" {
              value 5;
            }
            enum "txTurnOff" {
              value 6;
            }
            enum "txTurnOn" {
              value 7;
            }
            enum "ready" {
              value 8;
            }
            enum "fault" {
              value 9;
            }
          }
          description
            "The value of tmnxCohOptPortModState indicates the state of the
             coherent optical module.
             
                 reset          - The MDIO (Management Data Input/Output) interface
                                  is held in a high impedance state and all module
                                  circuits are in low-power mode.
                 init           - The MDIO remains in high impedance and the module
                                  registers are initialized.
                 lowPower       - All high-power comsuming circuits are in their
                                  low-power condition.
                 highPowerUp    - The module powers up all the functional circuitry
                                  and completes all required initialization of the
                                  module hardware.
                 highPowerDown  - The module powers down power-consuming circuitry
                                  that can be switched to a low-power state.
                 txOff          - The transmitter is turned off, but all other
                                  parts of the module remain high powered and
                                  functional.
                 txTurnOff      - The module turns off the network transmitter.
                 txTurnOn       - The module enables the transmitter.
                 ready          - The module is in a steady-state, ready for
                                  passing data.
                 fault          - A module fault has occurred and as a result the
                                  module is put into its low-power mode.";
          smiv2:max-access "read-only";
          smiv2:oid "1.3.6.1.4.1.6527.3.1.2.2.4.73.1.4";
        }
        leaf tmnxCohOptPortModTxTurnUpStates {
          type bits {
            bit init {
              position 0;
            }
            bit laserTurnUp {
              position 1;
            }
            bit laserReadyOff {
              position 2;
            }
            bit laserReady {
              position 3;
            }
            bit modulatorConverge {
              position 4;
            }
            bit outputPowerAdjust {
              position 5;
            }
          }
          description
            "The value of tmnxCohOptPortModTxTurnUpStates indicates the
             completed TX turn-up states of the coherent optical module.
             
                 init               - The entry state, in which configuration of
                                      the TX path is performed.
                 laserTurnUp        - This state begins the process of tuning the
                                      TX laser and locking devices on the TX path.
                 laserReadyOff      - When the laser is ready for operation, but
                                      light emission is suppressed, this state is
                                      entered.
                 laserReady         - This state brings the laser to full power and
                                      frequency lock.
                 modulatorConverge  - This state enables the TX modulator driver
                                      and waits for convergence of the modulator
                                      automatic bias control loop.
                 outputPowerAdjust  - This state sets and controls the TX output
                                      power using a VOA.";
          smiv2:max-access "read-only";
          smiv2:oid "1.3.6.1.4.1.6527.3.1.2.2.4.73.1.5";
        }
        leaf tmnxCohOptPortModRxTurnUpStates {
          type bits {
            bit init {
              position 0;
            }
            bit laserReady {
              position 1;
            }
            bit waitForInput {
              position 2;
            }
            bit adcSignal {
              position 3;
            }
            bit opticalLock {
              position 4;
            }
            bit demodLock {
              position 5;
            }
          }
          description
            "The value of tmnxCohOptPortModRxTurnUpStates indicates the completed
             RX turn-up states of the coherent optical module.
             
                 init          - The entry state, in which configuration of the RX
                                 path is performed.
                 laserReady    - The RX LO (Local Oscillator) laser is tuned.
                 waitForInput  - The RX input tap is monitored for power that
                                 exceeds the LOS threshold.
                 adcSignal     - When RX input power above LOS is detected, the
                                 module transitions to the ADC Signal
                                 (Analog-to-Digital Converter Signal) state. In the
                                 ADC Signal state the module calibrates the
                                 optical ADCs.
                 opticalLock   - This state (and state demodLock) reflects DSP
                                 operations by the demodulator.
                 demodLock     - In this state, RX path turn-up is achieved.";
          smiv2:max-access "read-only";
          smiv2:oid "1.3.6.1.4.1.6527.3.1.2.2.4.73.1.6";
        }
        leaf tmnxCohOptPortRxSNRXPolar {
          type int32;
          units "0.1 dB";
          description
            "The value of tmnxCohOptPortRxSNRYPolar indicates the network RX
             electrical SNR (Signal-to-Noise Ratio) of X polarization.";
          smiv2:max-access "read-only";
          smiv2:oid "1.3.6.1.4.1.6527.3.1.2.2.4.73.1.7";
        }
        leaf tmnxCohOptPortRxSNRYPolar {
          type int32;
          units "0.1 dB";
          description
            "The value of tmnxCohOptPortRxSNRYPolar indicates the network RX
             electrical SNR of Y polarization.";
          smiv2:max-access "read-only";
          smiv2:oid "1.3.6.1.4.1.6527.3.1.2.2.4.73.1.8";
        }
        leaf tmnxCohOptPortRxQMargin {
          type int32;
          units "0.1 dB";
          description
            "The value of tmnxCohOptPortRxQMargin indicates the RX Q (quality)
             Margin, represented in tenths of a dB.";
          smiv2:max-access "read-only";
          smiv2:oid "1.3.6.1.4.1.6527.3.1.2.2.4.73.1.9";
        }
      }
      config false;
    }
    container tPortEgrHsmdaQStatTable {
      description
        "The tPortEgrHsmdaQStatTable contains egress port HSMDA queue-group 
         Queue statistics.";
      smiv2:oid "1.3.6.1.4.1.6527.3.1.2.2.4.74";
      list tPortEgrHsmdaQStatEntry {
        key "tmnxChassisIndex tmnxPortPortID tPortAccEgrQGrpName tPortAccEgrQGrpInstanceId tPortEgrHsmdaQStatQueueId";
        description
          "The value of tPortEgrHsmdaQStatEntry specifies egress port HSMDA  
           queue-group Queue statistics.";
        smiv2:oid "1.3.6.1.4.1.6527.3.1.2.2.4.74.1";
        leaf tmnxChassisIndex {
          type leafref {
            path "/timetra-chassis:TIMETRA-CHASSIS-MIB/timetra-chassis:tmnxChassisTable/timetra-chassis:tmnxChassisEntry/timetra-chassis:tmnxChassisIndex";
          }
        }
        leaf tmnxPortPortID {
          type leafref {
            path "/timetra-port:TIMETRA-PORT-MIB/timetra-port:tmnxPortTable/timetra-port:tmnxPortEntry/timetra-port:tmnxPortPortID";
          }
        }
        leaf tPortAccEgrQGrpName {
          type leafref {
            path "/timetra-port:TIMETRA-PORT-MIB/timetra-port:tPortAccEgrQGrpTable/timetra-port:tPortAccEgrQGrpEntry/timetra-port:tPortAccEgrQGrpName";
          }
        }
        leaf tPortAccEgrQGrpInstanceId {
          type leafref {
            path "/timetra-port:TIMETRA-PORT-MIB/timetra-port:tPortAccEgrQGrpTable/timetra-port:tPortAccEgrQGrpEntry/timetra-port:tPortAccEgrQGrpInstanceId";
          }
        }
        leaf tPortEgrHsmdaQStatQueueId {
          type timetra-tc:TEgressHsmdaQueueId;
          description
            "The value of tPortEgrHsmdaQStatQueueId specifies the HSMDA queue ID 
             for the statistics.";
          smiv2:max-access "not-accessible";
          smiv2:oid "1.3.6.1.4.1.6527.3.1.2.2.4.74.1.1";
        }
        leaf tPortEgrHsmdaQStatFwdInProfPkts {
          type yang:counter64;
          description
            "The value of tPortEgrHsmdaQStatFwdInProfPkts indicates the number of
             in-profile packets forwarded on this egress port.";
          smiv2:max-access "read-only";
          smiv2:oid "1.3.6.1.4.1.6527.3.1.2.2.4.74.1.2";
        }
        leaf tPortEgrHsmdaQStatFwdInProfPktH {
          type yang:counter32;
          description
            "The value of tPortEgrHsmdaQStatFwdInProfPktH indicates the upper 
             32-bits of tPortEgrHsmdaQStatFwdInProfPkts.";
          smiv2:max-access "read-only";
          smiv2:oid "1.3.6.1.4.1.6527.3.1.2.2.4.74.1.3";
        }
        leaf tPortEgrHsmdaQStatFwdInProfPktL {
          type yang:counter32;
          description
            "The value of tPortEgrHsmdaQStatFwdInProfPktL indicates the lower 
             32-bits of tPortEgrHsmdaQStatFwdInProfPkts.";
          smiv2:max-access "read-only";
          smiv2:oid "1.3.6.1.4.1.6527.3.1.2.2.4.74.1.4";
        }
        leaf tPortEgrHsmdaQStatDpdInProfPkts {
          type yang:counter64;
          description
            "The value of tPortEgrHsmdaQStatDpdInProfPkts indicates the number of
             in-profile packets dropped on this egress port.";
          smiv2:max-access "read-only";
          smiv2:oid "1.3.6.1.4.1.6527.3.1.2.2.4.74.1.5";
        }
        leaf tPortEgrHsmdaQStatDpdInProfPktH {
          type yang:counter32;
          description
            "The value of tPortEgrHsmdaQStatDpdInProfPktH indicates the upper 
             32-bits of tPortEgrHsmdaQStatDpdInProfPkts.";
          smiv2:max-access "read-only";
          smiv2:oid "1.3.6.1.4.1.6527.3.1.2.2.4.74.1.6";
        }
        leaf tPortEgrHsmdaQStatDpdInProfPktL {
          type yang:counter32;
          description
            "The value of tPortEgrHsmdaQStatDpdInProfPktL indicates the lower 
             32-bits of tPortEgrHsmdaQStatDpdInProfPkts.";
          smiv2:max-access "read-only";
          smiv2:oid "1.3.6.1.4.1.6527.3.1.2.2.4.74.1.7";
        }
        leaf tPortEgrHsmdaQStatFwdOutProfPkts {
          type yang:counter64;
          description
            "The value of tPortEgrHsmdaQStatFwdOutProfPkts indicates the number of
             out-of-profile packets forwarded on this egress port.";
          smiv2:max-access "read-only";
          smiv2:oid "1.3.6.1.4.1.6527.3.1.2.2.4.74.1.8";
        }
        leaf tPortEgrHsmdaQStatFwdOutProfPktH {
          type yang:counter32;
          description
            "The value of tPortEgrHsmdaQStatFwdOutProfPktH indicates the upper 
             32-bits of tPortEgrHsmdaQStatFwdOutProfPkts.";
          smiv2:max-access "read-only";
          smiv2:oid "1.3.6.1.4.1.6527.3.1.2.2.4.74.1.9";
        }
        leaf tPortEgrHsmdaQStatFwdOutProfPktL {
          type yang:counter32;
          description
            "The value of tPortEgrHsmdaQStatFwdOutProfPktL indicates the lower 
             32-bits of tPortEgrHsmdaQStatFwdOutProfPkts.";
          smiv2:max-access "read-only";
          smiv2:oid "1.3.6.1.4.1.6527.3.1.2.2.4.74.1.10";
        }
        leaf tPortEgrHsmdaQStatDpdOutProfPkts {
          type yang:counter64;
          description
            "The value of tPortEgrHsmdaQStatDpdOutProfPkts indicates the number of
             out-of-profile packets dropped on this egress port.";
          smiv2:max-access "read-only";
          smiv2:oid "1.3.6.1.4.1.6527.3.1.2.2.4.74.1.11";
        }
        leaf tPortEgrHsmdaQStatDpdOutProfPktH {
          type yang:counter32;
          description
            "The value of tPortEgrHsmdaQStatDpdOutProfPktH indicates the upper 
             32-bits of tPortEgrHsmdaQStatDpdOutProfPkts.";
          smiv2:max-access "read-only";
          smiv2:oid "1.3.6.1.4.1.6527.3.1.2.2.4.74.1.12";
        }
        leaf tPortEgrHsmdaQStatDpdOutProfPktL {
          type yang:counter32;
          description
            "The value of tPortEgrHsmdaQStatDpdOutProfPktL indicates the lower 
             32-bits of tPortEgrHsmdaQStatDpdOutProfPkts.";
          smiv2:max-access "read-only";
          smiv2:oid "1.3.6.1.4.1.6527.3.1.2.2.4.74.1.13";
        }
        leaf tPortEgrHsmdaQStatFwdInProfOcts {
          type yang:counter64;
          description
            "The value of tPortEgrHsmdaQStatFwdInProfOcts indicates the number of
             out-of-profile octects forwarded on this egress port.";
          smiv2:max-access "read-only";
          smiv2:oid "1.3.6.1.4.1.6527.3.1.2.2.4.74.1.14";
        }
        leaf tPortEgrHsmdaQStatFwdInProfOctH {
          type yang:counter32;
          description
            "The value of tPortEgrHsmdaQStatFwdInProfOctH indicates the upper 
             32-bits of tPortEgrHsmdaQStatFwdInProfOcts.";
          smiv2:max-access "read-only";
          smiv2:oid "1.3.6.1.4.1.6527.3.1.2.2.4.74.1.15";
        }
        leaf tPortEgrHsmdaQStatFwdInProfOctL {
          type yang:counter32;
          description
            "The value of tPortEgrHsmdaQStatFwdInProfOctL indicates the lower 
             32-bits of tPortEgrHsmdaQStatFwdInProfOcts.";
          smiv2:max-access "read-only";
          smiv2:oid "1.3.6.1.4.1.6527.3.1.2.2.4.74.1.16";
        }
        leaf tPortEgrHsmdaQStatDpdInProfOcts {
          type yang:counter64;
          description
            "The value of tPortEgrHsmdaQStatDpdInProfOcts indicates the number of
             out-of-profile octects dropped on this egress port.";
          smiv2:max-access "read-only";
          smiv2:oid "1.3.6.1.4.1.6527.3.1.2.2.4.74.1.17";
        }
        leaf tPortEgrHsmdaQStatDpdInProfOctH {
          type yang:counter32;
          description
            "The value of tPortEgrHsmdaQStatDpdInProfOctH indicates the upper 
             32-bits of tPortEgrHsmdaQStatDpdInProfOcts.";
          smiv2:max-access "read-only";
          smiv2:oid "1.3.6.1.4.1.6527.3.1.2.2.4.74.1.18";
        }
        leaf tPortEgrHsmdaQStatDpdInProfOctL {
          type yang:counter32;
          description
            "The value of tPortEgrHsmdaQStatDpdInProfOctL indicates the lower 
             32-bits of tPortEgrHsmdaQStatDpdInProfOcts.";
          smiv2:max-access "read-only";
          smiv2:oid "1.3.6.1.4.1.6527.3.1.2.2.4.74.1.19";
        }
        leaf tPortEgrHsmdaQStatFwdOutProfOcts {
          type yang:counter64;
          description
            "The value of tPortEgrHsmdaQStatFwdOutProfOcts indicates the number of
             out-of-profile octects forwarded on this egress port.";
          smiv2:max-access "read-only";
          smiv2:oid "1.3.6.1.4.1.6527.3.1.2.2.4.74.1.20";
        }
        leaf tPortEgrHsmdaQStatFwdOutProfOctH {
          type yang:counter32;
          description
            "The value of tPortEgrHsmdaQStatFwdOutProfOctH indicates the upper 
             32-bits of tPortEgrHsmdaQStatFwdOutProfOcts.";
          smiv2:max-access "read-only";
          smiv2:oid "1.3.6.1.4.1.6527.3.1.2.2.4.74.1.21";
        }
        leaf tPortEgrHsmdaQStatFwdOutProfOctL {
          type yang:counter32;
          description
            "The value of tPortEgrHsmdaQStatFwdOutProfOctL indicates the lower 
             32-bits of tPortEgrHsmdaQStatFwdOutProfOcts.";
          smiv2:max-access "read-only";
          smiv2:oid "1.3.6.1.4.1.6527.3.1.2.2.4.74.1.22";
        }
        leaf tPortEgrHsmdaQStatDpdOutProfOcts {
          type yang:counter64;
          description
            "The value of tPortEgrHsmdaQStatDpdOutProfOcts indicates the number of
             out-of-profile octects dropped on egress this egress port.";
          smiv2:max-access "read-only";
          smiv2:oid "1.3.6.1.4.1.6527.3.1.2.2.4.74.1.23";
        }
        leaf tPortEgrHsmdaQStatDpdOutProfOctH {
          type yang:counter32;
          description
            "The value of tPortEgrHsmdaQStatDpdOutProfOctH indicates the upper 
             32-bits of tPortEgrHsmdaQStatDpdOutProfOcts.";
          smiv2:max-access "read-only";
          smiv2:oid "1.3.6.1.4.1.6527.3.1.2.2.4.74.1.24";
        }
        leaf tPortEgrHsmdaQStatDpdOutProfOctL {
          type yang:counter32;
          description
            "The value of tPortEgrHsmdaQStatDpdOutProfOctL indicates the lower 
             32-bits of tPortEgrHsmdaQStatDpdOutProfOcts.";
          smiv2:max-access "read-only";
          smiv2:oid "1.3.6.1.4.1.6527.3.1.2.2.4.74.1.25";
        }
      }
      config false;
    }
    container tPortEgrHsmdaCStatTable {
      description
        "The tPortEgrHsmdaCStatTable contains egress port HSMDA queue-group 
         Counter statistics.";
      smiv2:oid "1.3.6.1.4.1.6527.3.1.2.2.4.75";
      list tPortEgrHsmdaCStatEntry {
        key "tmnxChassisIndex tmnxPortPortID tPortAccEgrQGrpName tPortAccEgrQGrpInstanceId tPortEgrHsmdaCStatCntrId";
        description
          "The value of tPortEgrHsmdaCStatEntry specifies egress port HSMDA
           queue-group Counter statistics.";
        smiv2:oid "1.3.6.1.4.1.6527.3.1.2.2.4.75.1";
        leaf tmnxChassisIndex {
          type leafref {
            path "/timetra-chassis:TIMETRA-CHASSIS-MIB/timetra-chassis:tmnxChassisTable/timetra-chassis:tmnxChassisEntry/timetra-chassis:tmnxChassisIndex";
          }
        }
        leaf tmnxPortPortID {
          type leafref {
            path "/timetra-port:TIMETRA-PORT-MIB/timetra-port:tmnxPortTable/timetra-port:tmnxPortEntry/timetra-port:tmnxPortPortID";
          }
        }
        leaf tPortAccEgrQGrpName {
          type leafref {
            path "/timetra-port:TIMETRA-PORT-MIB/timetra-port:tPortAccEgrQGrpTable/timetra-port:tPortAccEgrQGrpEntry/timetra-port:tPortAccEgrQGrpName";
          }
        }
        leaf tPortAccEgrQGrpInstanceId {
          type leafref {
            path "/timetra-port:TIMETRA-PORT-MIB/timetra-port:tPortAccEgrQGrpTable/timetra-port:tPortAccEgrQGrpEntry/timetra-port:tPortAccEgrQGrpInstanceId";
          }
        }
        leaf tPortEgrHsmdaCStatCntrId {
          type timetra-tc:TEgressHsmdaCounterId;
          description
            "The value of tPortEgrHsmdaCStatCntrId specifies the HSMDA counter ID 
             for the statistics.";
          smiv2:max-access "not-accessible";
          smiv2:oid "1.3.6.1.4.1.6527.3.1.2.2.4.75.1.1";
        }
        leaf tPortEgrHsmdaCStatFwdInProfPkts {
          type yang:counter64;
          description
            "The value of tPortEgrHsmdaCStatFwdInProfPkts indicates the number of
             in-profile packets forwarded for the egress counter, specified by the
             index tPortEgrHsmdaCStatCntrId, on this port.";
          smiv2:max-access "read-only";
          smiv2:oid "1.3.6.1.4.1.6527.3.1.2.2.4.75.1.2";
        }
        leaf tPortEgrHsmdaCStatFwdInProfPktH {
          type yang:counter32;
          description
            "The value of tPortEgrHsmdaCStatFwdInProfPktH indicates the upper 
             32-bits of tPortEgrHsmdaCStatFwdInProfPkts.";
          smiv2:max-access "read-only";
          smiv2:oid "1.3.6.1.4.1.6527.3.1.2.2.4.75.1.3";
        }
        leaf tPortEgrHsmdaCStatFwdInProfPktL {
          type yang:counter32;
          description
            "The value of tPortEgrHsmdaCStatFwdInProfPktL indicates the lower 
             32-bits of tPortEgrHsmdaCStatFwdInProfPkts.";
          smiv2:max-access "read-only";
          smiv2:oid "1.3.6.1.4.1.6527.3.1.2.2.4.75.1.4";
        }
        leaf tPortEgrHsmdaCStatDpdInProfPkts {
          type yang:counter64;
          description
            "The value of tPortEgrHsmdaCStatDpdInProfPkts indicates the number of
             in-profile packets dropped for the egress counter, specified by the
             index tPortEgrHsmdaCStatCntrId, on this port.";
          smiv2:max-access "read-only";
          smiv2:oid "1.3.6.1.4.1.6527.3.1.2.2.4.75.1.5";
        }
        leaf tPortEgrHsmdaCStatDpdInProfPktH {
          type yang:counter32;
          description
            "The value of tPortEgrHsmdaCStatDpdInProfPktH indicates the upper 
             32-bits of tPortEgrHsmdaCStatDpdInProfPkts.";
          smiv2:max-access "read-only";
          smiv2:oid "1.3.6.1.4.1.6527.3.1.2.2.4.75.1.6";
        }
        leaf tPortEgrHsmdaCStatDpdInProfPktL {
          type yang:counter32;
          description
            "The value of tPortEgrHsmdaCStatDpdInProfPktL indicates the lower 
             32-bits of tPortEgrHsmdaCStatDpdInProfPkts.";
          smiv2:max-access "read-only";
          smiv2:oid "1.3.6.1.4.1.6527.3.1.2.2.4.75.1.7";
        }
        leaf tPortEgrHsmdaCStatFwdOutProfPkts {
          type yang:counter64;
          description
            "The value of tPortEgrHsmdaCStatFwdOutProfPkts indicates the number of
             out-of-profile packets forwarded for the egress counter, specified by 
             the index tPortEgrHsmdaCStatCntrId, on this port.";
          smiv2:max-access "read-only";
          smiv2:oid "1.3.6.1.4.1.6527.3.1.2.2.4.75.1.8";
        }
        leaf tPortEgrHsmdaCStatFwdOutProfPktH {
          type yang:counter32;
          description
            "The value of tPortEgrHsmdaCStatFwdOutProfPktH indicates the upper 
             32-bits of tPortEgrHsmdaCStatFwdOutProfPkts.";
          smiv2:max-access "read-only";
          smiv2:oid "1.3.6.1.4.1.6527.3.1.2.2.4.75.1.9";
        }
        leaf tPortEgrHsmdaCStatFwdOutProfPktL {
          type yang:counter32;
          description
            "The value of tPortEgrHsmdaCStatFwdOutProfPktL indicates the lower 
             32-bits of tPortEgrHsmdaCStatFwdOutProfPkts.";
          smiv2:max-access "read-only";
          smiv2:oid "1.3.6.1.4.1.6527.3.1.2.2.4.75.1.10";
        }
        leaf tPortEgrHsmdaCStatDpdOutProfPkts {
          type yang:counter64;
          description
            "The value of tPortEgrHsmdaCStatDpdOutProfPkts indicates the number of
             out-of-profile packets dropped or the egress counter, specified by the
             index tPortEgrHsmdaCStatCntrId, on this port.";
          smiv2:max-access "read-only";
          smiv2:oid "1.3.6.1.4.1.6527.3.1.2.2.4.75.1.11";
        }
        leaf tPortEgrHsmdaCStatDpdOutProfPktH {
          type yang:counter32;
          description
            "The value of tPortEgrHsmdaCStatDpdOutProfPktH indicates the upper 
             32-bits of tPortEgrHsmdaCStatDpdOutProfPkts.";
          smiv2:max-access "read-only";
          smiv2:oid "1.3.6.1.4.1.6527.3.1.2.2.4.75.1.12";
        }
        leaf tPortEgrHsmdaCStatDpdOutProfPktL {
          type yang:counter32;
          description
            "The value of tPortEgrHsmdaCStatDpdOutProfPktL indicates the lower 
             32-bits of tPortEgrHsmdaCStatDpdOutProfPkts.";
          smiv2:max-access "read-only";
          smiv2:oid "1.3.6.1.4.1.6527.3.1.2.2.4.75.1.13";
        }
        leaf tPortEgrHsmdaCStatFwdInProfOcts {
          type yang:counter64;
          description
            "The value of tPortEgrHsmdaCStatFwdInProfOcts indicates the number of
             out-of-profile octects forwarded for the egress counter, specified by 
             the index tPortEgrHsmdaCStatCntrId, on this port.";
          smiv2:max-access "read-only";
          smiv2:oid "1.3.6.1.4.1.6527.3.1.2.2.4.75.1.14";
        }
        leaf tPortEgrHsmdaCStatFwdInProfOctH {
          type yang:counter32;
          description
            "The value of tPortEgrHsmdaCStatFwdInProfOctH indicates the upper 
             32-bits of tPortEgrHsmdaCStatFwdInProfOcts.";
          smiv2:max-access "read-only";
          smiv2:oid "1.3.6.1.4.1.6527.3.1.2.2.4.75.1.15";
        }
        leaf tPortEgrHsmdaCStatFwdInProfOctL {
          type yang:counter32;
          description
            "The value of tPortEgrHsmdaCStatFwdInProfOctL indicates the lower 
             32-bits of tPortEgrHsmdaCStatFwdInProfOcts.";
          smiv2:max-access "read-only";
          smiv2:oid "1.3.6.1.4.1.6527.3.1.2.2.4.75.1.16";
        }
        leaf tPortEgrHsmdaCStatDpdInProfOcts {
          type yang:counter64;
          description
            "The value of tPortEgrHsmdaCStatDpdInProfOcts indicates the number of
             out-of-profile octects dropped for the egress counter, specified by the
             index tPortEgrHsmdaCStatCntrId, on this port.";
          smiv2:max-access "read-only";
          smiv2:oid "1.3.6.1.4.1.6527.3.1.2.2.4.75.1.17";
        }
        leaf tPortEgrHsmdaCStatDpdInProfOctH {
          type yang:counter32;
          description
            "The value of tPortEgrHsmdaCStatDpdInProfOctH indicates the upper 
             32-bits of tPortEgrHsmdaCStatDpdInProfOcts.";
          smiv2:max-access "read-only";
          smiv2:oid "1.3.6.1.4.1.6527.3.1.2.2.4.75.1.18";
        }
        leaf tPortEgrHsmdaCStatDpdInProfOctL {
          type yang:counter32;
          description
            "The value of tPortEgrHsmdaCStatDpdInProfOctL indicates the lower 
             32-bits of tPortEgrHsmdaCStatDpdInProfOcts.";
          smiv2:max-access "read-only";
          smiv2:oid "1.3.6.1.4.1.6527.3.1.2.2.4.75.1.19";
        }
        leaf tPortEgrHsmdaCStatFwdOutProfOcts {
          type yang:counter64;
          description
            "The value of tPortEgrHsmdaCStatFwdOutProfOcts indicates the number of
             out-of-profile octects forwarded for the egress counter, specified by 
             the index tPortEgrHsmdaCStatCntrId, on this port.";
          smiv2:max-access "read-only";
          smiv2:oid "1.3.6.1.4.1.6527.3.1.2.2.4.75.1.20";
        }
        leaf tPortEgrHsmdaCStatFwdOutProfOctH {
          type yang:counter32;
          description
            "The value of tPortEgrHsmdaCStatFwdOutProfOctH indicates the upper 
             32-bits of tPortEgrHsmdaCStatFwdOutProfOcts.";
          smiv2:max-access "read-only";
          smiv2:oid "1.3.6.1.4.1.6527.3.1.2.2.4.75.1.21";
        }
        leaf tPortEgrHsmdaCStatFwdOutProfOctL {
          type yang:counter32;
          description
            "The value of tPortEgrHsmdaCStatFwdOutProfOctL indicates the lower 
             32-bits of tPortEgrHsmdaCStatFwdOutProfOcts.";
          smiv2:max-access "read-only";
          smiv2:oid "1.3.6.1.4.1.6527.3.1.2.2.4.75.1.22";
        }
        leaf tPortEgrHsmdaCStatDpdOutProfOcts {
          type yang:counter64;
          description
            "The value of tPortEgrHsmdaCStatDpdOutProfOcts indicates the number of
             out-of-profile octects dropped for the egress counter, specified by the
             index tPortEgrHsmdaCStatCntrId, on this port.";
          smiv2:max-access "read-only";
          smiv2:oid "1.3.6.1.4.1.6527.3.1.2.2.4.75.1.23";
        }
        leaf tPortEgrHsmdaCStatDpdOutProfOctH {
          type yang:counter32;
          description
            "The value of tPortEgrHsmdaCStatDpdOutProfOctH indicates the upper 
             32-bits of tPortEgrHsmdaCStatDpdOutProfOcts.";
          smiv2:max-access "read-only";
          smiv2:oid "1.3.6.1.4.1.6527.3.1.2.2.4.75.1.24";
        }
        leaf tPortEgrHsmdaCStatDpdOutProfOctL {
          type yang:counter32;
          description
            "The value of tPortEgrHsmdaCStatDpdOutProfOctL indicates the lower 
             32-bits of tPortEgrHsmdaCStatDpdOutProfOcts.";
          smiv2:max-access "read-only";
          smiv2:oid "1.3.6.1.4.1.6527.3.1.2.2.4.75.1.25";
        }
      }
      config false;
    }
    container tPortAccEgrHsmdaQOverTable {
      description
        "The tPortAccEgrHsmdaQOverTable has an entry for each access egress port
         queue-group hsmda queue override configured on this system.";
      smiv2:oid "1.3.6.1.4.1.6527.3.1.2.2.4.76";
      list tPortAccEgrHsmdaQOverEntry {
        key "tmnxChassisIndex tmnxPortPortID tPortAccEgrQGrpName tPortAccEgrQGrpInstanceId tPortAccEgrHsmdaQOverQueue";
        description
          "Each row represents a particular port queue-group hsmda queue override.
           Entries are created and deleted by the user.";
        smiv2:oid "1.3.6.1.4.1.6527.3.1.2.2.4.76.1";
        leaf tmnxChassisIndex {
          type leafref {
            path "/timetra-chassis:TIMETRA-CHASSIS-MIB/timetra-chassis:tmnxChassisTable/timetra-chassis:tmnxChassisEntry/timetra-chassis:tmnxChassisIndex";
          }
          config true;
        }
        leaf tmnxPortPortID {
          type leafref {
            path "/timetra-port:TIMETRA-PORT-MIB/timetra-port:tmnxPortTable/timetra-port:tmnxPortEntry/timetra-port:tmnxPortPortID";
          }
          config true;
        }
        leaf tPortAccEgrQGrpName {
          type leafref {
            path "/timetra-port:TIMETRA-PORT-MIB/timetra-port:tPortAccEgrQGrpTable/timetra-port:tPortAccEgrQGrpEntry/timetra-port:tPortAccEgrQGrpName";
          }
          config true;
        }
        leaf tPortAccEgrQGrpInstanceId {
          type leafref {
            path "/timetra-port:TIMETRA-PORT-MIB/timetra-port:tPortAccEgrQGrpTable/timetra-port:tPortAccEgrQGrpEntry/timetra-port:tPortAccEgrQGrpInstanceId";
          }
          config true;
        }
        leaf tPortAccEgrHsmdaQOverQueue {
          type timetra-tc:TEgressHsmdaQueueId;
          description
            "The value of tPortAccEgrHsmdaQOverQueue specifies the hsmda egress
             queue which this override record will affect.";
          smiv2:max-access "not-accessible";
          smiv2:oid "1.3.6.1.4.1.6527.3.1.2.2.4.76.1.1";
          config true;
        }
        leaf tPortAccEgrHsmdaQOverRowStatus {
          type snmpv2-tc:RowStatus;
          description
            "The value of tPortAccEgrHsmdaQOverRowStatus controls the creation and
             deletion of rows in this table.";
          smiv2:max-access "read-write";
          smiv2:oid "1.3.6.1.4.1.6527.3.1.2.2.4.76.1.2";
          config false;
        }
        leaf tPortAccEgrHsmdaQOverLastChanged {
          type yang:timestamp;
          description
            "The value of tPortAccEgrHsmdaQOverLastChanged indicates the sysUpTime
             at the time of the most recent management-initiated change to this
             table row.";
          smiv2:max-access "read-only";
          smiv2:oid "1.3.6.1.4.1.6527.3.1.2.2.4.76.1.3";
          config false;
        }
        leaf tPortAccEgrHsmdaQOverAdminPIR {
          type timetra-tc:THsmdaPIRKRateOverride;
          units "kbps";
          description
            "The value of tPortAccEgrHsmdaQOverAdminPIR specifies the PIR rate
             allowed for this hsmda egress queue-group queue.";
          smiv2:defval "-2";
          smiv2:max-access "read-write";
          smiv2:oid "1.3.6.1.4.1.6527.3.1.2.2.4.76.1.4";
          config true;
        }
        leaf tPortAccEgrHsmdaQOverSlopePolicy {
          type timetra-tc:TNamedItemOrEmpty;
          description
            "The value of tPortAccEgrHsmdaQOverSlopePolicy specifies the slope
             policy that defines the RED slopes for this hsmda egress queue-group
             queue.";
          smiv2:defval "";
          smiv2:max-access "read-write";
          smiv2:oid "1.3.6.1.4.1.6527.3.1.2.2.4.76.1.5";
          config true;
        }
        leaf tPortAccEgrHsmdaQOverWrrWeight {
          type timetra-tc:THsmdaWrrWeightOverride;
          description
            "The value of tPortAccEgrHsmdaQOverWrrWeight specifies the weighted 
             round-robin weight override for the given hsmda queue for this
             queue-group instance.
             
             When set to default value, the weighted round-robin weight is not 
             overridden and the weighted round-robin weight from the queue-group
             template is honored.  When a non-default value is given, that value is
             used instead of the weighted round-robin weight given in the
             queue-group template.";
          smiv2:defval "-2";
          smiv2:max-access "read-write";
          smiv2:oid "1.3.6.1.4.1.6527.3.1.2.2.4.76.1.6";
          config true;
        }
        leaf tPortAccEgrHsmdaQOverMBS {
          type timetra-tc:THSMDABurstSizeBytesOverride;
          units "bytes";
          description
            "The value of tPortAccEgrHsmdaQOverMBS specifies the maximum buffer
             space (MBS) override for the given egress hsmda queue for this
             queue-group instance. 
             
             When set to default value, the MBS is not overridden and the MBS from 
             the queue-group template is honored. When a non-default value is given,
             that is used instead of the MBS given in the queue-group template.";
          smiv2:defval "-2";
          smiv2:max-access "read-write";
          smiv2:oid "1.3.6.1.4.1.6527.3.1.2.2.4.76.1.7";
          config true;
        }
        config true;
      }
      config true;
    }
    container tmnxFRDlcmiTable {
      description
        "The tmnxFRDlcmiTable has an entry for each port in the
         system that is configured for Frame Relay. It contains
         the parameters for the Data Link Connection Management
         Interface (DLCMI) for the frame relay service on this port.";
      smiv2:oid "1.3.6.1.4.1.6527.3.1.2.2.9.1";
      list tmnxFRDlcmiEntry {
        key "tmnxChassisIndex tmnxPortPortID";
        description
          "The Parameters for a particular Data Link Connection
           Management Interface. Entries cannot be created and
           deleted via SNMP SET operations.";
        smiv2:oid "1.3.6.1.4.1.6527.3.1.2.2.9.1.1";
        leaf tmnxChassisIndex {
          type leafref {
            path "/timetra-chassis:TIMETRA-CHASSIS-MIB/timetra-chassis:tmnxChassisTable/timetra-chassis:tmnxChassisEntry/timetra-chassis:tmnxChassisIndex";
          }
          config true;
        }
        leaf tmnxPortPortID {
          type leafref {
            path "/timetra-port:TIMETRA-PORT-MIB/timetra-port:tmnxPortTable/timetra-port:tmnxPortEntry/timetra-port:tmnxPortPortID";
          }
          config true;
        }
        leaf tmnxFRDlcmiMode {
          type enumeration {
            enum "dte" {
              value 1;
            }
            enum "dce" {
              value 2;
            }
            enum "bidir" {
              value 3;
            }
          }
          description
            "tmnxFRDlcmiMode is used to set the mode of the interface.
             It can be set as Data terminal equipment (dte),
             Data circuit-terminating equipment (dce) or both as Data
             terminal equipment and Data circuit-terminating
             equipment (bidir). ";
          smiv2:defval "dte";
          smiv2:max-access "read-write";
          smiv2:oid "1.3.6.1.4.1.6527.3.1.2.2.9.1.1.1";
          config true;
        }
        leaf tmnxFRDlcmiN392Dce {
          type int32 {
            range "1..10";
          }
          description
            "tmnxFRDlcmiN392Dce is used to configure the LMI error
             threshold for DCE interface.";
          smiv2:defval "3";
          smiv2:max-access "read-write";
          smiv2:oid "1.3.6.1.4.1.6527.3.1.2.2.9.1.1.2";
          config true;
        }
        leaf tmnxFRDlcmiN393Dce {
          type int32 {
            range "1..10";
          }
          description
            "tmnxFRDlcmiN393Dce is used to configure the LMI monitored
             event count for DCE interface.";
          smiv2:defval "4";
          smiv2:max-access "read-write";
          smiv2:oid "1.3.6.1.4.1.6527.3.1.2.2.9.1.1.3";
          config true;
        }
        leaf tmnxFRDlcmiT392Dce {
          type int32 {
            range "5..30";
          }
          units "seconds";
          description
            "tmnxFRDlcmiT392Dce is used to configure the polling verification
             timer for the Frame Relay DCE interface.";
          smiv2:defval "15";
          smiv2:max-access "read-write";
          smiv2:oid "1.3.6.1.4.1.6527.3.1.2.2.9.1.1.4";
          config true;
        }
        leaf tmnxFRDlcmiTxStatusEnqMsgs {
          type yang:counter32;
          units "messages";
          description
            "tmnxFRDlcmiTxStatusEnqMsgs indicates the number of LMI Status
             Enquiry messages transmitted on this Frame Relay interface.";
          smiv2:max-access "read-only";
          smiv2:oid "1.3.6.1.4.1.6527.3.1.2.2.9.1.1.5";
          config false;
        }
        leaf tmnxFRDlcmiRxStatusEnqMsgs {
          type yang:counter32;
          units "messages";
          description
            "tmnxFRDlcmiRxStatusEnqMsgs indicates the number of LMI Status
             Enquiry messages received on this Frame Relay interface.";
          smiv2:max-access "read-only";
          smiv2:oid "1.3.6.1.4.1.6527.3.1.2.2.9.1.1.6";
          config false;
        }
        leaf tmnxFRDlcmiStatusEnqMsgTimeouts {
          type yang:counter32;
          units "messages";
          description
            "tmnxFRDlcmiStatusEnqMsgTimeouts indicates the number of times
             the LMI agent did not receive a Status Enquiry message within
             the allotted time.";
          smiv2:max-access "read-only";
          smiv2:oid "1.3.6.1.4.1.6527.3.1.2.2.9.1.1.7";
          config false;
        }
        leaf tmnxFRDlcmiTxStatusMsgs {
          type yang:counter32;
          units "messages";
          description
            "tmnxFRDlcmiTxStatusMsgs indicates the number of LMI Status
             messages transmitted on this Frame Relay interface.";
          smiv2:max-access "read-only";
          smiv2:oid "1.3.6.1.4.1.6527.3.1.2.2.9.1.1.8";
          config false;
        }
        leaf tmnxFRDlcmiRxStatusMsgs {
          type yang:counter32;
          units "messages";
          description
            "tmnxFRDlcmiRxStatusMsgs indicates the number of LMI Status
             messages received on this Frame Relay interface.";
          smiv2:max-access "read-only";
          smiv2:oid "1.3.6.1.4.1.6527.3.1.2.2.9.1.1.9";
          config false;
        }
        leaf tmnxFRDlcmiStatusMsgTimeouts {
          type yang:counter32;
          units "messages";
          description
            "tmnxFRDlcmiStatusMsgTimeouts indicates the number of times
             the LMI agent did not receive a Status message within the
             allotted time.";
          smiv2:max-access "read-only";
          smiv2:oid "1.3.6.1.4.1.6527.3.1.2.2.9.1.1.10";
          config false;
        }
        leaf tmnxFRDlcmiDiscardedMsgs {
          type yang:counter32;
          units "messages";
          description
            "tmnxFRDlcmiDiscardedMsgs indicates the number of times
             the LMI agent discarded a received message because it
             wasn't expecting it, the type of message was incorrect,
             or the contents of the message were invalid.";
          smiv2:max-access "read-only";
          smiv2:oid "1.3.6.1.4.1.6527.3.1.2.2.9.1.1.11";
          config false;
        }
        leaf tmnxFRDlcmiInvRxSeqNumMsgs {
          type yang:counter32;
          units "messages";
          description
            "tmnxFRDlcmiInvRxSeqNumMsgs indicates the number of times
             the LMI agent received a message with an invalid receive
             sequence number: i.e. a sequence number that does not
             match the last transmitted sequence number of the agent.";
          smiv2:max-access "read-only";
          smiv2:oid "1.3.6.1.4.1.6527.3.1.2.2.9.1.1.12";
          config false;
        }
        config true;
      }
      config true;
    }
    container tmnxFrIntfTable {
      description
        "The tmnxFrIntfTable has an entry for each port/channel in the
         system that is configured for Frame Relay. It contains Frame Relay
         configuration parameters.";
      smiv2:oid "1.3.6.1.4.1.6527.3.1.2.2.9.2";
      list tmnxFrIntfEntry {
        key "tmnxChassisIndex tmnxPortPortID";
        description
          "The Parameters for a particular FR Interface. Entries cannot be
           created or deleted via SNMP SET operations.
           
           Entries will exist in this table when tmnxPortEncapType is set
           to frEncap.";
        smiv2:oid "1.3.6.1.4.1.6527.3.1.2.2.9.2.1";
        leaf tmnxChassisIndex {
          type leafref {
            path "/timetra-chassis:TIMETRA-CHASSIS-MIB/timetra-chassis:tmnxChassisTable/timetra-chassis:tmnxChassisEntry/timetra-chassis:tmnxChassisIndex";
          }
          config true;
        }
        leaf tmnxPortPortID {
          type leafref {
            path "/timetra-port:TIMETRA-PORT-MIB/timetra-port:tmnxPortTable/timetra-port:tmnxPortEntry/timetra-port:tmnxPortPortID";
          }
          config true;
        }
        leaf tmnxFrIntfFrf12Mode {
          type timetra-tc:TmnxEnabledDisabled;
          description
            "The value of tmnxFrIntfFrf12Mode enables or disables the
             use of FRF12 headers. This cannot be set to 'enabled'
             for entries with a tmnxPortBundleNumber set or bundles with
             a tmnxBundleType of mlfr.";
          smiv2:defval "disabled";
          smiv2:max-access "read-write";
          smiv2:oid "1.3.6.1.4.1.6527.3.1.2.2.9.2.1.1";
          config true;
        }
        leaf tmnxFrIntfLinkId {
          type snmp-framework:SnmpAdminString {
            length "0..49";
          }
          description
            "The value of tmnxFrIntfLinkId is a Link Identifier
             that is used when this entry is added to a MLFR bundle.";
          smiv2:defval "";
          smiv2:max-access "read-write";
          smiv2:oid "1.3.6.1.4.1.6527.3.1.2.2.9.2.1.2";
          config true;
        }
        leaf tmnxFrIntfLastChanged {
          type yang:timestamp;
          description
            "The value of tmnxFrIntfLastChanged indicates the value
             of sysUpTime at the time of the most recent management change to
             this row.";
          smiv2:max-access "read-only";
          smiv2:oid "1.3.6.1.4.1.6527.3.1.2.2.9.2.1.3";
          config false;
        }
        config true;
      }
      config true;
    }
    container tmnxFrf12IntfTable {
      description
        "The tmnxFrf12IntfTable contains entries for a port/channel
         that has frf12 mode 'enabled'.";
      smiv2:oid "1.3.6.1.4.1.6527.3.1.2.2.9.3";
      list tmnxFrf12IntfEntry {
        key "tmnxChassisIndex tmnxPortPortID";
        description
          "Each row represents a particular frame-relay interface that has
           enabled frf12 on a port/channel.
           
           Each row in this table is added/removed when frf12 is enabled
           on a port/channel.";
        smiv2:oid "1.3.6.1.4.1.6527.3.1.2.2.9.3.1";
        leaf tmnxChassisIndex {
          type leafref {
            path "/timetra-chassis:TIMETRA-CHASSIS-MIB/timetra-chassis:tmnxChassisTable/timetra-chassis:tmnxChassisEntry/timetra-chassis:tmnxChassisIndex";
          }
          config true;
        }
        leaf tmnxPortPortID {
          type leafref {
            path "/timetra-port:TIMETRA-PORT-MIB/timetra-port:tmnxPortTable/timetra-port:tmnxPortEntry/timetra-port:tmnxPortPortID";
          }
          config true;
        }
        leaf tmnxFrf12IntfFragmentThreshold {
          type uint32 {
            range "128..512";
          }
          description
            "The value of tmnxFrf12IntfFragmentThreshold specifies the
             maximum length of a fragment to be transmitted.
             A value of 0 specifies no fragmentation.";
          smiv2:defval "128";
          smiv2:max-access "read-write";
          smiv2:oid "1.3.6.1.4.1.6527.3.1.2.2.9.3.1.1";
          config true;
        }
        leaf tmnxFrf12IntfEgrQoSProfId {
          type timetra-tc:TMcFrQoSProfileId;
          description
            "The value of tmnxFrf12IntfEgrQoSProfId specifies the egress
             QoS profile to be used for the outgoing traffic over this frf12
             frame-relay interface.
             
             The value of tmnxFrf12IntfEgrQoSProfId of 0 indicates
             a default QoS profile is used as applicable to given hardware.";
          smiv2:defval "0";
          smiv2:max-access "read-write";
          smiv2:oid "1.3.6.1.4.1.6527.3.1.2.2.9.3.1.2";
          config true;
        }
        leaf tmnxFrf12IntfLastChanged {
          type yang:timestamp;
          description
            "The value of tmnxFrf12IntfLastChanged indicates the value
             of sysUpTime at the time of the most recent management change to
             this row.";
          smiv2:max-access "read-only";
          smiv2:oid "1.3.6.1.4.1.6527.3.1.2.2.9.3.1.3";
          config false;
        }
        config true;
      }
      config true;
    }
    container tmnxQosPoolAppTable {
      description
        "This table maintains associations of the buffer pools with the
         individual objects.";
      smiv2:oid "1.3.6.1.4.1.6527.3.1.2.2.10.2";
      list tmnxQosPoolAppEntry {
        key "tmnxChassisIndex tmnxObjectType tmnxObjectId tmnxObjectAppType tmnxObjectAppPool";
        description
          "This entry maintains the specifics about the association of a
           buffer pool and an object.";
        smiv2:oid "1.3.6.1.4.1.6527.3.1.2.2.10.2.1";
        leaf tmnxChassisIndex {
          type leafref {
            path "/timetra-chassis:TIMETRA-CHASSIS-MIB/timetra-chassis:tmnxChassisTable/timetra-chassis:tmnxChassisEntry/timetra-chassis:tmnxChassisIndex";
          }
          config true;
        }
        leaf tmnxObjectType {
          type enumeration {
            enum "mda" {
              value 1;
            }
            enum "port" {
              value 2;
            }
            enum "unused" {
              value 3;
            }
            enum "bundle" {
              value 4;
            }
          }
          description
            "The object tmnxObjectType defines the type of object to which the
             pool is being setup for.";
          smiv2:max-access "not-accessible";
          smiv2:oid "1.3.6.1.4.1.6527.3.1.2.2.10.2.1.1";
          config true;
        }
        leaf tmnxObjectId {
          type timetra-tc:TmnxPortID;
          description
            "tmnxObjectId is used to identify the specific object. If
             tmnxObjectType is 'mda', then the tmnxObjectId is encoded as a
             physical port with the port being '0'. For all other types the
             encoding is done as per the description of TmnxPortID.";
          smiv2:max-access "not-accessible";
          smiv2:oid "1.3.6.1.4.1.6527.3.1.2.2.10.2.1.2";
          config true;
        }
        leaf tmnxObjectAppType {
          type enumeration {
            enum "accessIngress" {
              value 1;
            }
            enum "accessEgress" {
              value 2;
            }
            enum "networkIngress" {
              value 3;
            }
            enum "networkEgress" {
              value 4;
            }
          }
          description
            "The object tmnxObjectAppType specifies the nature of usage the pool
             would be used for. The pools could be used for access or network
             traffic at either ingress or egress.";
          smiv2:max-access "not-accessible";
          smiv2:oid "1.3.6.1.4.1.6527.3.1.2.2.10.2.1.3";
          config true;
        }
        leaf tmnxObjectAppPool {
          type timetra-tc:TNamedItem;
          description
            "tmnxObjectAppPool specifies the name of the pool to be used/created.";
          smiv2:max-access "not-accessible";
          smiv2:oid "1.3.6.1.4.1.6527.3.1.2.2.10.2.1.4";
          config true;
        }
        leaf tmnxObjectAppPoolRowStatus {
          type snmpv2-tc:RowStatus;
          description
            "The object tmnxObjectAppPoolRowStatus is used to create or remove a
             pool application to the object.";
          smiv2:max-access "read-write";
          smiv2:oid "1.3.6.1.4.1.6527.3.1.2.2.10.2.1.5";
          config false;
        }
        leaf tmnxObjectAppResvCbs {
          type int32 {
            range "-1..100";
          }
          description
            "The percentage of pool size reserved for CBS. The value '-1'
             implies that the reserved CBS should be computed as the sum of
             the CBS requested by the entities using this pool if the application
             point is 'network'. For 'access' application points the value '-1'
             means a default of 30%.";
          smiv2:defval "-1";
          smiv2:max-access "read-write";
          smiv2:oid "1.3.6.1.4.1.6527.3.1.2.2.10.2.1.6";
          config true;
        }
        leaf tmnxObjectAppSlopePolicy {
          type timetra-tc:TNamedItem;
          description
            "tmnxObjectAppSlopePolicy specifies the slope policy being used for
             this pool. The Slope policies define the nature of the RED Slopes for
             the high and the low priority traffic.";
          smiv2:defval "default";
          smiv2:max-access "read-write";
          smiv2:oid "1.3.6.1.4.1.6527.3.1.2.2.10.2.1.7";
          config true;
        }
        leaf tmnxObjectAppPoolSize {
          type int32 {
            range "-1..100";
          }
          description
            "Size in percentage of buffer space. The value '-1' implies that
             the pool size should be computed as per fair weighing between
             all other pools.";
          smiv2:defval "-1";
          smiv2:max-access "read-write";
          smiv2:oid "1.3.6.1.4.1.6527.3.1.2.2.10.2.1.8";
          config true;
        }
        leaf tmnxObjectAppResvCbsAmbrAlrmStep {
          type int32 {
            range "0..100";
          }
          units "percent";
          description
            "The value of tmnxObjectAppResvCbsAmbrAlrmStep specifies the 
             percentage step-size for the reserved CBS size of the pool. 
             When tmnxObjectAppResvCbsAmbrAlrmStep is set to default value, the 
             adaptive CBS sizing is disabled. To enable adaptive CBS sizing, 
             tmnxObjectAppResvCbsAmbrAlrmStep MUST be set to non-default value along
             with tmnxObjectAppResvCbsAmbrAlrmMax. When reserved CBS is set to 
             default value, adaptive CBS sizing cannot be enabled. The reserved CBS
             (Committed Burst Size) defines the amount of buffer space within the 
             pool that is not considered shared.";
          smiv2:defval "0";
          smiv2:max-access "read-write";
          smiv2:oid "1.3.6.1.4.1.6527.3.1.2.2.10.2.1.9";
          config true;
        }
        leaf tmnxObjectAppResvCbsAmbrAlrmMax {
          type int32 {
            range "0..100";
          }
          units "percent";
          description
            "The value of tmnxObjectAppResvCbsAmbrAlrmMax specifies the 
             maximum percentage for the reserved CBS size of the pool. 
             When tmnxObjectAppResvCbsAmbrAlrmMax is set to default value, the 
             adaptive CBS sizing is disabled. To enable adaptive CBS sizing,
             tmnxObjectAppResvCbsAmbrAlrmMax MUST be set to non-default value along
             with tmnxObjectAppResvCbsAmbrAlrmStep. When reserved CBS is set to 
             default value, adaptive CBS sizing cannot be enabled. The reserved CBS
             (Committed Burst Size) defines the amount of buffer space within the
             pool that is not considered shared.  Max reserved CBS must not be more 
             than the reserved CBS.";
          smiv2:defval "0";
          smiv2:max-access "read-write";
          smiv2:oid "1.3.6.1.4.1.6527.3.1.2.2.10.2.1.10";
          config true;
        }
        leaf tmnxObjectAppAmbrAlrmThresh {
          type int32 {
            range "0..1000";
          }
          units "percent";
          description
            "The value of tmnxObjectAppAmbrAlrmThresh specifies the 
             threshold for the amber alarm on the over-subscription allowed.";
          smiv2:defval "0";
          smiv2:max-access "read-write";
          smiv2:oid "1.3.6.1.4.1.6527.3.1.2.2.10.2.1.11";
          config true;
        }
        leaf tmnxObjectAppRedAlrmThresh {
          type int32 {
            range "0..1000";
          }
          units "percent";
          description
            "The value of tmnxObjectAppRedAlrmThresh specifies the 
             threshold for the red alarm on the over-subscription allowed.";
          smiv2:defval "0";
          smiv2:max-access "read-write";
          smiv2:oid "1.3.6.1.4.1.6527.3.1.2.2.10.2.1.12";
          config true;
        }
        config true;
      }
      config true;
    }
    container tmnxATMIntfTable {
      description
        "The tmnxATMIntfTable has an entry for each port/channel in the
         system that is configured for ATM. It contains ATM cell layer
         configuration parameters.";
      smiv2:oid "1.3.6.1.4.1.6527.3.1.2.2.11.1";
      list tmnxATMIntfEntry {
        key "tmnxChassisIndex tmnxPortPortID";
        description
          "The Parameters for a particular ATM Cell
           Management Interface. Entries cannot be created or
           deleted via SNMP SET operations.
           Entries will exist in this table when ATM encapsulation
           is configured on the port/channel.";
        smiv2:oid "1.3.6.1.4.1.6527.3.1.2.2.11.1.1";
        leaf tmnxChassisIndex {
          type leafref {
            path "/timetra-chassis:TIMETRA-CHASSIS-MIB/timetra-chassis:tmnxChassisTable/timetra-chassis:tmnxChassisEntry/timetra-chassis:tmnxChassisIndex";
          }
          config true;
        }
        leaf tmnxPortPortID {
          type leafref {
            path "/timetra-port:TIMETRA-PORT-MIB/timetra-port:tmnxPortTable/timetra-port:tmnxPortEntry/timetra-port:tmnxPortPortID";
          }
          config true;
        }
        leaf tmnxATMIntfCellFormat {
          type enumeration {
            enum "uni" {
              value 1;
            }
            enum "nni" {
              value 2;
            }
          }
          description
            "tmnxATMIntfCellFormat is used to set the cell format
             (UNI or NNI) that is to be used on the ATM interface.";
          smiv2:defval "uni";
          smiv2:max-access "read-write";
          smiv2:oid "1.3.6.1.4.1.6527.3.1.2.2.11.1.1.1";
          config true;
        }
        leaf tmnxATMIntfMinVpValue {
          type int32 {
            range "0..4095";
          }
          description
            "tmnxATMIntfMinVpValue is used to set the minimum
             allowable VPI value that can be used on the
             ATM interface for a VPC.";
          smiv2:defval "0";
          smiv2:max-access "read-write";
          smiv2:oid "1.3.6.1.4.1.6527.3.1.2.2.11.1.1.2";
          config true;
        }
        leaf tmnxATMIntfMapping {
          type enumeration {
            enum "direct" {
              value 1;
            }
            enum "plcp" {
              value 2;
            }
          }
          description
            "The value of tmnxATMIntfMapping specifies the cell
             mapping that is to be used on this ATM interface.  When
             tmnxPortChanType does not have a value of 'pdhDs3 (14)',
             'inconsistentValue' error will be returned to SNMP SET
             requests.  When tmnxPortChanType has a value of 'pdhDs3 (14)',
             tmnxATMIntfMapping can be set to 'plcp (2)'.";
          smiv2:defval "direct";
          smiv2:max-access "read-write";
          smiv2:oid "1.3.6.1.4.1.6527.3.1.2.2.11.1.1.3";
          config true;
        }
        leaf tmnxATMIntfCustomBufferMode {
          type boolean;
          description
            "The value of tmnxATMIntfCustomBufferMode specifies whether
             port is in a mode that allows custom configuration of port buffer
             pool and VC thresholds.";
          smiv2:defval "false";
          smiv2:max-access "read-write";
          smiv2:oid "1.3.6.1.4.1.6527.3.1.2.2.11.1.1.4";
          config true;
        }
        leaf tmnxATMIntfBufferPool {
          type int32 {
            range "1..100";
          }
          description
            "The value of tmnxATMIntfBufferPool specifies the percentage
             of the buffers configured on this interface over the
             maximum allowed on this interface.
             
             The value can only be changed if tmnxATMIntfCustomBufferMode
             is set to 'true'.  Changing tmnxATMIntfCustomBufferMode to
             'false' will reset tmnxATMIntfBufferPool back to the default
             value.";
          smiv2:defval "100";
          smiv2:max-access "read-write";
          smiv2:oid "1.3.6.1.4.1.6527.3.1.2.2.11.1.1.5";
          config true;
        }
        leaf tmnxATMIntfVcThreshold {
          type int32 {
            range "190..117000";
          }
          description
            "The value of tmnxATMIntfVcThreshold specifies the VC buffer
             threshold for all VCs configured on this port.
             
             The value can only be changed if tmnxATMIntfCustomBufferMode
             is set to 'true'.  Changing tmnxATMIntfCustomBufferMode to
             'false' will reset tmnxATMIntfVcThreshold back to the default
             value.";
          smiv2:defval "190";
          smiv2:max-access "read-write";
          smiv2:oid "1.3.6.1.4.1.6527.3.1.2.2.11.1.1.6";
          config true;
        }
        config true;
      }
      config true;
    }
    container tmnxPortATMVpShaperTable {
      description
        "The tmnxPortATMVpShaperTable has an entry for each ATM port-level VP
         shaper configured on this system.";
      smiv2:oid "1.3.6.1.4.1.6527.3.1.2.2.11.3";
      list tmnxPortATMVpShaperEntry {
        key "tmnxChassisIndex tmnxPortPortID tmnxPortATMVpShaperVpi";
        description
          "Each row represents a particular ATM port-level VP shaper.
           Entries are created and deleted by the user.";
        smiv2:oid "1.3.6.1.4.1.6527.3.1.2.2.11.3.1";
        leaf tmnxChassisIndex {
          type leafref {
            path "/timetra-chassis:TIMETRA-CHASSIS-MIB/timetra-chassis:tmnxChassisTable/timetra-chassis:tmnxChassisEntry/timetra-chassis:tmnxChassisIndex";
          }
          config true;
        }
        leaf tmnxPortPortID {
          type leafref {
            path "/timetra-port:TIMETRA-PORT-MIB/timetra-port:tmnxPortTable/timetra-port:tmnxPortEntry/timetra-port:tmnxPortPortID";
          }
          config true;
        }
        leaf tmnxPortATMVpShaperVpi {
          type atm-tc:AtmVpIdentifier;
          description
            "The value of tmnxPortATMVpShaperVpi specifies the ATM Virtual Path 
             identifier of this row.";
          smiv2:max-access "not-accessible";
          smiv2:oid "1.3.6.1.4.1.6527.3.1.2.2.11.3.1.1";
          config true;
        }
        leaf tmnxPortATMVpShaperRowStatus {
          type snmpv2-tc:RowStatus;
          description
            "The value of sapAtmVcRangeRowStatus specifies the row status of this
             row.";
          smiv2:max-access "read-write";
          smiv2:oid "1.3.6.1.4.1.6527.3.1.2.2.11.3.1.2";
          config false;
        }
        leaf tmnxPortATMVpShaperLastMgmtCh {
          type yang:timestamp;
          description
            "The value of tmnxPortATMVpShaperLastMgmtCh indicates the sysUpTime
             at the time of the most recent management-initiated change to this
             table row.";
          smiv2:max-access "read-only";
          smiv2:oid "1.3.6.1.4.1.6527.3.1.2.2.11.3.1.3";
          config false;
        }
        leaf tmnxPortATMVpShaperEgrAtd {
          type atm-tc:AtmTrafficDescrParamIndex {
            range "1..1000";
          }
          description
            "The value of tmnxPortATMVpShaperEgrAtd specifies 
             the index of the ATM traffic descriptor in the ATM traffic 
             data encapsulation used for the egress direction over
             the AAL5 SSCS layer.
             
             The definition references RFC 2684 Multiprotocol Encapsulation over
             ATM AAL5 and to the ATM Forum LAN Emulation specification.
             
             The value of tmnxPortATMVpShaperEgrAtd must be specified when the
             conceptual row is created, and it cannot be changed afterwards.";
          smiv2:max-access "read-write";
          smiv2:oid "1.3.6.1.4.1.6527.3.1.2.2.11.3.1.4";
          config true;
        }
        config true;
      }
      config true;
    }
    container tmnxPortNetIngressStatsTable {
      description
        "Defines the Alcatel-Lucent SROS series network port ingress
         statistics table for providing, via SNMP, the capability of
         retrieving the traffic statistics for the physical queues
         being used for the ports to forward the network ingress
         traffic.";
      smiv2:oid "1.3.6.1.4.1.6527.3.1.2.2.12.1";
      list tmnxPortNetIngressStatsEntry {
        key "tmnxChassisIndex tmnxPortPortID tmnxPortNetIngressQueueIndex";
        description
          "Defines an entry in tmnxPortNetIngressStatsTable. Entries are
           created and deleted by the system depending on the queue policy
           being used at the specific port.";
        smiv2:oid "1.3.6.1.4.1.6527.3.1.2.2.12.1.1";
        leaf tmnxChassisIndex {
          type leafref {
            path "/timetra-chassis:TIMETRA-CHASSIS-MIB/timetra-chassis:tmnxChassisTable/timetra-chassis:tmnxChassisEntry/timetra-chassis:tmnxChassisIndex";
          }
        }
        leaf tmnxPortPortID {
          type leafref {
            path "/timetra-port:TIMETRA-PORT-MIB/timetra-port:tmnxPortTable/timetra-port:tmnxPortEntry/timetra-port:tmnxPortPortID";
          }
        }
        leaf tmnxPortNetIngressQueueIndex {
          type timetra-tc:TQueueId {
            range "1..16";
          }
          description
            "tmnxPortNetIngressQueueIndex serves as the tertiary index. When used
             in conjunction with tmnxChassisIndex and tmnxPortPortID, it uniquely
             identifies a network ingress queue for the specified port in the
             managed system.";
          smiv2:max-access "not-accessible";
          smiv2:oid "1.3.6.1.4.1.6527.3.1.2.2.12.1.1.1";
        }
        leaf tmnxPortNetIngressFwdInProfPkts {
          type yang:counter64;
          description
            "tmnxPortNetIngressFwdInProfPkts indicates the number of conforming
             network ingress packets forwarded on this port using this queue.";
          smiv2:max-access "read-only";
          smiv2:oid "1.3.6.1.4.1.6527.3.1.2.2.12.1.1.2";
        }
        leaf tmnxPortNetIngressFwdOutProfPkts {
          type yang:counter64;
          description
            "tmnxPortNetIngressFwdOutProfPkts indicates the number of exceeding
             network ingress packets forwarded on this port using this queue.";
          smiv2:max-access "read-only";
          smiv2:oid "1.3.6.1.4.1.6527.3.1.2.2.12.1.1.3";
        }
        leaf tmnxPortNetIngressFwdInProfOcts {
          type yang:counter64;
          description
            "tmnxPortNetIngressFwdInProfOcts indicates the number of conforming
             network ingress octets forwarded on this port using this queue.";
          smiv2:max-access "read-only";
          smiv2:oid "1.3.6.1.4.1.6527.3.1.2.2.12.1.1.4";
        }
        leaf tmnxPortNetIngressFwdOutProfOcts {
          type yang:counter64;
          description
            "tmnxPortNetIngressFwdOutProfOcts indicates the number of exceeding
             network ingress octets forwarded on this port using this queue.";
          smiv2:max-access "read-only";
          smiv2:oid "1.3.6.1.4.1.6527.3.1.2.2.12.1.1.5";
        }
        leaf tmnxPortNetIngressDroInProfPkts {
          type yang:counter64;
          description
            "tmnxPortNetIngressDroInProfPkts indicates the number of conforming
             network ingress packets dropped on this port using this queue.";
          smiv2:max-access "read-only";
          smiv2:oid "1.3.6.1.4.1.6527.3.1.2.2.12.1.1.6";
        }
        leaf tmnxPortNetIngressDroOutProfPkts {
          type yang:counter64;
          description
            "tmnxPortNetIngressDroOutProfPkts indicates the number of exceeding
             network ingress packets dropped on this port using this queue.";
          smiv2:max-access "read-only";
          smiv2:oid "1.3.6.1.4.1.6527.3.1.2.2.12.1.1.7";
        }
        leaf tmnxPortNetIngressDroInProfOcts {
          type yang:counter64;
          description
            "tmnxPortNetIngressDroInProfOcts indicates the number of conforming
             network ingress octets dropped on this port using this queue.";
          smiv2:max-access "read-only";
          smiv2:oid "1.3.6.1.4.1.6527.3.1.2.2.12.1.1.8";
        }
        leaf tmnxPortNetIngressDroOutProfOcts {
          type yang:counter64;
          description
            "tmnxPortNetIngressDroOutProfOcts indicates the number of exceeding
             network ingress octets dropped on this port using this queue.";
          smiv2:max-access "read-only";
          smiv2:oid "1.3.6.1.4.1.6527.3.1.2.2.12.1.1.9";
        }
      }
      config false;
    }
    container tmnxPortNetEgressStatsTable {
      description
        "Defines the Alcatel-Lucent SROS series network port egress
         statistics table for providing, via SNMP, the capability of
         retrieving the traffic statistics for the physical queues
         being used for the ports to forward the network egress
         traffic.";
      smiv2:oid "1.3.6.1.4.1.6527.3.1.2.2.12.2";
      list tmnxPortNetEgressStatsEntry {
        key "tmnxChassisIndex tmnxPortPortID tmnxPortNetEgressQueueIndex";
        description
          "Defines an entry in tmnxPortNetEgressStatsTable. Entries are
           created and deleted by the system depending on the queue policy
           being used at the specific port.";
        smiv2:oid "1.3.6.1.4.1.6527.3.1.2.2.12.2.1";
        leaf tmnxChassisIndex {
          type leafref {
            path "/timetra-chassis:TIMETRA-CHASSIS-MIB/timetra-chassis:tmnxChassisTable/timetra-chassis:tmnxChassisEntry/timetra-chassis:tmnxChassisIndex";
          }
        }
        leaf tmnxPortPortID {
          type leafref {
            path "/timetra-port:TIMETRA-PORT-MIB/timetra-port:tmnxPortTable/timetra-port:tmnxPortEntry/timetra-port:tmnxPortPortID";
          }
        }
        leaf tmnxPortNetEgressQueueIndex {
          type timetra-tc:TQueueId {
            range "1..8";
          }
          description
            "tmnxPortNetEgressQueueIndex serves as the tertiary index. When used
             in conjunction with tmnxChassisIndex and tmnxPortPortID, it uniquely
             identifies a network egress queue for the specified port in the
             managed system.";
          smiv2:max-access "not-accessible";
          smiv2:oid "1.3.6.1.4.1.6527.3.1.2.2.12.2.1.1";
        }
        leaf tmnxPortNetEgressFwdInProfPkts {
          type yang:counter64;
          description
            "tmnxPortNetEgressFwdInProfPkts indicates the number of conforming
             network egress packets forwarded on this port using this queue.";
          smiv2:max-access "read-only";
          smiv2:oid "1.3.6.1.4.1.6527.3.1.2.2.12.2.1.2";
        }
        leaf tmnxPortNetEgressFwdOutProfPkts {
          type yang:counter64;
          description
            "tmnxPortNetEgressFwdOutProfPkts indicates the number of exceeding
             network egress packets forwarded on this port using this queue.";
          smiv2:max-access "read-only";
          smiv2:oid "1.3.6.1.4.1.6527.3.1.2.2.12.2.1.3";
        }
        leaf tmnxPortNetEgressFwdInProfOcts {
          type yang:counter64;
          description
            "tmnxPortNetEgressFwdInProfOcts indicates the number of conforming
             network egress octets forwarded on this port using this queue.";
          smiv2:max-access "read-only";
          smiv2:oid "1.3.6.1.4.1.6527.3.1.2.2.12.2.1.4";
        }
        leaf tmnxPortNetEgressFwdOutProfOcts {
          type yang:counter64;
          description
            "tmnxPortNetEgressFwdOutProfOcts indicates the number of exceeding
             network egress octets forwarded on this port using this queue.";
          smiv2:max-access "read-only";
          smiv2:oid "1.3.6.1.4.1.6527.3.1.2.2.12.2.1.5";
        }
        leaf tmnxPortNetEgressDroInProfPkts {
          type yang:counter64;
          description
            "tmnxPortNetEgressDroInProfPkts indicates the number of conforming
             network egress packets dropped on this port using this queue.";
          smiv2:max-access "read-only";
          smiv2:oid "1.3.6.1.4.1.6527.3.1.2.2.12.2.1.6";
        }
        leaf tmnxPortNetEgressDroOutProfPkts {
          type yang:counter64;
          description
            "tmnxPortNetEgressDroOutProfPkts indicates the number of exceeding
             network egress packets dropped on this port using this queue.";
          smiv2:max-access "read-only";
          smiv2:oid "1.3.6.1.4.1.6527.3.1.2.2.12.2.1.7";
        }
        leaf tmnxPortNetEgressDroInProfOcts {
          type yang:counter64;
          description
            "tmnxPortNetEgressDroInProfOcts indicates the number of conforming
             network egress octets dropped on this port using this queue.";
          smiv2:max-access "read-only";
          smiv2:oid "1.3.6.1.4.1.6527.3.1.2.2.12.2.1.8";
        }
        leaf tmnxPortNetEgressDroOutProfOcts {
          type yang:counter64;
          description
            "tmnxPortNetEgressDroOutProfOcts indicates the number of exceeding
             network egress octets dropped on this port using this queue.";
          smiv2:max-access "read-only";
          smiv2:oid "1.3.6.1.4.1.6527.3.1.2.2.12.2.1.9";
        }
      }
      config false;
    }
    container tmnxMcMlpppStatsTable {
      description
        "Defines the Alcatel-Lucent SROS series Multiclass MLPPP
         statistics table for providing the capability of
         retrieving the traffic statistics for the physical queues
         being used for a class of a multiclass MLPPP bundle to
         forward the traffic.";
      smiv2:oid "1.3.6.1.4.1.6527.3.1.2.2.12.4";
      list tmnxMcMlpppStatsEntry {
        key "tmnxChassisIndex tmnxBundleBundleID tmnxMcMlpppClassIndex";
        description
          "Defines an entry in tmnxMcMlpppStatsTable. Entries are
           created and deleted by the system depending on the number of
           classes being used by a given MLPPP bundle.";
        smiv2:oid "1.3.6.1.4.1.6527.3.1.2.2.12.4.1";
        leaf tmnxChassisIndex {
          type leafref {
            path "/timetra-chassis:TIMETRA-CHASSIS-MIB/timetra-chassis:tmnxChassisTable/timetra-chassis:tmnxChassisEntry/timetra-chassis:tmnxChassisIndex";
          }
        }
        leaf tmnxBundleBundleID {
          type leafref {
            path "/timetra-port:TIMETRA-PORT-MIB/timetra-port:tmnxBundleTable/timetra-port:tmnxBundleEntry/timetra-port:tmnxBundleBundleID";
          }
        }
        leaf tmnxMcMlpppClassIndex {
          type timetra-port:TmnxMcMlpppClassIndex;
          description
            "tmnxMcMlpppClassIndex serves as the tertiary index. When used
             in conjunction with tmnxChassisIndex and tmnxBundleBundleID, it
             uniquely identifies a class of a multiclass MLPPP bundle in the
             managed system.";
          smiv2:max-access "not-accessible";
          smiv2:oid "1.3.6.1.4.1.6527.3.1.2.2.12.4.1.1";
        }
        leaf tmnxMcMlpppStatsIngressOct {
          type yang:counter32;
          description
            "The value of tmnxMcMlpppStatsIngressOct indicates the total
             number of octets in all packets received on the bundle
             for the given class on ingress before reassembly.";
          smiv2:max-access "read-only";
          smiv2:oid "1.3.6.1.4.1.6527.3.1.2.2.12.4.1.2";
        }
        leaf tmnxMcMlpppStatsIngressPkt {
          type yang:counter32;
          description
            "The value of tmnxMcMlpppStatsIngressPkt indicates the total
             number of packets forwarded on the bundle for the given
             class on ingress towards higher layer protocols.";
          smiv2:max-access "read-only";
          smiv2:oid "1.3.6.1.4.1.6527.3.1.2.2.12.4.1.3";
        }
        leaf tmnxMcMlpppStatsIngressErrPkt {
          type yang:counter32;
          description
            "The value of tmnxMcMlpppStatsIngressErrPkt indicates the total
             number of packets discarded due to reassembly errors
             on the bundle for the given class on ingress.";
          smiv2:max-access "read-only";
          smiv2:oid "1.3.6.1.4.1.6527.3.1.2.2.12.4.1.4";
        }
        leaf tmnxMcMlpppStatsEgressOct {
          type yang:counter32;
          description
            "The value of tmnxMcMlpppStatsEgressOct indicates the total
             number of octets in all packets received on the bundle
             for the given class on egress before segmentation.";
          smiv2:max-access "read-only";
          smiv2:oid "1.3.6.1.4.1.6527.3.1.2.2.12.4.1.5";
        }
        leaf tmnxMcMlpppStatsEgressPkt {
          type yang:counter32;
          description
            "The value of tmnxMcMlpppStatsEgressPkt indicates the total
             number of packets forwarded on the bundle for the given
             class on egress towards the line.";
          smiv2:max-access "read-only";
          smiv2:oid "1.3.6.1.4.1.6527.3.1.2.2.12.4.1.6";
        }
        leaf tmnxMcMlpppStatsEgressErrPkt {
          type yang:counter32;
          description
            "The value of tmnxMcMlpppStatsEgressErrPkt indicates the total
             number of packets discarded due to segmentation errors
             on the bundle for the given class on egress.";
          smiv2:max-access "read-only";
          smiv2:oid "1.3.6.1.4.1.6527.3.1.2.2.12.4.1.7";
        }
      }
      config false;
    }
    container tmnxPortNetEgrQStatTable {
      description
        "Defines the Alcatel-Lucent SROS series network port egress
         statistics table for providing, via SNMP, the capability of
         retrieving the traffic statistics for the queue-group queues
         being used for the ports to forward the network egress
         traffic.";
      smiv2:oid "1.3.6.1.4.1.6527.3.1.2.2.12.5";
      list tmnxPortNetEgrQStatEntry {
        key "tmnxChassisIndex tmnxPortPortID tPortNetEgrQGrpName tPortNetEgrQGrpInstanceId tmnxPortEgrQosQStatQueueId";
        description
          "Defines an entry in tmnxPortNetEgrQStatTable. Entries are
           created and deleted by the system depending on the queue policy
           being used at the specific port.
           
           In release 10.0 tPortNetEgrQGrpInstanceId is added as another index
           before tmnxPortEgrQosQStatQueueId for this tmnxPortNetEgrQStatTable.";
        smiv2:oid "1.3.6.1.4.1.6527.3.1.2.2.12.5.1";
        leaf tmnxChassisIndex {
          type leafref {
            path "/timetra-chassis:TIMETRA-CHASSIS-MIB/timetra-chassis:tmnxChassisTable/timetra-chassis:tmnxChassisEntry/timetra-chassis:tmnxChassisIndex";
          }
        }
        leaf tmnxPortPortID {
          type leafref {
            path "/timetra-port:TIMETRA-PORT-MIB/timetra-port:tmnxPortTable/timetra-port:tmnxPortEntry/timetra-port:tmnxPortPortID";
          }
        }
        leaf tPortNetEgrQGrpName {
          type leafref {
            path "/timetra-port:TIMETRA-PORT-MIB/timetra-port:tPortNetEgrQGrpTable/timetra-port:tPortNetEgrQGrpEntry/timetra-port:tPortNetEgrQGrpName";
          }
        }
        leaf tPortNetEgrQGrpInstanceId {
          type leafref {
            path "/timetra-port:TIMETRA-PORT-MIB/timetra-port:tPortNetEgrQGrpTable/timetra-port:tPortNetEgrQGrpEntry/timetra-port:tPortNetEgrQGrpInstanceId";
          }
        }
        leaf tmnxPortEgrQosQStatQueueId {
          type leafref {
            path "/timetra-port:TIMETRA-PORT-MIB/timetra-port:tmnxPortEgrQosQStatTable/timetra-port:tmnxPortEgrQosQStatEntry/timetra-port:tmnxPortEgrQosQStatQueueId";
          }
        }
        leaf tmnxPortNetEgrQFwdInProfPkts {
          type yang:counter64;
          description
            "The value of tmnxPortNetEgrQFwdInProfPkts indicates the number of
             conforming network egress packets forwarded on this port using this
             queue-group queue.";
          smiv2:max-access "read-only";
          smiv2:oid "1.3.6.1.4.1.6527.3.1.2.2.12.5.1.1";
        }
        leaf tmnxPortNetEgrQFwdOutProfPkts {
          type yang:counter64;
          description
            "The value of tmnxPortNetEgrQFwdOutProfPkts indicates the number of
             exceeding network egress packets forwarded on this port using this
             queue-group queue.";
          smiv2:max-access "read-only";
          smiv2:oid "1.3.6.1.4.1.6527.3.1.2.2.12.5.1.2";
        }
        leaf tmnxPortNetEgrQFwdInProfOcts {
          type yang:counter64;
          description
            "The value of tmnxPortNetEgrQFwdInProfOcts indicates the number of
             conforming network egress octets forwarded on this port using this
             queue-group queue.";
          smiv2:max-access "read-only";
          smiv2:oid "1.3.6.1.4.1.6527.3.1.2.2.12.5.1.3";
        }
        leaf tmnxPortNetEgrQFwdOutProfOcts {
          type yang:counter64;
          description
            "The value of tmnxPortNetEgrQFwdOutProfOcts indicates the number of
             exceeding network egress octets forwarded on this port using this
             queue-group queue.";
          smiv2:max-access "read-only";
          smiv2:oid "1.3.6.1.4.1.6527.3.1.2.2.12.5.1.4";
        }
        leaf tmnxPortNetEgrQDroInProfPkts {
          type yang:counter64;
          description
            "The value of tmnxPortNetEgrQDroInProfPkts indicates the number of
             conforming network egress packets dropped on this port using this
             queue-group queue.";
          smiv2:max-access "read-only";
          smiv2:oid "1.3.6.1.4.1.6527.3.1.2.2.12.5.1.5";
        }
        leaf tmnxPortNetEgrQDroOutProfPkts {
          type yang:counter64;
          description
            "The value of tmnxPortNetEgrQDroOutProfPkts indicates the number of
             exceeding network egress packets dropped on this port using this
             queue-group queue.";
          smiv2:max-access "read-only";
          smiv2:oid "1.3.6.1.4.1.6527.3.1.2.2.12.5.1.6";
        }
        leaf tmnxPortNetEgrQDroInProfOcts {
          type yang:counter64;
          description
            "The value of tmnxPortNetEgrQDroInProfOcts indicates the number of
             conforming network egress octets dropped on this port using this
             queue-group queue.";
          smiv2:max-access "read-only";
          smiv2:oid "1.3.6.1.4.1.6527.3.1.2.2.12.5.1.7";
        }
        leaf tmnxPortNetEgrQDroOutProfOcts {
          type yang:counter64;
          description
            "The value of tmnxPortNetEgrQDroOutProfOcts indicates the number of
             exceeding network egress octets dropped on this port using this
             queue-group queue.";
          smiv2:max-access "read-only";
          smiv2:oid "1.3.6.1.4.1.6527.3.1.2.2.12.5.1.8";
        }
      }
      config false;
    }
    container tmnxPortCemStatsTable {
      description
        "A table that contains CEM Port statistics.";
      smiv2:oid "1.3.6.1.4.1.6527.3.1.2.2.12.6";
      list tmnxPortCemStatsEntry {
        key "tmnxChassisIndex tmnxPortPortID";
        description
          "Statistics for a specific CEM Port.";
        smiv2:oid "1.3.6.1.4.1.6527.3.1.2.2.12.6.1";
        leaf tmnxChassisIndex {
          type leafref {
            path "/timetra-chassis:TIMETRA-CHASSIS-MIB/timetra-chassis:tmnxChassisTable/timetra-chassis:tmnxChassisEntry/timetra-chassis:tmnxChassisIndex";
          }
        }
        leaf tmnxPortPortID {
          type leafref {
            path "/timetra-port:TIMETRA-PORT-MIB/timetra-port:tmnxPortTable/timetra-port:tmnxPortEntry/timetra-port:tmnxPortPortID";
          }
        }
        leaf tmnxPortCemStatsReportAlarm {
          type bits {
            bit notUsed {
              position 0;
            }
            bit strayPkts {
              position 1;
            }
            bit malformedPkts {
              position 2;
            }
            bit pktLoss {
              position 3;
            }
            bit bfrOverrun {
              position 4;
            }
            bit bfrUnderrun {
              position 5;
            }
            bit rmtPktLoss {
              position 6;
            }
            bit rmtFault {
              position 7;
            }
            bit rmtRdi {
              position 8;
            }
          }
          description
            "The value of tmnxPortCemStatsReportAlarm indicates the type of
             Circuit EMulation (CEM) alarm currently active on the port. The
             syntax of this object mirrors that of the CemSapReportAlarm
             TEXTUAL-CONVENTION. The values may be one of:
                 strayPkts     (1)- receiving stray packets.
                 malformedPkts (2)- detecting malformed packets.
                 pktLoss       (3)- experiencing packet loss.
                 bfrOverrun    (4)- experiencing jitter buffer overrun.
                 bfrUnderrun   (5)- experiencing jitter buffer underrun.
                 rmtPktLoss    (6)- remote packet loss indication.
                 rmtFault      (7)- remote TDM fault indication.
                 rmtRdi        (8)- remote RDI indication.";
          smiv2:max-access "read-only";
          smiv2:oid "1.3.6.1.4.1.6527.3.1.2.2.12.6.1.1";
        }
        leaf tmnxPortCemStatsIgrForwardedPkts {
          type yang:counter32;
          description
            "The value of tmnxPortCemStatsIgrForwardedPkts indicates
             the number of packets that were successfully forwarded.";
          smiv2:max-access "read-only";
          smiv2:oid "1.3.6.1.4.1.6527.3.1.2.2.12.6.1.2";
        }
        leaf tmnxPortCemStatsIgrDroppedPkts {
          type yang:counter32;
          description
            "The value of tmnxPortCemStatsIgrDroppedPkts indicates
             the total number of packets that were dropped due to errors.";
          smiv2:max-access "read-only";
          smiv2:oid "1.3.6.1.4.1.6527.3.1.2.2.12.6.1.3";
        }
        leaf tmnxPortCemStatsEgrForwardedPkts {
          type yang:counter32;
          description
            "The value of tmnxPortCemStatsEgrForwardedPkts indicates the
             number of packets that were successfully forwarded.";
          smiv2:max-access "read-only";
          smiv2:oid "1.3.6.1.4.1.6527.3.1.2.2.12.6.1.4";
        }
        leaf tmnxPortCemStatsEgrDroppedPkts {
          type yang:counter32;
          description
            "The value of tmnxPortCemStatsEgrDroppedPkts indicates
             the total number of packets that were dropped due to errors.";
          smiv2:max-access "read-only";
          smiv2:oid "1.3.6.1.4.1.6527.3.1.2.2.12.6.1.5";
        }
        leaf tmnxPortCemStatsEgrMissingPkts {
          type yang:counter32;
          description
            "The value of tmnxPortCemStatsEgrMissingPkts indicates the number of
             missing packets (as detected via control word sequence number gaps).";
          smiv2:max-access "read-only";
          smiv2:oid "1.3.6.1.4.1.6527.3.1.2.2.12.6.1.6";
        }
        leaf tmnxPortCemStatsEgrPktsReOrder {
          type yang:counter32;
          description
            "The value of tmnxPortCemStatsEgrPktsReOrder indicates the
             number of packets detected out of sequence (via control
             word sequence number), but successfully re-ordered.";
          smiv2:max-access "read-only";
          smiv2:oid "1.3.6.1.4.1.6527.3.1.2.2.12.6.1.7";
        }
        leaf tmnxPortCemStatsEgrJtrBfrURun {
          type yang:counter32;
          description
            "The value of tmnxPortCemStatsEgrJtrBfrURun indicates
             the number of times a packet needed to be played out and
             the jitter buffer was empty.";
          smiv2:max-access "read-only";
          smiv2:oid "1.3.6.1.4.1.6527.3.1.2.2.12.6.1.8";
        }
        leaf tmnxPortCemStatsEgrJtrBfrORun {
          type yang:counter32;
          description
            "The value of tmnxPortCemStatsEgrJtrBfrORun indicates
             the number of times a packet was dropped because it could
             not fit in the jitter buffer.";
          smiv2:max-access "read-only";
          smiv2:oid "1.3.6.1.4.1.6527.3.1.2.2.12.6.1.9";
        }
        leaf tmnxPortCemStatsEgrMisOrderDrop {
          type yang:counter32;
          description
            "The value of tmnxPortCemStatsEgrMisOrderDrop indicates
             the number of packets detected out of order (via control
             word sequence numbers), and could not be re-ordered, or
             could not be placed in the jitter buffer because it was
             out of the current window.";
          smiv2:max-access "read-only";
          smiv2:oid "1.3.6.1.4.1.6527.3.1.2.2.12.6.1.10";
        }
        leaf tmnxPortCemStatsEgrMalformedPkts {
          type yang:counter32;
          description
            "The value of tmnxPortCemStatsEgrMalformedPkts indicates the
             number of packets detected with unexpected size, or bad
             headers' stack.";
          smiv2:max-access "read-only";
          smiv2:oid "1.3.6.1.4.1.6527.3.1.2.2.12.6.1.11";
        }
        leaf tmnxPortCemStatsEgrLBitDrop {
          type yang:counter32;
          description
            "The value of tmnxPortCemStatsEgrLBitDrop indicates the
             number of packets dropped due to the L bit set by the far end.";
          smiv2:max-access "read-only";
          smiv2:oid "1.3.6.1.4.1.6527.3.1.2.2.12.6.1.12";
        }
        leaf tmnxPortCemStatsEgrMultipleDrop {
          type yang:counter32;
          description
            "The value of tmnxPortCemStatsEgrMultipleDrop indicates
             the number of packets dropped due to multiple sequence numbers.";
          smiv2:max-access "read-only";
          smiv2:oid "1.3.6.1.4.1.6527.3.1.2.2.12.6.1.13";
        }
        leaf tmnxPortCemStatsEgrESs {
          type yang:counter32;
          description
            "The value of tmnxPortCemStatsEgrESs indicates the number of
             Error Seconds (ESs) encountered. Any malformed packet,
             seq.  error, LOPS and similar are considered as error seconds.";
          smiv2:max-access "read-only";
          smiv2:oid "1.3.6.1.4.1.6527.3.1.2.2.12.6.1.14";
        }
        leaf tmnxPortCemStatsEgrSESs {
          type yang:counter32;
          description
            "The value of tmnxPortCemStatsEgrSESs indicates the number
             of Severely Error Seconds (SESs) encountered.  This is
             when more than 30 percent of the packets within a one
             second window are missing.";
          smiv2:max-access "read-only";
          smiv2:oid "1.3.6.1.4.1.6527.3.1.2.2.12.6.1.15";
        }
        leaf tmnxPortCemStatsEgrUASs {
          type yang:counter32;
          description
            "The value of tmnxPortCemStatsEgrUASs indicates the number of
             Unavailable Seconds (UASs) encountered. Any consecutive
             ten seconds of SESs are counted as one UAS.";
          smiv2:max-access "read-only";
          smiv2:oid "1.3.6.1.4.1.6527.3.1.2.2.12.6.1.16";
        }
        leaf tmnxPortCemStatsEgrFailureCounts {
          type yang:counter32;
          description
            "The value of tmnxPortCemStatsEgrFailureCounts indicates
             the number failure events.  A failure event begins when
             the LOPS failure is declared, and ends when the failure
             is cleared.";
          smiv2:max-access "read-only";
          smiv2:oid "1.3.6.1.4.1.6527.3.1.2.2.12.6.1.17";
        }
        leaf tmnxPortCemStatsEgrURunCounts {
          type yang:counter32;
          description
            "The value of tmnxPortCemStatsEgrURunCounts indicates
             the number of times the jitter buffer went into an
             underrun state.";
          smiv2:max-access "read-only";
          smiv2:oid "1.3.6.1.4.1.6527.3.1.2.2.12.6.1.18";
        }
        leaf tmnxPortCemStatsEgrORunCounts {
          type yang:counter32;
          description
            "The value of tmnxPortCemStatsEgrORunCounts indicates
             the number of times the jitter buffer went into an
             overrun state.";
          smiv2:max-access "read-only";
          smiv2:oid "1.3.6.1.4.1.6527.3.1.2.2.12.6.1.19";
        }
        leaf tmnxPortCemStatsEgrJtrBfrDepth {
          type yang:gauge32;
          description
            "The value of tmnxPortCemStatsEgrJtrBfrDepth indicates
             the current packet depth of the jitter buffer.";
          smiv2:max-access "read-only";
          smiv2:oid "1.3.6.1.4.1.6527.3.1.2.2.12.6.1.20";
        }
      }
      config false;
    }
    container tPortNetEgrQGrpPStatTable {
      description
        "The value of tPortNetEgrQGrpPStatTable contains port egress 
         queue group policer statistics on network side.";
      smiv2:oid "1.3.6.1.4.1.6527.3.1.2.2.12.7";
      list tPortNetEgrQGrpPStatEntry {
        key "tmnxChassisIndex tmnxPortPortID tPortNetEgrQGrpName tPortNetEgrQGrpInstanceId tPortNetEgrQGrpPStatQosPolicerId";
        description
          "The value of tPortNetEgrQGrpPStatEntry defines an entry in the
           tPortNetEgrQGrpPStatTable. It represents statistics about a 
           specific QoS egress queue group policer on the specified port.";
        smiv2:oid "1.3.6.1.4.1.6527.3.1.2.2.12.7.1";
        leaf tmnxChassisIndex {
          type leafref {
            path "/timetra-chassis:TIMETRA-CHASSIS-MIB/timetra-chassis:tmnxChassisTable/timetra-chassis:tmnxChassisEntry/timetra-chassis:tmnxChassisIndex";
          }
        }
        leaf tmnxPortPortID {
          type leafref {
            path "/timetra-port:TIMETRA-PORT-MIB/timetra-port:tmnxPortTable/timetra-port:tmnxPortEntry/timetra-port:tmnxPortPortID";
          }
        }
        leaf tPortNetEgrQGrpName {
          type leafref {
            path "/timetra-port:TIMETRA-PORT-MIB/timetra-port:tPortNetEgrQGrpTable/timetra-port:tPortNetEgrQGrpEntry/timetra-port:tPortNetEgrQGrpName";
          }
        }
        leaf tPortNetEgrQGrpInstanceId {
          type leafref {
            path "/timetra-port:TIMETRA-PORT-MIB/timetra-port:tPortNetEgrQGrpTable/timetra-port:tPortNetEgrQGrpEntry/timetra-port:tPortNetEgrQGrpInstanceId";
          }
        }
        leaf tPortNetEgrQGrpPStatQosPolicerId {
          type timetra-tc:TEgrPolicerId;
          description
            "The value of tPortNetEgrQGrpPStatQosPolicerId specifies the index of the 
             egress QoS policer queue group on network port.";
          smiv2:max-access "not-accessible";
          smiv2:oid "1.3.6.1.4.1.6527.3.1.2.2.12.7.1.1";
        }
        leaf tPortNetEgrQGrpPStatMode {
          type timetra-tc:TmnxEgrPolicerStatMode;
          description
            "The value of tPortNetEgrQGrpPStatMode indicates the stat mode used by 
             this policer.";
          smiv2:max-access "read-only";
          smiv2:oid "1.3.6.1.4.1.6527.3.1.2.2.12.7.1.2";
        }
        leaf tPortNetEgrQGrpPStOffInProfPkt {
          type yang:counter64;
          description
            "The value of tPortNetEgrQGrpPStOffInProfPkt indicates the number of 
             in-profile packets (rate below CIR) offered by the egress Pchip.";
          smiv2:max-access "read-only";
          smiv2:oid "1.3.6.1.4.1.6527.3.1.2.2.12.7.1.3";
        }
        leaf tPortNetEgrQGrpPStOffInProfPktL {
          type yang:counter32;
          description
            "The value of tPortNetEgrQGrpPStOffInProfPktL indicates the lower 32 
             bits of tPortNetEgrQGrpPStOffInProfPkt.";
          smiv2:max-access "read-only";
          smiv2:oid "1.3.6.1.4.1.6527.3.1.2.2.12.7.1.4";
        }
        leaf tPortNetEgrQGrpPStOffInProfPktH {
          type yang:counter32;
          description
            "The value of tPortNetEgrQGrpPStOffInProfPktH indicates the upper 32 
             bits of tPortNetEgrQGrpPStOffInProfPkt.";
          smiv2:max-access "read-only";
          smiv2:oid "1.3.6.1.4.1.6527.3.1.2.2.12.7.1.5";
        }
        leaf tPortNetEgrQGrpPStFwdInProfPkt {
          type yang:counter64;
          description
            "The value of tPortNetEgrQGrpPStFwdInProfPkt indicates the number of 
             in-profile packets (rate below CIR) forwarded by the egress Pchip.";
          smiv2:max-access "read-only";
          smiv2:oid "1.3.6.1.4.1.6527.3.1.2.2.12.7.1.6";
        }
        leaf tPortNetEgrQGrpPStFwdInProfPktL {
          type yang:counter32;
          description
            "The value of tPortNetEgrQGrpPStFwdInProfPktL indicates the lower 32
             bits of tPortNetEgrQGrpPStFwdInProfPkt.";
          smiv2:max-access "read-only";
          smiv2:oid "1.3.6.1.4.1.6527.3.1.2.2.12.7.1.7";
        }
        leaf tPortNetEgrQGrpPStFwdInProfPktH {
          type yang:counter32;
          description
            "The value of tPortNetEgrQGrpPStFwdInProfPktH indicates the upper 32 
             bits of tPortNetEgrQGrpPStFwdInProfPkt.";
          smiv2:max-access "read-only";
          smiv2:oid "1.3.6.1.4.1.6527.3.1.2.2.12.7.1.8";
        }
        leaf tPortNetEgrQGrpPStDrpInProfPkt {
          type yang:counter64;
          description
            "The value of tPortNetEgrQGrpPStDrpInProfPkt indicates the number of 
             in-profile packets discarded by the egress Pchip due to: MBS exceeded,
             buffer pool limit exceeded, etc.";
          smiv2:max-access "read-only";
          smiv2:oid "1.3.6.1.4.1.6527.3.1.2.2.12.7.1.9";
        }
        leaf tPortNetEgrQGrpPStDrpInProfPktL {
          type yang:counter32;
          description
            "The value of tPortNetEgrQGrpPStDrpInProfPktL indicates the lower 32 
             bits of tPortNetEgrQGrpPStDrpInProfPkt.";
          smiv2:max-access "read-only";
          smiv2:oid "1.3.6.1.4.1.6527.3.1.2.2.12.7.1.10";
        }
        leaf tPortNetEgrQGrpPStDrpInProfPktH {
          type yang:counter32;
          description
            "The value of tPortNetEgrQGrpPStDrpInProfPktH indicates the upper 32 
             bits of tPortNetEgrQGrpPStDrpInProfPkt.";
          smiv2:max-access "read-only";
          smiv2:oid "1.3.6.1.4.1.6527.3.1.2.2.12.7.1.11";
        }
        leaf tPortNetEgrQGrpPStOffOutProfPkt {
          type yang:counter64;
          description
            "The value of tPortNetEgrQGrpPStOffOutProfPkt indicates the number of 
             out-of-profile packets (rate above CIR) offered by the  egress Pchip.";
          smiv2:max-access "read-only";
          smiv2:oid "1.3.6.1.4.1.6527.3.1.2.2.12.7.1.12";
        }
        leaf tPortNetEgrQGrpPStOffOutProfPktL {
          type yang:counter32;
          description
            "The value of tPortNetEgrQGrpPStOffOutProfPktL indicates the lower 32 
             bits of tPortNetEgrQGrpPStOffOutProfPkt.";
          smiv2:max-access "read-only";
          smiv2:oid "1.3.6.1.4.1.6527.3.1.2.2.12.7.1.13";
        }
        leaf tPortNetEgrQGrpPStOffOutProfPktH {
          type yang:counter32;
          description
            "The value of tPortNetEgrQGrpPStOffOutProfPktH indicates the upper 32 
             bits of tPortNetEgrQGrpPStOffOutProfPkt.";
          smiv2:max-access "read-only";
          smiv2:oid "1.3.6.1.4.1.6527.3.1.2.2.12.7.1.14";
        }
        leaf tPortNetEgrQGrpPStFwdOutProfPkt {
          type yang:counter64;
          description
            "The value of tPortNetEgrQGrpPStFwdOutProfPkt indicates the number of 
             out-of-profile packets (rate above CIR) forwarded by the egress Pchip.";
          smiv2:max-access "read-only";
          smiv2:oid "1.3.6.1.4.1.6527.3.1.2.2.12.7.1.15";
        }
        leaf tPortNetEgrQGrpPStFwdOutProfPktL {
          type yang:counter32;
          description
            "The value of tPortNetEgrQGrpPStFwdOutProfPktL indicates the lower 32
             bits of tPortNetEgrQGrpPStFwdOutProfPkt.";
          smiv2:max-access "read-only";
          smiv2:oid "1.3.6.1.4.1.6527.3.1.2.2.12.7.1.16";
        }
        leaf tPortNetEgrQGrpPStFwdOutProfPktH {
          type yang:counter32;
          description
            "The value of tPortNetEgrQGrpPStFwdOutProfPktH indicates the upper 32 
             bits of tPortNetEgrQGrpPStFwdOutProfPkt.";
          smiv2:max-access "read-only";
          smiv2:oid "1.3.6.1.4.1.6527.3.1.2.2.12.7.1.17";
        }
        leaf tPortNetEgrQGrpPStDrpOutProfPkt {
          type yang:counter64;
          description
            "The value of tPortNetEgrQGrpPStDrpOutProfPkt indicates the number of 
             out-of-profile packets discarded by the egress Pchip due to: MBS 
             exceeded, buffer pool limit exceeded, etc.";
          smiv2:max-access "read-only";
          smiv2:oid "1.3.6.1.4.1.6527.3.1.2.2.12.7.1.18";
        }
        leaf tPortNetEgrQGrpPStDrpOutProfPktL {
          type yang:counter32;
          description
            "The value of tPortNetEgrQGrpPStDrpOutProfPktL indicates the lower 32 
             bits of tPortNetEgrQGrpPStDrpOutProfPkt.";
          smiv2:max-access "read-only";
          smiv2:oid "1.3.6.1.4.1.6527.3.1.2.2.12.7.1.19";
        }
        leaf tPortNetEgrQGrpPStDrpOutProfPktH {
          type yang:counter32;
          description
            "The value of tPortNetEgrQGrpPStDrpOutProfPktH indicates the upper 32 
             bits of tPortNetEgrQGrpPStDrpOutProfPkt.";
          smiv2:max-access "read-only";
          smiv2:oid "1.3.6.1.4.1.6527.3.1.2.2.12.7.1.20";
        }
        leaf tPortNetEgrQGrpPStOffInProfOct {
          type yang:counter64;
          description
            "The value of tPortNetEgrQGrpPStOffInProfOct indicates the number of 
             in-profile octets (rate below CIR) offered by the egress Pchip.";
          smiv2:max-access "read-only";
          smiv2:oid "1.3.6.1.4.1.6527.3.1.2.2.12.7.1.21";
        }
        leaf tPortNetEgrQGrpPStOffInProfOctL {
          type yang:counter32;
          description
            "The value of tPortNetEgrQGrpPStOffInProfOctL indicates the lower 32 
             bits of tPortNetEgrQGrpPStOffInProfOct.";
          smiv2:max-access "read-only";
          smiv2:oid "1.3.6.1.4.1.6527.3.1.2.2.12.7.1.22";
        }
        leaf tPortNetEgrQGrpPStOffInProfOctH {
          type yang:counter32;
          description
            "The value of tPortNetEgrQGrpPStOffInProfOctH indicates the upper 32 
             bits of tPortNetEgrQGrpPStOffInProfOct.";
          smiv2:max-access "read-only";
          smiv2:oid "1.3.6.1.4.1.6527.3.1.2.2.12.7.1.23";
        }
        leaf tPortNetEgrQGrpPStFwdInProfOct {
          type yang:counter64;
          description
            "The value of tPortNetEgrQGrpPStFwdInProfOct indicates the number of 
             in-profile octets (rate below CIR) forwarded by the egress Pchip.";
          smiv2:max-access "read-only";
          smiv2:oid "1.3.6.1.4.1.6527.3.1.2.2.12.7.1.24";
        }
        leaf tPortNetEgrQGrpPStFwdInProfOctL {
          type yang:counter32;
          description
            "The value of tPortNetEgrQGrpPStFwdInProfOctL indicates the lower 32 
             bits of tPortNetEgrQGrpPStFwdInProfOct.";
          smiv2:max-access "read-only";
          smiv2:oid "1.3.6.1.4.1.6527.3.1.2.2.12.7.1.25";
        }
        leaf tPortNetEgrQGrpPStFwdInProfOctH {
          type yang:counter32;
          description
            "The value of tPortNetEgrQGrpPStFwdInProfOctH indicates the upper 32 
             bits of tPortNetEgrQGrpPStFwdInProfOct.";
          smiv2:max-access "read-only";
          smiv2:oid "1.3.6.1.4.1.6527.3.1.2.2.12.7.1.26";
        }
        leaf tPortNetEgrQGrpPStDrpInProfOct {
          type yang:counter64;
          description
            "The value of tPortNetEgrQGrpPStDrpInProfOct indicates the number of 
             in-profile octets discarded by the egress Pchip due to: MBS exceeded, 
             buffer pool limit exceeded, etc.";
          smiv2:max-access "read-only";
          smiv2:oid "1.3.6.1.4.1.6527.3.1.2.2.12.7.1.27";
        }
        leaf tPortNetEgrQGrpPStDrpInProfOctL {
          type yang:counter32;
          description
            "The value of tPortNetEgrQGrpPStDrpInProfOctL indicates the lower 32 
             bits of tPortNetEgrQGrpPStDrpInProfOct.";
          smiv2:max-access "read-only";
          smiv2:oid "1.3.6.1.4.1.6527.3.1.2.2.12.7.1.28";
        }
        leaf tPortNetEgrQGrpPStDrpInProfOctH {
          type yang:counter32;
          description
            "The value of tPortNetEgrQGrpPStDrpInProfOctH indicates the upper 32 
             bits of tPortNetEgrQGrpPStDrpInProfOct.";
          smiv2:max-access "read-only";
          smiv2:oid "1.3.6.1.4.1.6527.3.1.2.2.12.7.1.29";
        }
        leaf tPortNetEgrQGrpPStOffOutProfOct {
          type yang:counter64;
          description
            "The value of tPortNetEgrQGrpPStOffOutProfOct indicates the number of 
             out-of-profile octets (rate above CIR) forwarded by the egress Pchip.";
          smiv2:max-access "read-only";
          smiv2:oid "1.3.6.1.4.1.6527.3.1.2.2.12.7.1.30";
        }
        leaf tPortNetEgrQGrpPStOffOutProfOctL {
          type yang:counter32;
          description
            "The value of tPortNetEgrQGrpPStOffOutProfOctL indicates the lower 32 
             bits of tPortNetEgrQGrpPStOffOutProfOct.";
          smiv2:max-access "read-only";
          smiv2:oid "1.3.6.1.4.1.6527.3.1.2.2.12.7.1.31";
        }
        leaf tPortNetEgrQGrpPStOffOutProfOctH {
          type yang:counter32;
          description
            "The value of tPortNetEgrQGrpPStOffOutProfOctH indicates the upper 32 
             bits of tPortNetEgrQGrpPStOffOutProfOct.";
          smiv2:max-access "read-only";
          smiv2:oid "1.3.6.1.4.1.6527.3.1.2.2.12.7.1.32";
        }
        leaf tPortNetEgrQGrpPStFwdOutProfOct {
          type yang:counter64;
          description
            "The value of tPortNetEgrQGrpPStFwdOutProfOct indicates the number of 
             out-of-profile octets (rate above CIR) forwarded by the egress Pchip.";
          smiv2:max-access "read-only";
          smiv2:oid "1.3.6.1.4.1.6527.3.1.2.2.12.7.1.33";
        }
        leaf tPortNetEgrQGrpPStFwdOutProfOctL {
          type yang:counter32;
          description
            "The value of tPortNetEgrQGrpPStFwdOutProfOctL indicates the lower 32 
             bits of tPortNetEgrQGrpPStFwdOutProfOct.";
          smiv2:max-access "read-only";
          smiv2:oid "1.3.6.1.4.1.6527.3.1.2.2.12.7.1.34";
        }
        leaf tPortNetEgrQGrpPStFwdOutProfOctH {
          type yang:counter32;
          description
            "The value of tPortNetEgrQGrpPStFwdOutProfOctH indicates the upper 32 
             bits of tPortNetEgrQGrpPStFwdOutProfOct.";
          smiv2:max-access "read-only";
          smiv2:oid "1.3.6.1.4.1.6527.3.1.2.2.12.7.1.35";
        }
        leaf tPortNetEgrQGrpPStDrpOutProfOct {
          type yang:counter64;
          description
            "The value of tPortNetEgrQGrpPStDrpOutProfOct indicates the number of 
             out-of-profile octets discarded by the egress Pchip due to: MBS 
             exceeded, buffer pool limit exceeded, etc.";
          smiv2:max-access "read-only";
          smiv2:oid "1.3.6.1.4.1.6527.3.1.2.2.12.7.1.36";
        }
        leaf tPortNetEgrQGrpPStDrpOutProfOctL {
          type yang:counter32;
          description
            "The value of tPortNetEgrQGrpPStDrpOutProfOctL indicates the lower 32 
             bits of tPortNetEgrQGrpPStDrpOutProfOct.";
          smiv2:max-access "read-only";
          smiv2:oid "1.3.6.1.4.1.6527.3.1.2.2.12.7.1.37";
        }
        leaf tPortNetEgrQGrpPStDrpOutProfOctH {
          type yang:counter32;
          description
            "The value of tPortNetEgrQGrpPStDrpOutProfOctH indicates the upper 32 
             bits of tPortNetEgrQGrpPStDrpOutProfOct.";
          smiv2:max-access "read-only";
          smiv2:oid "1.3.6.1.4.1.6527.3.1.2.2.12.7.1.38";
        }
        leaf tPortNetEgrQGrpPStUncolPktOff {
          type yang:counter64;
          description
            "The value of tPortNetEgrQGrpPStUncolPktOff indicates the number of
             uncolored packets forwarded by the egress Pchip.";
          smiv2:max-access "read-only";
          smiv2:oid "1.3.6.1.4.1.6527.3.1.2.2.12.7.1.39";
        }
        leaf tPortNetEgrQGrpPStUncolPktOffL {
          type yang:counter32;
          description
            "The value of tPortNetEgrQGrpPStUncolPktOffL indicates the lower 32 
             bits of tPortNetEgrQGrpPStUncolPktOff.";
          smiv2:max-access "read-only";
          smiv2:oid "1.3.6.1.4.1.6527.3.1.2.2.12.7.1.40";
        }
        leaf tPortNetEgrQGrpPStUncolPktOffH {
          type yang:counter32;
          description
            "The value of tPortNetEgrQGrpPStUncolPktOffH indicates the upper 32 
             bits of tPortNetEgrQGrpPStUncolPktOff.";
          smiv2:max-access "read-only";
          smiv2:oid "1.3.6.1.4.1.6527.3.1.2.2.12.7.1.41";
        }
        leaf tPortNetEgrQGrpPStUncolOctOff {
          type yang:counter64;
          description
            "The value of tPortNetEgrQGrpPStUncolOctOff indicates the number of 
             uncolored octets forwarded by the egress Pchip.";
          smiv2:max-access "read-only";
          smiv2:oid "1.3.6.1.4.1.6527.3.1.2.2.12.7.1.42";
        }
        leaf tPortNetEgrQGrpPStUncolOctOffL {
          type yang:counter32;
          description
            "The value of tPortNetEgrQGrpPStUncolOctOffL indicates the lower 32 
             bits of tPortNetEgrQGrpPStUncolOctOff.";
          smiv2:max-access "read-only";
          smiv2:oid "1.3.6.1.4.1.6527.3.1.2.2.12.7.1.43";
        }
        leaf tPortNetEgrQGrpPStUncolOctOffH {
          type yang:counter32;
          description
            "The value of tPortNetEgrQGrpPStUncolOctOffH indicates the upper 32 
             bits of tPortNetEgrQGrpPStUncolOctOff.";
          smiv2:max-access "read-only";
          smiv2:oid "1.3.6.1.4.1.6527.3.1.2.2.12.7.1.44";
        }
      }
      config false;
    }
    container tmnxCohOptPortStatsTable {
      description
        "The tmnxCohOptPortStatsTable contains statistics information for DWDM
         coherent optical ports in the Alcatel-Lucent SROS system.";
      smiv2:oid "1.3.6.1.4.1.6527.3.1.2.2.12.8";
      list tmnxCohOptPortStatsEntry {
        key "tmnxChassisIndex tmnxPortPortID";
        description
          "Each row entry includes statistics for a DWDM coherent optical port in
           the system. Entries cannot be created or deleted via SNMP SET
           operations.";
        smiv2:oid "1.3.6.1.4.1.6527.3.1.2.2.12.8.1";
        leaf tmnxChassisIndex {
          type leafref {
            path "/timetra-chassis:TIMETRA-CHASSIS-MIB/timetra-chassis:tmnxChassisTable/timetra-chassis:tmnxChassisEntry/timetra-chassis:tmnxChassisIndex";
          }
        }
        leaf tmnxPortPortID {
          type leafref {
            path "/timetra-port:TIMETRA-PORT-MIB/timetra-port:tmnxPortTable/timetra-port:tmnxPortEntry/timetra-port:tmnxPortPortID";
          }
        }
        leaf tmnxCohOptPortStatsElapsedSec {
          type yang:counter32;
          units "seconds";
          description
            "The value of tmnxCohOptPortStatsElapsedSec indicates the number of
             elapsed seconds since the start of coherent optical stats collection
             after the last port statistics clear.";
          smiv2:max-access "read-only";
          smiv2:oid "1.3.6.1.4.1.6527.3.1.2.2.12.8.1.1";
        }
        leaf tmnxCohOptPortRxBER {
          type yang:gauge32;
          description
            "The value of tmnxCohOptPortRxBER indicates the RX Bit Error Rate (BER)
             since the last port statistics clear, represented as an IEEE 754
             32-bit floating point number.";
          smiv2:max-access "read-only";
          smiv2:oid "1.3.6.1.4.1.6527.3.1.2.2.12.8.1.2";
        }
        leaf tmnxCohOptPortRxBERAvg {
          type yang:gauge32;
          description
            "The value of tmnxCohOptPortRxBERAvg indicates the RX average BER since
             the last port statistics clear, represented as an IEEE 754 32-bit
             floating point number.";
          smiv2:max-access "read-only";
          smiv2:oid "1.3.6.1.4.1.6527.3.1.2.2.12.8.1.3";
        }
        leaf tmnxCohOptPortRxBERMin {
          type yang:gauge32;
          description
            "The value of tmnxCohOptPortRxBERMin indicates the RX minimum BER since
             the last port statistics clear, represented as an IEEE 754 32-bit
             floating point number.";
          smiv2:max-access "read-only";
          smiv2:oid "1.3.6.1.4.1.6527.3.1.2.2.12.8.1.4";
        }
        leaf tmnxCohOptPortRxBERMax {
          type yang:gauge32;
          description
            "The value of tmnxCohOptPortRxBERMax indicates the RX maximum BER since
             the last port statistics clear, represented as an IEEE 754 32-bit
             floating point number.";
          smiv2:max-access "read-only";
          smiv2:oid "1.3.6.1.4.1.6527.3.1.2.2.12.8.1.5";
        }
        leaf tmnxCohOptPortRxSNR {
          type yang:gauge32;
          units "0.1 dB";
          description
            "The value of tmnxCohOptPortRxSNR indicates the RX Signal-to-Noise
             Ratio (SNR) since the last port statistics clear, represented in
             tenths of a dB.";
          smiv2:max-access "read-only";
          smiv2:oid "1.3.6.1.4.1.6527.3.1.2.2.12.8.1.6";
        }
        leaf tmnxCohOptPortRxSNRAvg {
          type yang:gauge32;
          units "0.1 dB";
          description
            "The value of tmnxCohOptPortRxSNRAvg indicates the RX average SNR since
             the last port statistics clear, represented in tenths of a dB.";
          smiv2:max-access "read-only";
          smiv2:oid "1.3.6.1.4.1.6527.3.1.2.2.12.8.1.7";
        }
        leaf tmnxCohOptPortRxSNRMin {
          type yang:gauge32;
          units "0.1 dB";
          description
            "The value of tmnxCohOptPortRxSNRMin indicates the RX minimum SNR since
             the last port statistics clear, represented in tenths of a dB.";
          smiv2:max-access "read-only";
          smiv2:oid "1.3.6.1.4.1.6527.3.1.2.2.12.8.1.8";
        }
        leaf tmnxCohOptPortRxSNRMax {
          type yang:gauge32;
          units "0.1 dB";
          description
            "The value of tmnxCohOptPortRxSNRMax indicates the RX maximum SNR since
             the last port statistics clear, represented in tenths of a dB.";
          smiv2:max-access "read-only";
          smiv2:oid "1.3.6.1.4.1.6527.3.1.2.2.12.8.1.9";
        }
        leaf tmnxCohOptPortRxChromaticDisp {
          type int32;
          units "picoseconds per nanometer";
          description
            "The value of tmnxCohOptPortRxChromaticDisp indicates the RX chromatic
             dispersion since the last port statistics clear.";
          smiv2:max-access "read-only";
          smiv2:oid "1.3.6.1.4.1.6527.3.1.2.2.12.8.1.10";
        }
        leaf tmnxCohOptPortRxChromaticDispAvg {
          type int32;
          units "picoseconds per nanometer";
          description
            "The value of tmnxCohOptPortRxChromaticDispAvg indicates the RX average
             chromatic dispersion since the last port statistics clear.";
          smiv2:max-access "read-only";
          smiv2:oid "1.3.6.1.4.1.6527.3.1.2.2.12.8.1.11";
        }
        leaf tmnxCohOptPortRxChromaticDispMin {
          type int32;
          units "picoseconds per nanometer";
          description
            "The value of tmnxCohOptPortRxChromaticDispMin indicates the RX minimum
             chromatic dispersion since the last port statistics clear.";
          smiv2:max-access "read-only";
          smiv2:oid "1.3.6.1.4.1.6527.3.1.2.2.12.8.1.12";
        }
        leaf tmnxCohOptPortRxChromaticDispMax {
          type int32;
          units "picoseconds per nanometer";
          description
            "The value of tmnxCohOptPortRxChromaticDispMax indicates the RX maximum
             chromatic dispersion since the last port statistics clear.";
          smiv2:max-access "read-only";
          smiv2:oid "1.3.6.1.4.1.6527.3.1.2.2.12.8.1.13";
        }
        leaf tmnxCohOptPortRxDiffGrpDly {
          type yang:gauge32;
          units "picoseconds";
          description
            "The value of tmnxCohOptPortRxDiffGrpDly indicates the RX differential
             group delay since the last port statistics clear.";
          smiv2:max-access "read-only";
          smiv2:oid "1.3.6.1.4.1.6527.3.1.2.2.12.8.1.14";
        }
        leaf tmnxCohOptPortRxDiffGrpDlyAvg {
          type yang:gauge32;
          units "picoseconds";
          description
            "The value of tmnxCohOptPortRxDiffGrpDlyAvg indicates the RX average
             differential group delay since the last port statistics clear.";
          smiv2:max-access "read-only";
          smiv2:oid "1.3.6.1.4.1.6527.3.1.2.2.12.8.1.15";
        }
        leaf tmnxCohOptPortRxDiffGrpDlyMin {
          type yang:gauge32;
          units "picoseconds";
          description
            "The value of tmnxCohOptPortRxDiffGrpDlyMin indicates the RX minimum
             differential group delay since the last port statistics clear.";
          smiv2:max-access "read-only";
          smiv2:oid "1.3.6.1.4.1.6527.3.1.2.2.12.8.1.16";
        }
        leaf tmnxCohOptPortRxDiffGrpDlyMax {
          type yang:gauge32;
          units "picoseconds";
          description
            "The value of tmnxCohOptPortRxDiffGrpDlyMax indicates the RX maximum
             differential group delay since the last port statistics clear.";
          smiv2:max-access "read-only";
          smiv2:oid "1.3.6.1.4.1.6527.3.1.2.2.12.8.1.17";
        }
        leaf tmnxCohOptPortRxFreqOffset {
          type int32;
          units "MHz";
          description
            "The value of tmnxCohOptPortRxFreqOffset indicates the RX frequency
             offset since the last port statistics clear.";
          smiv2:max-access "read-only";
          smiv2:oid "1.3.6.1.4.1.6527.3.1.2.2.12.8.1.18";
        }
        leaf tmnxCohOptPortRxFreqOffsetAvg {
          type int32;
          units "MHz";
          description
            "The value of tmnxCohOptPortRxFreqOffsetAvg indicates the RX average
             frequency offset since the last port statistics clear.";
          smiv2:max-access "read-only";
          smiv2:oid "1.3.6.1.4.1.6527.3.1.2.2.12.8.1.19";
        }
        leaf tmnxCohOptPortRxFreqOffsetMin {
          type int32;
          units "MHz";
          description
            "The value of tmnxCohOptPortRxFreqOffsetMin indicates the RX minimum
             frequency offset since the last port statistics clear.";
          smiv2:max-access "read-only";
          smiv2:oid "1.3.6.1.4.1.6527.3.1.2.2.12.8.1.20";
        }
        leaf tmnxCohOptPortRxFreqOffsetMax {
          type int32;
          units "MHz";
          description
            "The value of tmnxCohOptPortRxFreqOffsetMax indicates the RX maximum
             frequency offset since the last port statistics clear.";
          smiv2:max-access "read-only";
          smiv2:oid "1.3.6.1.4.1.6527.3.1.2.2.12.8.1.21";
        }
        leaf tmnxCohOptPortRxQ {
          type int32;
          units "0.1 dB";
          description
            "The value of tmnxCohOptPortRxQ indicates the RX Q since the last port
             statistics clear, represented in tenths of a dB.";
          smiv2:max-access "read-only";
          smiv2:oid "1.3.6.1.4.1.6527.3.1.2.2.12.8.1.22";
        }
        leaf tmnxCohOptPortRxQAvg {
          type int32;
          units "0.1 dB";
          description
            "The value of tmnxCohOptPortRxQAvg indicates the RX average Q since
             the last port statistics clear, represented in tenths of a dB.";
          smiv2:max-access "read-only";
          smiv2:oid "1.3.6.1.4.1.6527.3.1.2.2.12.8.1.23";
        }
        leaf tmnxCohOptPortRxQMin {
          type int32;
          units "0.1 dB";
          description
            "The value of tmnxCohOptPortRxQMin indicates the RX minimum Q since
             the last port statistics clear, represented in tenths of a dB.";
          smiv2:max-access "read-only";
          smiv2:oid "1.3.6.1.4.1.6527.3.1.2.2.12.8.1.24";
        }
        leaf tmnxCohOptPortRxQMax {
          type int32;
          units "0.1 dB";
          description
            "The value of tmnxCohOptPortRxQMax indicates the RX maximum Q since
             the last port statistics clear, represented in tenths of a dB.";
          smiv2:max-access "read-only";
          smiv2:oid "1.3.6.1.4.1.6527.3.1.2.2.12.8.1.25";
        }
        leaf tmnxCohOptPortRxPower {
          type int32;
          units "mBm";
          description
            "The value of tmnxCohOptPortRxPower indicates the RX optical power
             since the last port statistics clear.";
          smiv2:max-access "read-only";
          smiv2:oid "1.3.6.1.4.1.6527.3.1.2.2.12.8.1.26";
        }
        leaf tmnxCohOptPortRxPowerAvg {
          type int32;
          units "mBm";
          description
            "The value of tmnxCohOptPortRxPowerAvg indicates the RX average optical
             power since the last port statistics clear.";
          smiv2:max-access "read-only";
          smiv2:oid "1.3.6.1.4.1.6527.3.1.2.2.12.8.1.27";
        }
        leaf tmnxCohOptPortRxPowerMin {
          type int32;
          units "mBm";
          description
            "The value of tmnxCohOptPortRxPowerMin indicates the RX minimum optical
             power since the last port statistics clear.";
          smiv2:max-access "read-only";
          smiv2:oid "1.3.6.1.4.1.6527.3.1.2.2.12.8.1.28";
        }
        leaf tmnxCohOptPortRxPowerMax {
          type int32;
          units "mBm";
          description
            "The value of tmnxCohOptPortRxPowerMax indicates the RX maximum optical
             power since the last port statistics clear.";
          smiv2:max-access "read-only";
          smiv2:oid "1.3.6.1.4.1.6527.3.1.2.2.12.8.1.29";
        }
        leaf tmnxCohOptPortTxPower {
          type int32;
          units "mBm";
          description
            "The value of tmnxCohOptPortTxPower indicates the TX optical power
             since the last port statistics clear.";
          smiv2:max-access "read-only";
          smiv2:oid "1.3.6.1.4.1.6527.3.1.2.2.12.8.1.30";
        }
        leaf tmnxCohOptPortTxPowerAvg {
          type int32;
          units "mBm";
          description
            "The value of tmnxCohOptPortTxPowerAvg indicates the TX average optical
             power since the last port statistics clear.";
          smiv2:max-access "read-only";
          smiv2:oid "1.3.6.1.4.1.6527.3.1.2.2.12.8.1.31";
        }
        leaf tmnxCohOptPortTxPowerMin {
          type int32;
          units "mBm";
          description
            "The value of tmnxCohOptPortTxPowerMin indicates the TX minimum optical
             power since the last port statistics clear.";
          smiv2:max-access "read-only";
          smiv2:oid "1.3.6.1.4.1.6527.3.1.2.2.12.8.1.32";
        }
        leaf tmnxCohOptPortTxPowerMax {
          type int32;
          units "mBm";
          description
            "The value of tmnxCohOptPortTxPowerMax indicates the TX maximum optical
             power since the last port statistics clear.";
          smiv2:max-access "read-only";
          smiv2:oid "1.3.6.1.4.1.6527.3.1.2.2.12.8.1.33";
        }
      }
      config false;
    }
    config true;
  }
  smiv2:alias "tmnxPortTestTable" {
    description
      "The tmnxPortTestTable has an entry for each port on each IOM
       card in each chassis in the TMNX system.";
    smiv2:oid "1.3.6.1.4.1.6527.3.1.2.2.4.3";
  }
  smiv2:alias "tmnxPortTestEntry" {
    description
      "Each row entry represents a port on a IOM card in a
       chassis in the system.  Entries cannot be created and
       deleted via SNMP SET operations.";
    smiv2:oid "1.3.6.1.4.1.6527.3.1.2.2.4.3.1";
  }

  augment "/timetra-port:TIMETRA-PORT-MIB/timetra-port:tmnxPortTable/timetra-port:tmnxPortEntry" {
    description
      "Each row entry represents a port on a IOM card in a
       chassis in the system.  Entries cannot be created and
       deleted via SNMP SET operations.";
    smiv2:oid "1.3.6.1.4.1.6527.3.1.2.2.4.3.1";
    leaf tmnxPortTestState {
      type enumeration {
        enum "notInTest" {
          value 1;
        }
        enum "inTest" {
          value 2;
        }
      }
      description
        "The current testing status of this port.";
      smiv2:max-access "read-only";
      smiv2:oid "1.3.6.1.4.1.6527.3.1.2.2.4.3.1.1";
      config false;
    }
    leaf tmnxPortTestMode {
      type enumeration {
        enum "notApplicable" {
          value 0;
        }
        enum "loopback1" {
          value 1;
        }
        enum "loopback2" {
          value 2;
        }
        enum "loopback3" {
          value 3;
        }
        enum "singalInsertion" {
          value 4;
        }
      }
      description
        "The type of test to be executed on this port.";
      smiv2:max-access "read-write";
      smiv2:oid "1.3.6.1.4.1.6527.3.1.2.2.4.3.1.2";
      config true;
    }
    leaf tmnxPortTestParameter {
      type uint32;
      description
        "A parameter to be passed to the test program.";
      smiv2:max-access "read-write";
      smiv2:oid "1.3.6.1.4.1.6527.3.1.2.2.4.3.1.3";
      config true;
    }
    leaf tmnxPortTestLastResult {
      type enumeration {
        enum "notApplicable" {
          value 0;
        }
        enum "success" {
          value 1;
        }
        enum "failure" {
          value 2;
        }
        enum "timeout" {
          value 3;
        }
      }
      description
        "The status of the last test executed on this port.";
      smiv2:max-access "read-only";
      smiv2:oid "1.3.6.1.4.1.6527.3.1.2.2.4.3.1.4";
      config false;
    }
    leaf tmnxPortTestStartTime {
      type snmpv2-tc:DateAndTime;
      description
        "The date and time the test started on this port.
         Returns 0 if tmnxPortTestState is notInTest.";
      smiv2:max-access "read-only";
      smiv2:oid "1.3.6.1.4.1.6527.3.1.2.2.4.3.1.5";
      config false;
    }
    leaf tmnxPortTestEndTime {
      type snmpv2-tc:DateAndTime;
      description
        "The date and time the last test completed.  Returns 0
         if a test is in progress or no tests have yet to be run on
         this port.";
      smiv2:max-access "read-only";
      smiv2:oid "1.3.6.1.4.1.6527.3.1.2.2.4.3.1.6";
      config false;
    }
    leaf tmnxPortTestDuration {
      type int32 {
        range "0..256";
      }
      description
        "The number of seconds the port test is anticipated to last.";
      smiv2:max-access "read-write";
      smiv2:oid "1.3.6.1.4.1.6527.3.1.2.2.4.3.1.7";
      config true;
    }
    leaf tmnxPortTestAction {
      type enumeration {
        enum "none" {
          value 1;
        }
        enum "startTest" {
          value 2;
        }
        enum "stopTest" {
          value 3;
        }
      }
      description
        "The operator sets this variable to perform the appropriate
         type of testing.";
      smiv2:max-access "read-write";
      smiv2:oid "1.3.6.1.4.1.6527.3.1.2.2.4.3.1.8";
      config true;
    }
  }
  smiv2:alias "tmnxCohOptPortCommandTable" {
    description
      "The tmnxCohOptPortCommandTable contains information pertaining to
       the execution of commands on DWDM coherent optical ports in the
       Alcatel-Lucent SROS system.";
    smiv2:oid "1.3.6.1.4.1.6527.3.1.2.2.4.72";
  }
  smiv2:alias "tmnxCohOptPortCommandEntry" {
    description
      "Each row entry exists only if the associated tmnxCohOptPortCfgEntry
       exists. Entries cannot be created or deleted via SNMP SET operations.";
    smiv2:oid "1.3.6.1.4.1.6527.3.1.2.2.4.72.1";
  }

  augment "/timetra-port:TIMETRA-PORT-MIB/timetra-port:tmnxCohOptPortCfgTable/timetra-port:tmnxCohOptPortCfgEntry" {
    description
      "Each row entry exists only if the associated tmnxCohOptPortCfgEntry
       exists. Entries cannot be created or deleted via SNMP SET operations.";
    smiv2:oid "1.3.6.1.4.1.6527.3.1.2.2.4.72.1";
    leaf tmnxCohOptPortCprWinSizeSearch {
      type enumeration {
        enum "noCmd" {
          value 1;
        }
        enum "execute" {
          value 2;
        }
      }
      description
        "The value of tmnxCohOptPortCprWinSizeSearch specifies the execution
         of a search for the optimal CPR window size when the value specified
         is 'execute(2)'. When the value specified is 'noCmd(1)', no action
         will be taken.
         
         The status of the search can be found in
         tmnxCohOptPortCprWnSzSrchStatus. The search result can be found in
         tmnxCohOptPortCprWnSzSrchResult.
         
         If the value specified is 'execute(2)' and the
         tmnxCohOptPortCprWnSzSrchStatus is 'inProgress(2)', the action will be
         rejected with an error status of inconsistentValue.
         
         In an SNNP get response, tmnxCohOptPortCprWinSizeSearch will have a
         value of 'noCmd(1)'.";
      smiv2:defval "noCmd";
      smiv2:max-access "read-write";
      smiv2:oid "1.3.6.1.4.1.6527.3.1.2.2.4.72.1.1";
      config true;
    }
    leaf tmnxCohOptPortCprWnSzSrchStatus {
      type enumeration {
        enum "none" {
          value 1;
        }
        enum "requested" {
          value 2;
        }
        enum "starting" {
          value 3;
        }
        enum "inProgress" {
          value 4;
        }
        enum "succeeded" {
          value 5;
        }
        enum "failed" {
          value 6;
        }
      }
      description
        "The value of tmnxCohOptPortCprWnSzSrchStatus indicates the status of
         the last search for the CPR optimal window size, executed by
         tmnxCohOptPortCprWinSizeSearch with a value of 'execute(2)'.
         
         The value will be 'none(1)' if no search has been performed since the
         last system startup or since the last reset of the associated MDA or
         IOM.
         
         The value will be 'requested(2)' if the search was requested by the
         user but has not started because the tmnxCohOptPortModState is not
         'ready(8)'.
         
         The value will be 'starting(3)' if the search was requested and the
         tmnxCohOptPortModRxTurnUpStates has not achieved 'adcSignal'.
         
         The value will be 'inProgress(4)' if the search is in progress.
         
         The value will be 'succeeded(5)' if the search has completed
         successfully.
         
         The value will be 'failed(6)' if the search has completed with
         a failure.";
      smiv2:max-access "read-only";
      smiv2:oid "1.3.6.1.4.1.6527.3.1.2.2.4.72.1.2";
      config false;
    }
    leaf tmnxCohOptPortCprWnSzSrchResult {
      type uint32;
      units "symbols";
      description
        "The value of tmnxCohOptPortCprWnSzSrchResult indicates the CPR
         optimal window size found on the last search for the CPR optimal
         window size, executed by tmnxCohOptPortCprWinSizeSearch with a value
         of 'execute(2)'. The value of tmnxCohOptPortCprWnSzSrchResult may not
         be equivalent to what is configured for tmnxCohOptPortCfgCprWinSize.
         
         The tmnxCohOptPortCprWnSzSrchResult value of 0 indicates that no CPR
         optimal window size was found.";
      smiv2:max-access "read-only";
      smiv2:oid "1.3.6.1.4.1.6527.3.1.2.2.4.72.1.3";
      config false;
    }
  }
  smiv2:alias "tmnxCiscoHDLCStatsTable" {
    description
      "The tmnxCiscoHDLCStatsTable has an entry for each port in the
       system that is configured for Cisco HDLC encapsulation. It contains
       Cisco HDLC protocol statistics for the particular port.";
    smiv2:oid "1.3.6.1.4.1.6527.3.1.2.2.12.3";
  }
  smiv2:alias "tmnxCiscoHDLCStatsEntry" {
    description
      "An entry in the tmnxCiscoHDLCStatsTable.";
    smiv2:oid "1.3.6.1.4.1.6527.3.1.2.2.12.3.1";
  }

  augment "/timetra-port:TIMETRA-PORT-MIB/timetra-port:tmnxCiscoHDLCTable/timetra-port:tmnxCiscoHDLCEntry" {
    description
      "An entry in the tmnxCiscoHDLCStatsTable.";
    smiv2:oid "1.3.6.1.4.1.6527.3.1.2.2.12.3.1";
    leaf tmnxCiscoHDLCDiscardStatInPkts {
      type uint32;
      description
        "tmnxCiscoHDLCDiscardStatInPkts indicates the number of
         inbound Cisco HDLC packets discarded.";
      smiv2:max-access "read-only";
      smiv2:oid "1.3.6.1.4.1.6527.3.1.2.2.12.3.1.1";
      config false;
    }
    leaf tmnxCiscoHDLCDiscardStatOutPkts {
      type uint32;
      description
        "tmnxCiscoHDLCDiscardStatOutPkts indicates the number of
         outbound Cisco HDLC packets discarded.";
      smiv2:max-access "read-only";
      smiv2:oid "1.3.6.1.4.1.6527.3.1.2.2.12.3.1.2";
      config false;
    }
    leaf tmnxCiscoHDLCStatInPkts {
      type uint32;
      description
        "tmnxCiscoHDLCStatInPkts indicates the number of inbound Cisco
         HDLC packets.";
      smiv2:max-access "read-only";
      smiv2:oid "1.3.6.1.4.1.6527.3.1.2.2.12.3.1.3";
      config false;
    }
    leaf tmnxCiscoHDLCStatOutPkts {
      type uint32;
      description
        "tmnxCiscoHDLCStatOutPkts indicates the number of outbound Cisco
         HDLC packets.";
      smiv2:max-access "read-only";
      smiv2:oid "1.3.6.1.4.1.6527.3.1.2.2.12.3.1.4";
      config false;
    }
    leaf tmnxCiscoHDLCStatInOctets {
      type uint32;
      description
        "tmnxCiscoHDLCStatInOctets indicates the number of inbound Cisco
         HDLC octets.";
      smiv2:max-access "read-only";
      smiv2:oid "1.3.6.1.4.1.6527.3.1.2.2.12.3.1.5";
      config false;
    }
    leaf tmnxCiscoHDLCStatOutOctets {
      type uint32;
      description
        "tmnxCiscoHDLCStatOutOctets indicates the number of outbound
         Cisco HDLC octets.";
      smiv2:max-access "read-only";
      smiv2:oid "1.3.6.1.4.1.6527.3.1.2.2.12.3.1.6";
      config false;
    }
  }
  notification tmnxEqOobPortFailure {
    status obsolete;
    description
      "Generated when the out-of-band Ethernet port has failed.  On the
       Alcatel-Lucent SROS system, the out-of-band port is the CPM management
       interface.
       
       This notification was made obsolete in the 2.1 release.
       
       The Out-of-band, OOB, port is what id refered to as the
       management port or cpm port.  It has an entry in ifTable
       and linkup, linkDown and tmnxEqPortError notifications
       are sent for the management port just as for any other
       port in the system.";
    smiv2:oid "1.3.6.1.4.1.6527.3.1.3.2.2.0.1";
    container object-1 {
      leaf tmnxChassisNotifyChassisId {
        type timetra-chassis:TmnxChassisIndex;
        description
          "Used by tmnx chassis and port Notifications, indicates the chassis
           associated with the alarm.";
        smiv2:max-access "accessible-for-notify";
        smiv2:oid "1.3.6.1.4.1.6527.3.1.2.2.6.3";
      }
    }
    container object-2 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
  }
  notification tmnxEqPortFailure {
    status obsolete;
    description
      "Generated when a port has failed.
       
       This notification was made obsolete in the 2.1 release.
       
       tmnxEqPortError is used instead of tmnxEqPortFailure.
       
       Standard IETF linkDown notification is sent when a
       physical port failure is detected.  tmnxEqPortError is
       sent with a ASCII reason message when port errors are
       detected.
       
       It was originally intended that tmnxEqPortError be used
       to report errors that do not cause port state change to
       'down'.
       
       tmnxEqPortFailure was intended to report errors that
       do cause the port state change to 'down'.
       
       However, in the implementation tmnxEqPortError is used
       for both fatal and non-fatal errors.";
    smiv2:oid "1.3.6.1.4.1.6527.3.1.3.2.2.0.2";
    container object-1 {
      leaf tmnxChassisNotifyChassisId {
        type timetra-chassis:TmnxChassisIndex;
        description
          "Used by tmnx chassis and port Notifications, indicates the chassis
           associated with the alarm.";
        smiv2:max-access "accessible-for-notify";
        smiv2:oid "1.3.6.1.4.1.6527.3.1.2.2.6.3";
      }
    }
    container object-2 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
  }
  notification tmnxQosServiceDegraded {
    status obsolete;
    description
      "Generated when the port is unable to provided the specified
       quality of service level.";
    smiv2:oid "1.3.6.1.4.1.6527.3.1.3.2.2.0.3";
    container object-1 {
      leaf tmnxChassisNotifyChassisId {
        type timetra-chassis:TmnxChassisIndex;
        description
          "Used by tmnx chassis and port Notifications, indicates the chassis
           associated with the alarm.";
        smiv2:max-access "accessible-for-notify";
        smiv2:oid "1.3.6.1.4.1.6527.3.1.2.2.6.3";
      }
    }
    container object-2 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
  }
  notification tmnxEqPortSonetAlarm {
    description
      "Generated when a SONET/SDH port alarm condition is detected.
       It is generated only when the type of alarm being raised is enabled
       in tmnxSonetReportAlarm.";
    smiv2:oid "1.3.6.1.4.1.6527.3.1.3.2.2.0.4";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
    container object-2 {
      leaf tmnxPortNotifySonetAlarmReason {
        type enumeration {
          enum "notUsed" {
            value 0;
          }
          enum "loc" {
            value 1;
          }
          enum "lais" {
            value 2;
          }
          enum "lrdi" {
            value 3;
          }
          enum "ss1f" {
            value 4;
          }
          enum "sb1err" {
            value 5;
          }
          enum "lb2erSd" {
            value 6;
          }
          enum "lb2erSf" {
            value 7;
          }
          enum "slof" {
            value 8;
          }
          enum "slos" {
            value 9;
          }
          enum "stxptr" {
            value 10;
          }
          enum "srxptr" {
            value 11;
          }
          enum "lrei" {
            value 12;
          }
        }
        description
          "Used by tmnx sonet Port Notifications, the value of
           tmnxPortNotifySonetAlarmReason indicates the reason a sonet port
           alarm has been raised.";
        smiv2:max-access "accessible-for-notify";
        smiv2:oid "1.3.6.1.4.1.6527.3.1.2.2.7.2";
      }
    }
  }
  notification tmnxEqPortSonetAlarmClear {
    description
      "Generated when a SONET/SDH port alarm condition is cleared.
       It is generated only when the type of alarm being cleared is enabled
       in tmnxSonetReportAlarm.";
    smiv2:oid "1.3.6.1.4.1.6527.3.1.3.2.2.0.5";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
    container object-2 {
      leaf tmnxPortNotifySonetAlarmReason {
        type enumeration {
          enum "notUsed" {
            value 0;
          }
          enum "loc" {
            value 1;
          }
          enum "lais" {
            value 2;
          }
          enum "lrdi" {
            value 3;
          }
          enum "ss1f" {
            value 4;
          }
          enum "sb1err" {
            value 5;
          }
          enum "lb2erSd" {
            value 6;
          }
          enum "lb2erSf" {
            value 7;
          }
          enum "slof" {
            value 8;
          }
          enum "slos" {
            value 9;
          }
          enum "stxptr" {
            value 10;
          }
          enum "srxptr" {
            value 11;
          }
          enum "lrei" {
            value 12;
          }
        }
        description
          "Used by tmnx sonet Port Notifications, the value of
           tmnxPortNotifySonetAlarmReason indicates the reason a sonet port
           alarm has been raised.";
        smiv2:max-access "accessible-for-notify";
        smiv2:oid "1.3.6.1.4.1.6527.3.1.2.2.7.2";
      }
    }
  }
  notification tmnxEqPortSonetPathAlarm {
    description
      "Generated when a SONET/SDH path alarm condition is detected.
       It is generated only when the type of alarm being raised is enabled
       in tmnxSonetPathReportAlarm.";
    smiv2:oid "1.3.6.1.4.1.6527.3.1.3.2.2.0.6";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
    container object-2 {
      leaf tmnxPortNotifySonetPathAlarmReason {
        type enumeration {
          enum "notUsed" {
            value 0;
          }
          enum "pais" {
            value 1;
          }
          enum "plop" {
            value 2;
          }
          enum "prdi" {
            value 3;
          }
          enum "pb3err" {
            value 4;
          }
          enum "pplm" {
            value 5;
          }
          enum "prei" {
            value 6;
          }
          enum "puneq" {
            value 7;
          }
          enum "plcd" {
            value 8;
          }
        }
        description
          "Used by tmnx sonet path Notifications, the value of
           tmnxPortNotifySonetPathAlarmReason indicates the reason a sonet path
           alarm has been raised.";
        smiv2:max-access "accessible-for-notify";
        smiv2:oid "1.3.6.1.4.1.6527.3.1.2.2.7.3";
      }
    }
  }
  notification tmnxEqPortSonetPathAlarmClear {
    description
      "Generated when a SONET/SDH path alarm condition is cleared.
       It is generated only when the type of alarm being cleared is enabled
       in tmnxSonetPathReportAlarm.";
    smiv2:oid "1.3.6.1.4.1.6527.3.1.3.2.2.0.7";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
    container object-2 {
      leaf tmnxPortNotifySonetPathAlarmReason {
        type enumeration {
          enum "notUsed" {
            value 0;
          }
          enum "pais" {
            value 1;
          }
          enum "plop" {
            value 2;
          }
          enum "prdi" {
            value 3;
          }
          enum "pb3err" {
            value 4;
          }
          enum "pplm" {
            value 5;
          }
          enum "prei" {
            value 6;
          }
          enum "puneq" {
            value 7;
          }
          enum "plcd" {
            value 8;
          }
        }
        description
          "Used by tmnx sonet path Notifications, the value of
           tmnxPortNotifySonetPathAlarmReason indicates the reason a sonet path
           alarm has been raised.";
        smiv2:max-access "accessible-for-notify";
        smiv2:oid "1.3.6.1.4.1.6527.3.1.2.2.7.3";
      }
    }
  }
  notification tmnxEqPortSFPInserted {
    description
      "Generated when an SFF is inserted in the port.";
    smiv2:oid "1.3.6.1.4.1.6527.3.1.3.2.2.0.8";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
  }
  notification tmnxEqPortSFPRemoved {
    description
      "Generated when an SFF is removed from the port.";
    smiv2:oid "1.3.6.1.4.1.6527.3.1.3.2.2.0.9";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
  }
  notification tmnxEqPortWrongSFP {
    status obsolete;
    description
      "Generated when a wrong type of SFF optics module
       is plugged into a 1 Gig MDA, SONET MDA, or 100FX MDA.
       
       Because of the large variety of SFFs now supported and
       their different encoding schemes for compliance bits, the
       check for wrong SFF has been removed. As a result,
       tmnxEqPortWrongSFP notification is no longer generated.
       
       However, wrong SFF can be inferred from port statistics.";
    smiv2:oid "1.3.6.1.4.1.6527.3.1.3.2.2.0.10";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
  }
  notification tmnxEqPortSFPCorrupted {
    status obsolete;
    description
      "Generated when SFF information stored in the EPROM
       on the SFF is corrupt. This notification was made
       obsolete for revision 6.0 on Alcatel-Lucent SROS series
       systems; it was replaced by tmnxEqPortSFPStatusFailure.";
    smiv2:oid "1.3.6.1.4.1.6527.3.1.3.2.2.0.11";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
  }
  notification tmnxPortNotifyBerSdTca {
    status obsolete;
    description
      "Generated when a SONET/SDH port's signal degradation bit error
       rate is greater than the configured error rate threshold.
       
       This notification was made obsolete in the 2.1 release.";
    smiv2:oid "1.3.6.1.4.1.6527.3.1.3.2.2.0.12";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
    container object-2 {
      leaf tmnxChassisIndex {
        type leafref {
          path "/timetra-chassis:TIMETRA-CHASSIS-MIB/timetra-chassis:tmnxChassisTable/timetra-chassis:tmnxChassisEntry/timetra-chassis:tmnxChassisIndex";
        }
      }
      leaf tmnxPortPortID {
        type leafref {
          path "/timetra-port:TIMETRA-PORT-MIB/timetra-port:tmnxPortTable/timetra-port:tmnxPortEntry/timetra-port:tmnxPortPortID";
        }
      }
      leaf tmnxSonetBerSdThreshold {
        type leafref {
          path "/timetra-port:TIMETRA-PORT-MIB/timetra-port:tmnxSonetTable/timetra-port:tmnxSonetEntry/timetra-port:tmnxSonetBerSdThreshold";
        }
      }
    }
  }
  notification tmnxPortNotifyBerSfTca {
    status obsolete;
    description
      "Generated when a SONET/SDH port's signal failure bit error
       rate is greater than the configured error rate threshold.
       
       This notification was made obsolete in the 2.1 release.";
    smiv2:oid "1.3.6.1.4.1.6527.3.1.3.2.2.0.13";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
    container object-2 {
      leaf tmnxChassisIndex {
        type leafref {
          path "/timetra-chassis:TIMETRA-CHASSIS-MIB/timetra-chassis:tmnxChassisTable/timetra-chassis:tmnxChassisEntry/timetra-chassis:tmnxChassisIndex";
        }
      }
      leaf tmnxPortPortID {
        type leafref {
          path "/timetra-port:TIMETRA-PORT-MIB/timetra-port:tmnxPortTable/timetra-port:tmnxPortEntry/timetra-port:tmnxPortPortID";
        }
      }
      leaf tmnxSonetBerSfThreshold {
        type leafref {
          path "/timetra-port:TIMETRA-PORT-MIB/timetra-port:tmnxSonetTable/timetra-port:tmnxSonetEntry/timetra-port:tmnxSonetBerSfThreshold";
        }
      }
    }
  }
  notification tmnxEqPortError {
    description
      "Generated when an error listed in tmnxPortNotifyError
       is detected on the port.";
    smiv2:oid "1.3.6.1.4.1.6527.3.1.3.2.2.0.14";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
    container object-2 {
      leaf tmnxPortNotifyError {
        type enumeration {
          enum "txClockError" {
            value 1;
          }
          enum "rxClockError" {
            value 2;
          }
          enum "txFifoError" {
            value 3;
          }
          enum "laserError" {
            value 4;
          }
          enum "miscError" {
            value 5;
          }
        }
        description
          "Used by tmnxEqPortError notification, the value of
           tmnxPortNotifyError indicates the reason a port has
           an error.";
        smiv2:max-access "accessible-for-notify";
        smiv2:oid "1.3.6.1.4.1.6527.3.1.2.2.7.4";
      }
    }
  }
  notification tmnxEqPortDS3Alarm {
    description
      "Generated when a DS3 interface alarm condition is detected.
       It is generated only when the type of alarm being raised is enabled
       in tmnxDS3ChannelReportAlarm.";
    smiv2:oid "1.3.6.1.4.1.6527.3.1.3.2.2.0.15";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
    container object-2 {
      leaf tmnxPortNotifyDS3AlarmReason {
        type enumeration {
          enum "notUsed" {
            value 0;
          }
          enum "ais" {
            value 1;
          }
          enum "los" {
            value 2;
          }
          enum "oof" {
            value 3;
          }
          enum "rai" {
            value 4;
          }
          enum "looped" {
            value 5;
          }
        }
        description
          "Used by tmnx DS3 Port Notifications, the value of
           tmnxPortNotifyDS3AlarmReason indicates the reason a DS3 interface
           alarm has been raised.";
        smiv2:max-access "accessible-for-notify";
        smiv2:oid "1.3.6.1.4.1.6527.3.1.2.2.7.5";
      }
    }
  }
  notification tmnxEqPortDS3AlarmClear {
    description
      "Generated when a DS3 interface alarm condition is cleared.
       It is generated only when the type of alarm being cleared is enabled
       in tmnxDS3ChannelReportAlarm.";
    smiv2:oid "1.3.6.1.4.1.6527.3.1.3.2.2.0.16";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
    container object-2 {
      leaf tmnxPortNotifyDS3AlarmReason {
        type enumeration {
          enum "notUsed" {
            value 0;
          }
          enum "ais" {
            value 1;
          }
          enum "los" {
            value 2;
          }
          enum "oof" {
            value 3;
          }
          enum "rai" {
            value 4;
          }
          enum "looped" {
            value 5;
          }
        }
        description
          "Used by tmnx DS3 Port Notifications, the value of
           tmnxPortNotifyDS3AlarmReason indicates the reason a DS3 interface
           alarm has been raised.";
        smiv2:max-access "accessible-for-notify";
        smiv2:oid "1.3.6.1.4.1.6527.3.1.2.2.7.5";
      }
    }
  }
  notification tmnxEqPortDS1Alarm {
    description
      "Generated when a DS1 interface alarm condition is detected.
       It is generated only when the type of alarm being raised is enabled
       in tmnxDS1ReportAlarm.";
    smiv2:oid "1.3.6.1.4.1.6527.3.1.3.2.2.0.17";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
    container object-2 {
      leaf tmnxPortNotifyDS1AlarmReason {
        type enumeration {
          enum "notUsed" {
            value 0;
          }
          enum "ais" {
            value 1;
          }
          enum "los" {
            value 2;
          }
          enum "oof" {
            value 3;
          }
          enum "rai" {
            value 4;
          }
          enum "looped" {
            value 5;
          }
          enum "berSd" {
            value 6;
          }
          enum "berSf" {
            value 7;
          }
        }
        description
          "Used by tmnx DS1 Port Notifications, the value of
           tmnxPortNotifyDS1AlarmReason indicates the reason a DS1 interface
           alarm has been raised.";
        smiv2:max-access "accessible-for-notify";
        smiv2:oid "1.3.6.1.4.1.6527.3.1.2.2.7.6";
      }
    }
  }
  notification tmnxEqPortDS1AlarmClear {
    description
      "Generated when a DS1 interface alarm condition is cleared.
       It is generated only when the type of alarm being cleared is enabled
       in tmnxDS1ReportAlarm.";
    smiv2:oid "1.3.6.1.4.1.6527.3.1.3.2.2.0.18";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
    container object-2 {
      leaf tmnxPortNotifyDS1AlarmReason {
        type enumeration {
          enum "notUsed" {
            value 0;
          }
          enum "ais" {
            value 1;
          }
          enum "los" {
            value 2;
          }
          enum "oof" {
            value 3;
          }
          enum "rai" {
            value 4;
          }
          enum "looped" {
            value 5;
          }
          enum "berSd" {
            value 6;
          }
          enum "berSf" {
            value 7;
          }
        }
        description
          "Used by tmnx DS1 Port Notifications, the value of
           tmnxPortNotifyDS1AlarmReason indicates the reason a DS1 interface
           alarm has been raised.";
        smiv2:max-access "accessible-for-notify";
        smiv2:oid "1.3.6.1.4.1.6527.3.1.2.2.7.6";
      }
    }
  }
  notification tmnxEqPortBndlYellowDiffExceeded {
    description
      "Generated when the differential delay of a port in the bundle
       exceeds the configured value in tmnxBundleYellowDiffDelay.";
    smiv2:oid "1.3.6.1.4.1.6527.3.1.3.2.2.0.19";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
    container object-2 {
      leaf tmnxChassisIndex {
        type leafref {
          path "/timetra-chassis:TIMETRA-CHASSIS-MIB/timetra-chassis:tmnxChassisTable/timetra-chassis:tmnxChassisEntry/timetra-chassis:tmnxChassisIndex";
        }
      }
      leaf tmnxBundleBundleID {
        type leafref {
          path "/timetra-port:TIMETRA-PORT-MIB/timetra-port:tmnxBundleTable/timetra-port:tmnxBundleEntry/timetra-port:tmnxBundleBundleID";
        }
      }
      leaf tmnxBundleYellowDiffDelay {
        type leafref {
          path "/timetra-port:TIMETRA-PORT-MIB/timetra-port:tmnxBundleTable/timetra-port:tmnxBundleEntry/timetra-port:tmnxBundleYellowDiffDelay";
        }
      }
    }
  }
  notification tmnxEqPortBndlRedDiffExceeded {
    description
      "Generated when the differential delay of a port in the bundle
       exceeds the configured value in tmnxBundleRedDiffDelay.";
    smiv2:oid "1.3.6.1.4.1.6527.3.1.3.2.2.0.20";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
    container object-2 {
      leaf tmnxChassisIndex {
        type leafref {
          path "/timetra-chassis:TIMETRA-CHASSIS-MIB/timetra-chassis:tmnxChassisTable/timetra-chassis:tmnxChassisEntry/timetra-chassis:tmnxChassisIndex";
        }
      }
      leaf tmnxBundleBundleID {
        type leafref {
          path "/timetra-port:TIMETRA-PORT-MIB/timetra-port:tmnxBundleTable/timetra-port:tmnxBundleEntry/timetra-port:tmnxBundleBundleID";
        }
      }
      leaf tmnxBundleRedDiffDelay {
        type leafref {
          path "/timetra-port:TIMETRA-PORT-MIB/timetra-port:tmnxBundleTable/timetra-port:tmnxBundleEntry/timetra-port:tmnxBundleRedDiffDelay";
        }
      }
    }
  }
  notification tmnxEqPortBndlBadEndPtDiscr {
    description
      "Generated when the port detected mismatched peer endpoint
       discriminator for the bundle.";
    smiv2:oid "1.3.6.1.4.1.6527.3.1.3.2.2.0.21";
    container object-1 {
      leaf tmnxBundleBundleID {
        type leafref {
          path "/timetra-port:TIMETRA-PORT-MIB/timetra-port:tmnxBundleTable/timetra-port:tmnxBundleEntry/timetra-port:tmnxBundleBundleID";
        }
      }
      leaf tmnxPortPortID {
        type leafref {
          path "/timetra-port:TIMETRA-PORT-MIB/timetra-port:tmnxPortTable/timetra-port:tmnxPortEntry/timetra-port:tmnxPortPortID";
        }
      }
      leaf tmnxBundleMemberDownReason {
        type leafref {
          path "/timetra-port:TIMETRA-PORT-MIB/timetra-port:tmnxBundleMemberTable/timetra-port:tmnxBundleMemberEntry/timetra-port:tmnxBundleMemberDownReason";
        }
      }
    }
  }
  notification tmnxEqPortEtherAlarm {
    description
      "tmnxEqPortEtherAlarm is generated when a ethernet port alarm
       condition is detected. It is generated only when the type of
       alarm being raised is enabled in tmnxPortEtherReportAlarm.";
    smiv2:oid "1.3.6.1.4.1.6527.3.1.3.2.2.0.22";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
    container object-2 {
      leaf tmnxPortNotifyEtherAlarmReason {
        type timetra-port:TmnxPortEtherReportValue;
        description
          "Used by tmnx ethernet Port Notifications, the value of
           tmnxPortNotifyEtherAlarmReason indicates the reason a ethernet port
           alarm has been raised.";
        smiv2:max-access "accessible-for-notify";
        smiv2:oid "1.3.6.1.4.1.6527.3.1.2.2.7.8";
      }
    }
  }
  notification tmnxEqPortEtherAlarmClear {
    description
      "tmnxEqPortEtherAlarmClear is generated when a ethernet port alarm
       condition is cleared. It is generated only when the type of alarm
       being cleared is enabled in tmnxPortEtherReportAlarm.";
    smiv2:oid "1.3.6.1.4.1.6527.3.1.3.2.2.0.23";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
    container object-2 {
      leaf tmnxPortNotifyEtherAlarmReason {
        type timetra-port:TmnxPortEtherReportValue;
        description
          "Used by tmnx ethernet Port Notifications, the value of
           tmnxPortNotifyEtherAlarmReason indicates the reason a ethernet port
           alarm has been raised.";
        smiv2:max-access "accessible-for-notify";
        smiv2:oid "1.3.6.1.4.1.6527.3.1.2.2.7.8";
      }
    }
  }
  notification tmnxDS1E1LoopbackStarted {
    description
      "The tmnxDS1E1LoopbackStarted notification is generated when a
       loopback is provisioned on a DS1/E1 port.";
    smiv2:oid "1.3.6.1.4.1.6527.3.1.3.2.2.0.24";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
    container object-2 {
      leaf tmnxChassisIndex {
        type leafref {
          path "/timetra-chassis:TIMETRA-CHASSIS-MIB/timetra-chassis:tmnxChassisTable/timetra-chassis:tmnxChassisEntry/timetra-chassis:tmnxChassisIndex";
        }
      }
      leaf tmnxPortPortID {
        type leafref {
          path "/timetra-port:TIMETRA-PORT-MIB/timetra-port:tmnxPortTable/timetra-port:tmnxPortEntry/timetra-port:tmnxPortPortID";
        }
      }
      leaf tmnxDS1Loopback {
        type leafref {
          path "/timetra-port:TIMETRA-PORT-MIB/timetra-port:tmnxDS1Table/timetra-port:tmnxDS1Entry/timetra-port:tmnxDS1Loopback";
        }
      }
    }
  }
  notification tmnxDS1E1LoopbackStopped {
    description
      "The tmnxDS1E1LoopbackStopped notification is generated when a
       loopback is removed on a DS1/E1 port. The value of
       tmnxSonetLoopback specifies the type of loopback that was
       configured and has now been removed.";
    smiv2:oid "1.3.6.1.4.1.6527.3.1.3.2.2.0.25";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
    container object-2 {
      leaf tmnxChassisIndex {
        type leafref {
          path "/timetra-chassis:TIMETRA-CHASSIS-MIB/timetra-chassis:tmnxChassisTable/timetra-chassis:tmnxChassisEntry/timetra-chassis:tmnxChassisIndex";
        }
      }
      leaf tmnxPortPortID {
        type leafref {
          path "/timetra-port:TIMETRA-PORT-MIB/timetra-port:tmnxPortTable/timetra-port:tmnxPortEntry/timetra-port:tmnxPortPortID";
        }
      }
      leaf tmnxDS1Loopback {
        type leafref {
          path "/timetra-port:TIMETRA-PORT-MIB/timetra-port:tmnxDS1Table/timetra-port:tmnxDS1Entry/timetra-port:tmnxDS1Loopback";
        }
      }
    }
  }
  notification tmnxDS3E3LoopbackStarted {
    description
      "The tmnxDS3E3LoopbackStarted notification is generated when a
       loopback is provisioned on a DS3/E3 port.";
    smiv2:oid "1.3.6.1.4.1.6527.3.1.3.2.2.0.26";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
    container object-2 {
      leaf tmnxChassisIndex {
        type leafref {
          path "/timetra-chassis:TIMETRA-CHASSIS-MIB/timetra-chassis:tmnxChassisTable/timetra-chassis:tmnxChassisEntry/timetra-chassis:tmnxChassisIndex";
        }
      }
      leaf tmnxPortPortID {
        type leafref {
          path "/timetra-port:TIMETRA-PORT-MIB/timetra-port:tmnxPortTable/timetra-port:tmnxPortEntry/timetra-port:tmnxPortPortID";
        }
      }
      leaf tmnxDS3ChannelLoopback {
        type leafref {
          path "/timetra-port:TIMETRA-PORT-MIB/timetra-port:tmnxDS3ChannelTable/timetra-port:tmnxDS3ChannelEntry/timetra-port:tmnxDS3ChannelLoopback";
        }
      }
    }
  }
  notification tmnxDS3E3LoopbackStopped {
    description
      "The tmnxDS3E3LoopbackStopped notification is generated when a
       loopback is removed on a DS3/E3 port. The value of
       tmnxDS3ChannelLoopback specifies the type of loopback that was
       configured and has now been removed.";
    smiv2:oid "1.3.6.1.4.1.6527.3.1.3.2.2.0.27";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
    container object-2 {
      leaf tmnxChassisIndex {
        type leafref {
          path "/timetra-chassis:TIMETRA-CHASSIS-MIB/timetra-chassis:tmnxChassisTable/timetra-chassis:tmnxChassisEntry/timetra-chassis:tmnxChassisIndex";
        }
      }
      leaf tmnxPortPortID {
        type leafref {
          path "/timetra-port:TIMETRA-PORT-MIB/timetra-port:tmnxPortTable/timetra-port:tmnxPortEntry/timetra-port:tmnxPortPortID";
        }
      }
      leaf tmnxDS3ChannelLoopback {
        type leafref {
          path "/timetra-port:TIMETRA-PORT-MIB/timetra-port:tmnxDS3ChannelTable/timetra-port:tmnxDS3ChannelEntry/timetra-port:tmnxDS3ChannelLoopback";
        }
      }
    }
  }
  notification tmnxSonetSDHLoopbackStarted {
    description
      "The tmnxSonetSDHLoopbackStarted notification is generated when a
       loopback is provisioned on a Sonet-SDH port.";
    smiv2:oid "1.3.6.1.4.1.6527.3.1.3.2.2.0.28";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
    container object-2 {
      leaf tmnxChassisIndex {
        type leafref {
          path "/timetra-chassis:TIMETRA-CHASSIS-MIB/timetra-chassis:tmnxChassisTable/timetra-chassis:tmnxChassisEntry/timetra-chassis:tmnxChassisIndex";
        }
      }
      leaf tmnxPortPortID {
        type leafref {
          path "/timetra-port:TIMETRA-PORT-MIB/timetra-port:tmnxPortTable/timetra-port:tmnxPortEntry/timetra-port:tmnxPortPortID";
        }
      }
      leaf tmnxSonetLoopback {
        type leafref {
          path "/timetra-port:TIMETRA-PORT-MIB/timetra-port:tmnxSonetTable/timetra-port:tmnxSonetEntry/timetra-port:tmnxSonetLoopback";
        }
      }
    }
  }
  notification tmnxSonetSDHLoopbackStopped {
    description
      "The tmnxSonetSDHLoopbackStopped notification is generated when a
       loopback test is removed on a Sonet-SDH port. The value of
       tmnxDS1Loopback specifies the type of loopback that was
       configured and has now been removed.";
    smiv2:oid "1.3.6.1.4.1.6527.3.1.3.2.2.0.29";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
    container object-2 {
      leaf tmnxChassisIndex {
        type leafref {
          path "/timetra-chassis:TIMETRA-CHASSIS-MIB/timetra-chassis:tmnxChassisTable/timetra-chassis:tmnxChassisEntry/timetra-chassis:tmnxChassisIndex";
        }
      }
      leaf tmnxPortPortID {
        type leafref {
          path "/timetra-port:TIMETRA-PORT-MIB/timetra-port:tmnxPortTable/timetra-port:tmnxPortEntry/timetra-port:tmnxPortPortID";
        }
      }
      leaf tmnxSonetLoopback {
        type leafref {
          path "/timetra-port:TIMETRA-PORT-MIB/timetra-port:tmnxSonetTable/timetra-port:tmnxSonetEntry/timetra-port:tmnxSonetLoopback";
        }
      }
    }
  }
  notification tmnxEqPortEtherLoopDetected {
    description
      "The tmnxEqPortEtherLoopDetected notification is genereated when
       down-when-looped detects an Ethernet port is receiving PDUs that
       it transmitted and tmnxPortEtherDownWhenLoopedEnabled is set to
       'true'.";
    smiv2:oid "1.3.6.1.4.1.6527.3.1.3.2.2.0.30";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
  }
  notification tmnxEqPortEtherLoopCleared {
    description
      "The tmnxEqPortEtherLoopCleared notification is generated when
       down-when-looped detects an Ethernet port has stopped receiving
       PDUs that it transmitted and tmnxPortEtherDownWhenLoopedEnabled
       is set to 'true'.  Setting tmnxPortEtherDownWhenLoopedEnabled to
       'false' will also cause this notification to be generated if
       tmnxEqPortEtherLoopDetected had previously been raised.";
    smiv2:oid "1.3.6.1.4.1.6527.3.1.3.2.2.0.31";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
  }
  notification tmnxEqPortSpeedCfgNotCompatible {
    description
      "Generated when a configured speed on an MDA port is not
       compatible with the MDA type.
       
       [EFFECT] Though services can still be created, if the tmnxMdaNotifyType
       is the same as the tmnxMDAEquippedType then the MDA will fail to
       operate as configured and will be in a failed state.
       
       [RECOVERY] Change the configuration to reflect the capabilities of the
       MDA port, or switch out/re-provision the MDA for one that is
       compatible.";
    smiv2:oid "1.3.6.1.4.1.6527.3.1.3.2.2.0.32";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
    container object-2 {
      leaf tmnxChassisIndex {
        type leafref {
          path "/timetra-chassis:TIMETRA-CHASSIS-MIB/timetra-chassis:tmnxChassisTable/timetra-chassis:tmnxChassisEntry/timetra-chassis:tmnxChassisIndex";
        }
      }
      leaf tmnxPortPortID {
        type leafref {
          path "/timetra-port:TIMETRA-PORT-MIB/timetra-port:tmnxPortTable/timetra-port:tmnxPortEntry/timetra-port:tmnxPortPortID";
        }
      }
      leaf tmnxPortEtherSpeed {
        type leafref {
          path "/timetra-port:TIMETRA-PORT-MIB/timetra-port:tmnxPortEtherTable/timetra-port:tmnxPortEtherEntry/timetra-port:tmnxPortEtherSpeed";
        }
      }
    }
    container object-3 {
      leaf tmnxMdaNotifyType {
        type timetra-chassis:TmnxMdaType;
        description
          "Used by equipment alarms where the type of MDA isn't supported with
           the current configuration.";
        smiv2:max-access "accessible-for-notify";
        smiv2:oid "1.3.6.1.4.1.6527.3.1.2.2.6.16";
      }
    }
  }
  notification tmnxEqPortDuplexCfgNotCompatible {
    description
      "Generated when a configured duplex on an MDA port is not
       compatible with the MDA type.
       
       [EFFECT] Though services can still be created, if the tmnxMdaNotifyType
       is the same as the tmnxMDAEquippedType then the MDA will fail to
       operate as configured and will be in a failed state.
       
       [RECOVERY] Change the configuration to reflect the capabilities of the
       MDA port, or switch out/re-provision the MDA for one that is
       compatible.";
    smiv2:oid "1.3.6.1.4.1.6527.3.1.3.2.2.0.33";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
    container object-2 {
      leaf tmnxChassisIndex {
        type leafref {
          path "/timetra-chassis:TIMETRA-CHASSIS-MIB/timetra-chassis:tmnxChassisTable/timetra-chassis:tmnxChassisEntry/timetra-chassis:tmnxChassisIndex";
        }
      }
      leaf tmnxPortPortID {
        type leafref {
          path "/timetra-port:TIMETRA-PORT-MIB/timetra-port:tmnxPortTable/timetra-port:tmnxPortEntry/timetra-port:tmnxPortPortID";
        }
      }
      leaf tmnxPortEtherDuplex {
        type leafref {
          path "/timetra-port:TIMETRA-PORT-MIB/timetra-port:tmnxPortEtherTable/timetra-port:tmnxPortEtherEntry/timetra-port:tmnxPortEtherDuplex";
        }
      }
    }
    container object-3 {
      leaf tmnxMdaNotifyType {
        type timetra-chassis:TmnxMdaType;
        description
          "Used by equipment alarms where the type of MDA isn't supported with
           the current configuration.";
        smiv2:max-access "accessible-for-notify";
        smiv2:oid "1.3.6.1.4.1.6527.3.1.2.2.6.16";
      }
    }
  }
  notification tmnxEqPortIngressRateCfgNotCompatible {
    description
      "Generated when a configured ingress rate on an MDA port is not
       compatible with the MDA type.
       
       [EFFECT] Though services can still be created, if the tmnxMdaNotifyType
       is the same as the tmnxMDAEquippedType then the MDA will fail to
       operate as configured and will be in a failed state.
       
       [RECOVERY] Change the configuration to reflect the capabilities of the
       MDA port, or switch out/re-provision the MDA for one that is
       compatible.";
    smiv2:oid "1.3.6.1.4.1.6527.3.1.3.2.2.0.34";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
    container object-2 {
      leaf tmnxMdaNotifyType {
        type timetra-chassis:TmnxMdaType;
        description
          "Used by equipment alarms where the type of MDA isn't supported with
           the current configuration.";
        smiv2:max-access "accessible-for-notify";
        smiv2:oid "1.3.6.1.4.1.6527.3.1.2.2.6.16";
      }
    }
  }
  notification tmnxEqDigitalDiagMonitorFailure {
    description
      "Generated when an SFF that supports Digital Diagnostic
       Monitoring (DDM) enters a failed state.";
    smiv2:oid "1.3.6.1.4.1.6527.3.1.3.2.2.0.35";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
    container object-2 {
      leaf tmnxDDMFailedObject {
        type enumeration {
          enum "unknown" {
            value 0;
          }
          enum "temperature-low-warning" {
            value 1;
          }
          enum "temperature-low-alarm" {
            value 2;
          }
          enum "temperature-high-warning" {
            value 3;
          }
          enum "temperature-high-alarm" {
            value 4;
          }
          enum "supplyVoltage-low-warning" {
            value 5;
          }
          enum "supplyVoltage-low-alarm" {
            value 6;
          }
          enum "supplyVoltage-high-warning" {
            value 7;
          }
          enum "supplyVoltage-high-alarm" {
            value 8;
          }
          enum "txBiasCurrent-low-warning" {
            value 9;
          }
          enum "txBiasCurrent-low-alarm" {
            value 10;
          }
          enum "txBiasCurrent-high-warning" {
            value 11;
          }
          enum "txBiasCurrent-high-alarm" {
            value 12;
          }
          enum "txOutputPower-low-warning" {
            value 13;
          }
          enum "txOutputPower-low-alarm" {
            value 14;
          }
          enum "txOutputPower-high-warning" {
            value 15;
          }
          enum "txOutputPower-high-alarm" {
            value 16;
          }
          enum "rxOpticalPower-low-warning" {
            value 17;
          }
          enum "rxOpticalPower-low-alarm" {
            value 18;
          }
          enum "rxOpticalPower-high-warning" {
            value 19;
          }
          enum "rxOpticalPower-high-alarm" {
            value 20;
          }
          enum "aux1-low-warning" {
            value 21;
          }
          enum "aux1-low-alarm" {
            value 22;
          }
          enum "aux1-high-warning" {
            value 23;
          }
          enum "aux1-high-alarm" {
            value 24;
          }
          enum "aux2-low-warning" {
            value 25;
          }
          enum "aux2-low-alarm" {
            value 26;
          }
          enum "aux2-high-warning" {
            value 27;
          }
          enum "aux2-high-alarm" {
            value 28;
          }
        }
        description
          "Used by Digital Diagnostic Monitoring (DDM) Notifications, the
           value of tmnxDDMFailedObject indicates which object of the
           monitored SFF is in a failed or cleared threshold state.";
        smiv2:max-access "accessible-for-notify";
        smiv2:oid "1.3.6.1.4.1.6527.3.1.2.2.7.9";
      }
    }
    container object-3 {
      leaf tmnxDDMLaneIdOrModule {
        type uint32 {
          range "0..16";
        }
        description
          "The value of tmnxDDMLaneIdOrModule indicates which component of the
           Digital Diagnostic Monitoring (DDM) SFF device caused the notification
           to be raised. A value of zero (0) indicates the SFF module failed,
           otherwise the SFF Lane ID is specified. For SFF modules that do not
           support Lanes, this object will always be set to the value zero (0).";
        smiv2:max-access "accessible-for-notify";
        smiv2:oid "1.3.6.1.4.1.6527.3.1.2.2.7.31";
      }
    }
  }
  notification tmnxEqPortSFPStatusFailure {
    description
      "Generated when the tmnxPortSFPStatus of an SFF results in
       a value other than 'not-equipped (0)', or 'operational (1)'.
       tmnxEqPortSFPStatusFailure obsoleted tmnxEqPortSFPCorrupted for
       revision 6.0 on Alcatel-Lucent SROS series systems.";
    smiv2:oid "1.3.6.1.4.1.6527.3.1.3.2.2.0.36";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
    container object-2 {
      leaf tmnxChassisIndex {
        type leafref {
          path "/timetra-chassis:TIMETRA-CHASSIS-MIB/timetra-chassis:tmnxChassisTable/timetra-chassis:tmnxChassisEntry/timetra-chassis:tmnxChassisIndex";
        }
      }
      leaf tmnxPortPortID {
        type leafref {
          path "/timetra-port:TIMETRA-PORT-MIB/timetra-port:tmnxPortTable/timetra-port:tmnxPortEntry/timetra-port:tmnxPortPortID";
        }
      }
      leaf tmnxPortSFPStatus {
        type leafref {
          path "/timetra-port:TIMETRA-PORT-MIB/timetra-port:tmnxPortTable/timetra-port:tmnxPortEntry/timetra-port:tmnxPortSFPStatus";
        }
      }
    }
  }
  notification tmnxDSXClockSyncStateChange {
    description
      "Generated when the tmnxDS3ChannelClockSyncState changes for a DS3 or
       DS1 channel with adaptive or differentical clock source.";
    smiv2:oid "1.3.6.1.4.1.6527.3.1.3.2.2.0.37";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
    container object-2 {
      leaf tmnxDSXClockSyncStateObject {
        type timetra-port:TmnxDSXClockSyncState;
        description
          "Used by tmnxDSXClockSyncStateChange.  The value of
           tmnxDSXClockSyncStateObject indicates the clock sync state
           of a DS3 or DS1 channel with clock source adaptive or
           differential.";
        smiv2:max-access "accessible-for-notify";
        smiv2:oid "1.3.6.1.4.1.6527.3.1.2.2.7.10";
      }
    }
  }
  notification tmnxPortUnsupportedFunction {
    description
      "Generated when a functionality is required from this port that it
       cannot support.
       
       The object tmnxPortNotifyDescription explains what function is
       affected.";
    smiv2:oid "1.3.6.1.4.1.6527.3.1.3.2.2.0.38";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
    container object-2 {
      leaf tmnxPortNotifyDescription {
        type snmpv2-tc:DisplayString;
        description
          "The object tmnxPortNotifyDescription is a printable character
           string.";
        smiv2:max-access "accessible-for-notify";
        smiv2:oid "1.3.6.1.4.1.6527.3.1.2.2.7.11";
      }
    }
  }
  notification tmnxBundleMemberMlfrLoopback {
    description
      "Generated when a Multilink Frame-Relay Bundle Member enters or leaves
       the 'loopback (3)' state.";
    smiv2:oid "1.3.6.1.4.1.6527.3.1.3.2.2.0.39";
    container object-1 {
      leaf tmnxBundleBundleID {
        type leafref {
          path "/timetra-port:TIMETRA-PORT-MIB/timetra-port:tmnxBundleTable/timetra-port:tmnxBundleEntry/timetra-port:tmnxBundleBundleID";
        }
      }
      leaf tmnxPortPortID {
        type leafref {
          path "/timetra-port:TIMETRA-PORT-MIB/timetra-port:tmnxPortTable/timetra-port:tmnxPortEntry/timetra-port:tmnxPortPortID";
        }
      }
      leaf tmnxBundleMemberMlfrDownReason {
        type leafref {
          path "/timetra-port:TIMETRA-PORT-MIB/timetra-port:tmnxBundleMemberMlfrTable/timetra-port:tmnxBundleMemberMlfrEntry/timetra-port:tmnxBundleMemberMlfrDownReason";
        }
      }
    }
  }
  notification tmnxEqPortWaveTrackerAlarm {
    description
      "The tmnxEqPortWaveTrackerAlarm notification indicates that a
       Wave Tracker interface has experienced either a raising or clearing
       of an alarm as indicated by the value of tmnxPortNotifyWTAlarmReason.";
    smiv2:oid "1.3.6.1.4.1.6527.3.1.3.2.2.0.40";
    container object-1 {
      leaf tmnxPortNotifyWTAlarmReason {
        type enumeration {
          enum "notUsed" {
            value 0;
          }
          enum "encFail" {
            value 1;
          }
          enum "encDegr" {
            value 2;
          }
          enum "pwrFail" {
            value 3;
          }
          enum "pwrDegr" {
            value 4;
          }
          enum "pwrHigh" {
            value 5;
          }
          enum "pwrLow" {
            value 6;
          }
          enum "missing" {
            value 7;
          }
        }
        description
          "Used by Wavelength Tracker Port Notifications, the value of
           tmnxPortNotifyWTAlarmReason indicates the reason a Wavelength
           Tracker port alarm has been raised. The values correspond to the
           TmnxWaveTrackerAlarm bits.";
        smiv2:max-access "accessible-for-notify";
        smiv2:oid "1.3.6.1.4.1.6527.3.1.2.2.7.12";
      }
    }
    container object-2 {
      leaf tmnxChassisIndex {
        type leafref {
          path "/timetra-chassis:TIMETRA-CHASSIS-MIB/timetra-chassis:tmnxChassisTable/timetra-chassis:tmnxChassisEntry/timetra-chassis:tmnxChassisIndex";
        }
      }
      leaf tmnxPortPortID {
        type leafref {
          path "/timetra-port:TIMETRA-PORT-MIB/timetra-port:tmnxPortTable/timetra-port:tmnxPortEntry/timetra-port:tmnxPortPortID";
        }
      }
      leaf tmnxWaveTrackerAlarmState {
        type leafref {
          path "/timetra-port:TIMETRA-PORT-MIB/timetra-port:tmnxWaveTrackerTable/timetra-port:tmnxWaveTrackerEntry/timetra-port:tmnxWaveTrackerAlarmState";
        }
      }
    }
  }
  notification tPortAccEgrQGrpHostMatchFailure {
    description
      "The tPortAccEgrQGrpHostMatchFailure notification indicates that a
       host match lookup failed to resolve a specific port egress 
       queue-group. In such case the default policer-output-queue is used.";
    smiv2:oid "1.3.6.1.4.1.6527.3.1.3.2.2.0.41";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
    container object-2 {
      leaf tmnxHostMatchNotifyIntDestId {
        type timetra-tc:TmnxSubMgtIntDestId;
        description
          "Used by tPortAccEgrQGrpHostMatchFailure and
           tPortEgrVPortHostMatchFailure. The value of
           tmnxHostMatchNotifyIntDestId indicates the intermediate destination
           id of the host which was used to lookup the port egress queue-group
           or virtual port.";
        smiv2:max-access "accessible-for-notify";
        smiv2:oid "1.3.6.1.4.1.6527.3.1.2.2.7.13";
      }
    }
    container object-3 {
      leaf tmnxHostMatchNotifyOrgString {
        type timetra-tc:TmnxSubMgtOrgStrOrZero;
        description
          "Used by tPortAccEgrQGrpHostMatchFailure and
           tPortEgrVPortHostMatchFailure. The value of 
           tmnxHostMatchNotifyOrgString indicates the organization string of
           the host which was used to lookup the port egress queue-group or
           virtual port.";
        smiv2:max-access "accessible-for-notify";
        smiv2:oid "1.3.6.1.4.1.6527.3.1.2.2.7.14";
      }
    }
    container object-4 {
      leaf tmnxHostMatchNotifySubIdent {
        type timetra-tc:TmnxSubIdentStringOrEmpty;
        description
          "Used by tPortAccEgrQGrpHostMatchFailure and
           tPortEgrVPortHostMatchFailure. The value of 
           tmnxHostMatchNotifySubIdent indicates the subscriber identification
           string of the host which was used to lookup the port egress
           queue-group or virtual port.";
        smiv2:max-access "accessible-for-notify";
        smiv2:oid "1.3.6.1.4.1.6527.3.1.2.2.7.15";
      }
    }
  }
  notification tPortEgrVPortHostMatchFailure {
    description
      "The tPortEgrVPortHostMatchFailure notification indicates that a
       host match lookup failed to resolve a specific port egress 
       virtual port.";
    smiv2:oid "1.3.6.1.4.1.6527.3.1.3.2.2.0.42";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
    container object-2 {
      leaf tmnxHostMatchNotifyIntDestId {
        type timetra-tc:TmnxSubMgtIntDestId;
        description
          "Used by tPortAccEgrQGrpHostMatchFailure and
           tPortEgrVPortHostMatchFailure. The value of
           tmnxHostMatchNotifyIntDestId indicates the intermediate destination
           id of the host which was used to lookup the port egress queue-group
           or virtual port.";
        smiv2:max-access "accessible-for-notify";
        smiv2:oid "1.3.6.1.4.1.6527.3.1.2.2.7.13";
      }
    }
    container object-3 {
      leaf tmnxHostMatchNotifyOrgString {
        type timetra-tc:TmnxSubMgtOrgStrOrZero;
        description
          "Used by tPortAccEgrQGrpHostMatchFailure and
           tPortEgrVPortHostMatchFailure. The value of 
           tmnxHostMatchNotifyOrgString indicates the organization string of
           the host which was used to lookup the port egress queue-group or
           virtual port.";
        smiv2:max-access "accessible-for-notify";
        smiv2:oid "1.3.6.1.4.1.6527.3.1.2.2.7.14";
      }
    }
    container object-4 {
      leaf tmnxHostMatchNotifySubIdent {
        type timetra-tc:TmnxSubIdentStringOrEmpty;
        description
          "Used by tPortAccEgrQGrpHostMatchFailure and
           tPortEgrVPortHostMatchFailure. The value of 
           tmnxHostMatchNotifySubIdent indicates the subscriber identification
           string of the host which was used to lookup the port egress
           queue-group or virtual port.";
        smiv2:max-access "accessible-for-notify";
        smiv2:oid "1.3.6.1.4.1.6527.3.1.2.2.7.15";
      }
    }
  }
  notification tmnxEqDigitalDiagMonitorClear {
    description
      "Generated when an SFF that supports Digital Diagnostic
       Monitoring (DDM) clears a failed state.";
    smiv2:oid "1.3.6.1.4.1.6527.3.1.3.2.2.0.43";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
    container object-2 {
      leaf tmnxDDMFailedObject {
        type enumeration {
          enum "unknown" {
            value 0;
          }
          enum "temperature-low-warning" {
            value 1;
          }
          enum "temperature-low-alarm" {
            value 2;
          }
          enum "temperature-high-warning" {
            value 3;
          }
          enum "temperature-high-alarm" {
            value 4;
          }
          enum "supplyVoltage-low-warning" {
            value 5;
          }
          enum "supplyVoltage-low-alarm" {
            value 6;
          }
          enum "supplyVoltage-high-warning" {
            value 7;
          }
          enum "supplyVoltage-high-alarm" {
            value 8;
          }
          enum "txBiasCurrent-low-warning" {
            value 9;
          }
          enum "txBiasCurrent-low-alarm" {
            value 10;
          }
          enum "txBiasCurrent-high-warning" {
            value 11;
          }
          enum "txBiasCurrent-high-alarm" {
            value 12;
          }
          enum "txOutputPower-low-warning" {
            value 13;
          }
          enum "txOutputPower-low-alarm" {
            value 14;
          }
          enum "txOutputPower-high-warning" {
            value 15;
          }
          enum "txOutputPower-high-alarm" {
            value 16;
          }
          enum "rxOpticalPower-low-warning" {
            value 17;
          }
          enum "rxOpticalPower-low-alarm" {
            value 18;
          }
          enum "rxOpticalPower-high-warning" {
            value 19;
          }
          enum "rxOpticalPower-high-alarm" {
            value 20;
          }
          enum "aux1-low-warning" {
            value 21;
          }
          enum "aux1-low-alarm" {
            value 22;
          }
          enum "aux1-high-warning" {
            value 23;
          }
          enum "aux1-high-alarm" {
            value 24;
          }
          enum "aux2-low-warning" {
            value 25;
          }
          enum "aux2-low-alarm" {
            value 26;
          }
          enum "aux2-high-warning" {
            value 27;
          }
          enum "aux2-high-alarm" {
            value 28;
          }
        }
        description
          "Used by Digital Diagnostic Monitoring (DDM) Notifications, the
           value of tmnxDDMFailedObject indicates which object of the
           monitored SFF is in a failed or cleared threshold state.";
        smiv2:max-access "accessible-for-notify";
        smiv2:oid "1.3.6.1.4.1.6527.3.1.2.2.7.9";
      }
    }
    container object-3 {
      leaf tmnxDDMLaneIdOrModule {
        type uint32 {
          range "0..16";
        }
        description
          "The value of tmnxDDMLaneIdOrModule indicates which component of the
           Digital Diagnostic Monitoring (DDM) SFF device caused the notification
           to be raised. A value of zero (0) indicates the SFF module failed,
           otherwise the SFF Lane ID is specified. For SFF modules that do not
           support Lanes, this object will always be set to the value zero (0).";
        smiv2:max-access "accessible-for-notify";
        smiv2:oid "1.3.6.1.4.1.6527.3.1.2.2.7.31";
      }
    }
  }
  notification tmnxEqPortOpticalAmpAlarm {
    description
      "The tmnxEqPortOpticalAmpAlarm notification indicates that an
       Optical Amplifier interface has experienced either a raising
       or clearing of an alarm as indicated by the value of
       tmnxOpticalPortAmpAlarmState.";
    smiv2:oid "1.3.6.1.4.1.6527.3.1.3.2.2.0.44";
    container object-1 {
      leaf tmnxChassisIndex {
        type leafref {
          path "/timetra-chassis:TIMETRA-CHASSIS-MIB/timetra-chassis:tmnxChassisTable/timetra-chassis:tmnxChassisEntry/timetra-chassis:tmnxChassisIndex";
        }
      }
      leaf tmnxPortPortID {
        type leafref {
          path "/timetra-port:TIMETRA-PORT-MIB/timetra-port:tmnxPortTable/timetra-port:tmnxPortEntry/timetra-port:tmnxPortPortID";
        }
      }
      leaf tmnxOpticalPortAmpAlarmState {
        type leafref {
          path "/timetra-port:TIMETRA-PORT-MIB/timetra-port:tmnxOpticalPortOperTable/timetra-port:tmnxOpticalPortOperEntry/timetra-port:tmnxOpticalPortAmpAlarmState";
        }
      }
    }
  }
  notification tmnxEqPortOpticalTdcmAlarm {
    description
      "The tmnxEqPortOpticalTdcmAlarm notification indicates that an
       Optical Tdcm interface has experienced either a raising
       or clearing of an alarm as indicated by the value of
       tmnxOpticalPortTdcmAlarmState.";
    smiv2:oid "1.3.6.1.4.1.6527.3.1.3.2.2.0.45";
    container object-1 {
      leaf tmnxChassisIndex {
        type leafref {
          path "/timetra-chassis:TIMETRA-CHASSIS-MIB/timetra-chassis:tmnxChassisTable/timetra-chassis:tmnxChassisEntry/timetra-chassis:tmnxChassisIndex";
        }
      }
      leaf tmnxPortPortID {
        type leafref {
          path "/timetra-port:TIMETRA-PORT-MIB/timetra-port:tmnxPortTable/timetra-port:tmnxPortEntry/timetra-port:tmnxPortPortID";
        }
      }
      leaf tmnxOpticalPortTdcmAlarmState {
        type leafref {
          path "/timetra-port:TIMETRA-PORT-MIB/timetra-port:tmnxOpticalPortOperTable/timetra-port:tmnxOpticalPortOperEntry/timetra-port:tmnxOpticalPortTdcmAlarmState";
        }
      }
    }
  }
  notification tmnxEqSonetClockSrcNotCompatible {
    description
      "Notification tmnxEqSonetClockSrcNotCompatible is generated when a
       configured SONET/SDH clock source on an MDA port is not compatible
       with the MDA type.
       
       [EFFECT] Though services can still be created, if the tmnxMdaNotifyType
       is the same as the tmnxMDAEquippedType then the MDA will fail to
       operate as configured and will be in a failed state.
       
       [RECOVERY] Change the configuration to reflect the capabilities of the
       MDA port, or switch out/re-provision the MDA for one that is
       compatible.";
    smiv2:oid "1.3.6.1.4.1.6527.3.1.3.2.2.0.46";
    container object-1 {
      leaf tmnxChassisIndex {
        type leafref {
          path "/timetra-chassis:TIMETRA-CHASSIS-MIB/timetra-chassis:tmnxChassisTable/timetra-chassis:tmnxChassisEntry/timetra-chassis:tmnxChassisIndex";
        }
      }
      leaf tmnxPortPortID {
        type leafref {
          path "/timetra-port:TIMETRA-PORT-MIB/timetra-port:tmnxPortTable/timetra-port:tmnxPortEntry/timetra-port:tmnxPortPortID";
        }
      }
      leaf tmnxSonetClockSource {
        type leafref {
          path "/timetra-port:TIMETRA-PORT-MIB/timetra-port:tmnxSonetTable/timetra-port:tmnxSonetEntry/timetra-port:tmnxSonetClockSource";
        }
      }
    }
    container object-2 {
      leaf tmnxMdaNotifyType {
        type timetra-chassis:TmnxMdaType;
        description
          "Used by equipment alarms where the type of MDA isn't supported with
           the current configuration.";
        smiv2:max-access "accessible-for-notify";
        smiv2:oid "1.3.6.1.4.1.6527.3.1.2.2.6.16";
      }
    }
  }
  notification tmnxEqSonetSfThreshNotCompatible {
    description
      "Notification tmnxEqSonetSfThreshNotCompatible is generated when a
       configured SONET/SDH Signal Fail (SF) threshold on an MDA port is not
       compatible with the MDA type.
       
       [EFFECT] Though services can still be created, if the tmnxMdaNotifyType
       is the same as the tmnxMDAEquippedType then the MDA will fail to
       operate as configured and will be in a failed state.
       
       [RECOVERY] Change the configuration to reflect the capabilities of the
       MDA port, or switch out/re-provision the MDA for one that is
       compatible.";
    smiv2:oid "1.3.6.1.4.1.6527.3.1.3.2.2.0.47";
    container object-1 {
      leaf tmnxChassisIndex {
        type leafref {
          path "/timetra-chassis:TIMETRA-CHASSIS-MIB/timetra-chassis:tmnxChassisTable/timetra-chassis:tmnxChassisEntry/timetra-chassis:tmnxChassisIndex";
        }
      }
      leaf tmnxPortPortID {
        type leafref {
          path "/timetra-port:TIMETRA-PORT-MIB/timetra-port:tmnxPortTable/timetra-port:tmnxPortEntry/timetra-port:tmnxPortPortID";
        }
      }
      leaf tmnxSonetBerSfThreshold {
        type leafref {
          path "/timetra-port:TIMETRA-PORT-MIB/timetra-port:tmnxSonetTable/timetra-port:tmnxSonetEntry/timetra-port:tmnxSonetBerSfThreshold";
        }
      }
    }
    container object-2 {
      leaf tmnxMdaNotifyType {
        type timetra-chassis:TmnxMdaType;
        description
          "Used by equipment alarms where the type of MDA isn't supported with
           the current configuration.";
        smiv2:max-access "accessible-for-notify";
        smiv2:oid "1.3.6.1.4.1.6527.3.1.2.2.6.16";
      }
    }
  }
  notification tmnxEqSonetFramingNotCompatible {
    description
      "Notification tmnxEqSonetFramingNotCompatible is generated when a
       configured SONET/SDH framing on an MDA port is not compatible with
       the MDA type.
       
       [EFFECT] Though services can still be created, if the tmnxMdaNotifyType
       is the same as the tmnxMDAEquippedType then the MDA will fail to
       operate as configured and will be in a failed state.
       
       [RECOVERY] Change the configuration to reflect the capabilities of the
       MDA port, or switch out/re-provision the MDA for one that is
       compatible.";
    smiv2:oid "1.3.6.1.4.1.6527.3.1.3.2.2.0.48";
    container object-1 {
      leaf tmnxChassisIndex {
        type leafref {
          path "/timetra-chassis:TIMETRA-CHASSIS-MIB/timetra-chassis:tmnxChassisTable/timetra-chassis:tmnxChassisEntry/timetra-chassis:tmnxChassisIndex";
        }
      }
      leaf tmnxPortPortID {
        type leafref {
          path "/timetra-port:TIMETRA-PORT-MIB/timetra-port:tmnxPortTable/timetra-port:tmnxPortEntry/timetra-port:tmnxPortPortID";
        }
      }
      leaf tmnxSonetFraming {
        type leafref {
          path "/timetra-port:TIMETRA-PORT-MIB/timetra-port:tmnxSonetTable/timetra-port:tmnxSonetEntry/timetra-port:tmnxSonetFraming";
        }
      }
    }
    container object-2 {
      leaf tmnxMdaNotifyType {
        type timetra-chassis:TmnxMdaType;
        description
          "Used by equipment alarms where the type of MDA isn't supported with
           the current configuration.";
        smiv2:max-access "accessible-for-notify";
        smiv2:oid "1.3.6.1.4.1.6527.3.1.2.2.6.16";
      }
    }
  }
  notification tmnxResvCbsPoolThreshGreen {
    description
      "The notification tmnxResvCbsPoolThreshGreen is generated when a
       reserved-CBS of an object (MDA or port) returns to within defined
       thresholds.
       
       [EFFECT] Reserved CBS of the object has returned to within normal
       parameters.
       
       [RECOVERY] None required.";
    smiv2:oid "1.3.6.1.4.1.6527.3.1.3.2.2.0.49";
    container object-1 {
      leaf tmnxObjType {
        type enumeration {
          enum "mda" {
            value 1;
          }
          enum "port" {
            value 2;
          }
          enum "unused" {
            value 3;
          }
          enum "bundle" {
            value 4;
          }
        }
        description
          "The object tmnxObjType defines the type of object for which this
           notification is sent.";
        smiv2:max-access "accessible-for-notify";
        smiv2:oid "1.3.6.1.4.1.6527.3.1.2.2.7.20";
      }
    }
    container object-2 {
      leaf tmnxObjPortId {
        type timetra-tc:TmnxPortID;
        description
          "The object tmnxObjPortId is used to identify the specific Port object.";
        smiv2:max-access "accessible-for-notify";
        smiv2:oid "1.3.6.1.4.1.6527.3.1.2.2.7.21";
      }
    }
    container object-3 {
      leaf tmnxObjMdaId {
        type timetra-tc:TmnxPortID;
        description
          "The tmnxObjMdaId is used to identify the specific MDA object.
           If tmnxObjType is 'mda', then the tmnxObjMdaId is encoded as a
           physical port with the port being '0'.";
        smiv2:max-access "accessible-for-notify";
        smiv2:oid "1.3.6.1.4.1.6527.3.1.2.2.7.22";
      }
    }
    container object-4 {
      leaf tmnxObjAppType {
        type enumeration {
          enum "accessIngress" {
            value 1;
          }
          enum "accessEgress" {
            value 2;
          }
          enum "networkIngress" {
            value 3;
          }
          enum "networkEgress" {
            value 4;
          }
          enum "ingress" {
            value 5;
          }
          enum "egress" {
            value 6;
          }
        }
        description
          "The object tmnxObjAppType specifies the nature of usage the pool
           tmnxObjAppPool is used for. The pools could be used for access or
           network traffic at either ingress or egress.
           
           The value of 'ingress' and 'egress' is used with objects using
           named-pool policy.";
        smiv2:max-access "accessible-for-notify";
        smiv2:oid "1.3.6.1.4.1.6527.3.1.2.2.7.23";
      }
    }
    container object-5 {
      leaf tmnxObjAppPool {
        type timetra-tc:TNamedItemOrEmpty;
        description
          "The object tmnxObjAppPool specifies the name of the pool being used.";
        smiv2:max-access "accessible-for-notify";
        smiv2:oid "1.3.6.1.4.1.6527.3.1.2.2.7.24";
      }
    }
    container object-6 {
      leaf tmnxObjNamedPoolPolicy {
        type timetra-tc:TNamedItemOrEmpty;
        description
          "The value of tmnxObjNamedPoolPolicy indicates the name of 
           the tmnxPortIngNamedPoolPlcy or tmnxPortEgrNamedPoolPlcy object
           to which this notification belongs.";
        smiv2:max-access "accessible-for-notify";
        smiv2:oid "1.3.6.1.4.1.6527.3.1.2.2.7.25";
      }
    }
    container object-7 {
      leaf tmnxObjAppResvSize {
        type uint32;
        units "kilo-bytes";
        description
          "The value of tmnxObjAppResvSize indicates operational value of reserved
           size of the associated object (MDA or port).
           
           This is used by tmnxResvCbsPoolThreshGreen, tmnxResvCbsPoolThreshAmber
           and tmnxResvCbsPoolThreshRed notifications.";
        smiv2:max-access "accessible-for-notify";
        smiv2:oid "1.3.6.1.4.1.6527.3.1.2.2.7.16";
      }
    }
    container object-8 {
      leaf tmnxObjAppSumOfQResvSize {
        type uint32;
        units "kilo-bytes";
        description
          "The value of tmnxObjAppSumOfQResvSize indicates sum of the reserved
           CBS queue size of reserved CBS of the associated object (MDA or port).
            
           This is used by tmnxResvCbsPoolThreshGreen, tmnxResvCbsPoolThreshAmber
           and tmnxResvCbsPoolThreshRed notifications.";
        smiv2:max-access "accessible-for-notify";
        smiv2:oid "1.3.6.1.4.1.6527.3.1.2.2.7.19";
      }
    }
    container object-9 {
      leaf tmnxObjAppResvCbsOld {
        type uint32;
        units "percent";
        description
          "The value of tmnxObjAppResvCbsOld indicates old value of reserved
           CBS of the associated object (MDA or port). When tmnxObjAppResvCbsOld 
           is set to '4294967295', tmnxObjAppResvCbsOld indicates invalid reserved
           size value.
           
           This is used by tmnxResvCbsPoolThreshGreen, tmnxResvCbsPoolThreshAmber
           and tmnxResvCbsPoolThreshRed notifications.";
        smiv2:max-access "accessible-for-notify";
        smiv2:oid "1.3.6.1.4.1.6527.3.1.2.2.7.17";
      }
    }
    container object-10 {
      leaf tmnxObjAppResvCbsNew {
        type uint32;
        units "percent";
        description
          "The value of tmnxObjAppResvCbsNew indicates new value of reserved
           CBS of the associated object (MDA or port).
           
           This is used by tmnxResvCbsPoolThreshGreen, tmnxResvCbsPoolThreshAmber
           and tmnxResvCbsPoolThreshRed notifications.";
        smiv2:max-access "accessible-for-notify";
        smiv2:oid "1.3.6.1.4.1.6527.3.1.2.2.7.18";
      }
    }
    container object-11 {
      leaf tmnxObjAppResvSizeOld {
        type uint32;
        units "kilo-bytes";
        description
          "The value of tmnxObjAppResvSizeOld indicates old value of reserved
           size of the associated object (MDA or port). When tmnxObjAppResvSizeOld 
           is set to '4294967295', tmnxObjAppResvSizeOld indicates invalid reserved
           size value.
           
           This is used by tmnxResvCbsPoolThreshGreen, tmnxResvCbsPoolThreshAmber
           and tmnxResvCbsPoolThreshRed notifications.";
        smiv2:max-access "accessible-for-notify";
        smiv2:oid "1.3.6.1.4.1.6527.3.1.2.2.7.30";
      }
    }
  }
  notification tmnxResvCbsPoolThreshAmber {
    description
      "The notification tmnxResvCbsPoolThreshAmber is generated when a
       reserved-CBS of an object (MDA or port) has crossed threshold value
       specified by tmnxObjectAppAmbrAlrmThresh or tQ1NamedPoolAmbrAlrmThresh.
       
       [EFFECT] This is warning event but the traffic is not yet affected.
       
       [RECOVERY] The value of tmnxObjectAppResvCbs
       or TIMETRA-QOS-MIB::tQ1NamedPoolReservedCbs may need to be adjusted.";
    smiv2:oid "1.3.6.1.4.1.6527.3.1.3.2.2.0.50";
    container object-1 {
      leaf tmnxObjType {
        type enumeration {
          enum "mda" {
            value 1;
          }
          enum "port" {
            value 2;
          }
          enum "unused" {
            value 3;
          }
          enum "bundle" {
            value 4;
          }
        }
        description
          "The object tmnxObjType defines the type of object for which this
           notification is sent.";
        smiv2:max-access "accessible-for-notify";
        smiv2:oid "1.3.6.1.4.1.6527.3.1.2.2.7.20";
      }
    }
    container object-2 {
      leaf tmnxObjPortId {
        type timetra-tc:TmnxPortID;
        description
          "The object tmnxObjPortId is used to identify the specific Port object.";
        smiv2:max-access "accessible-for-notify";
        smiv2:oid "1.3.6.1.4.1.6527.3.1.2.2.7.21";
      }
    }
    container object-3 {
      leaf tmnxObjMdaId {
        type timetra-tc:TmnxPortID;
        description
          "The tmnxObjMdaId is used to identify the specific MDA object.
           If tmnxObjType is 'mda', then the tmnxObjMdaId is encoded as a
           physical port with the port being '0'.";
        smiv2:max-access "accessible-for-notify";
        smiv2:oid "1.3.6.1.4.1.6527.3.1.2.2.7.22";
      }
    }
    container object-4 {
      leaf tmnxObjAppType {
        type enumeration {
          enum "accessIngress" {
            value 1;
          }
          enum "accessEgress" {
            value 2;
          }
          enum "networkIngress" {
            value 3;
          }
          enum "networkEgress" {
            value 4;
          }
          enum "ingress" {
            value 5;
          }
          enum "egress" {
            value 6;
          }
        }
        description
          "The object tmnxObjAppType specifies the nature of usage the pool
           tmnxObjAppPool is used for. The pools could be used for access or
           network traffic at either ingress or egress.
           
           The value of 'ingress' and 'egress' is used with objects using
           named-pool policy.";
        smiv2:max-access "accessible-for-notify";
        smiv2:oid "1.3.6.1.4.1.6527.3.1.2.2.7.23";
      }
    }
    container object-5 {
      leaf tmnxObjAppPool {
        type timetra-tc:TNamedItemOrEmpty;
        description
          "The object tmnxObjAppPool specifies the name of the pool being used.";
        smiv2:max-access "accessible-for-notify";
        smiv2:oid "1.3.6.1.4.1.6527.3.1.2.2.7.24";
      }
    }
    container object-6 {
      leaf tmnxObjNamedPoolPolicy {
        type timetra-tc:TNamedItemOrEmpty;
        description
          "The value of tmnxObjNamedPoolPolicy indicates the name of 
           the tmnxPortIngNamedPoolPlcy or tmnxPortEgrNamedPoolPlcy object
           to which this notification belongs.";
        smiv2:max-access "accessible-for-notify";
        smiv2:oid "1.3.6.1.4.1.6527.3.1.2.2.7.25";
      }
    }
    container object-7 {
      leaf tmnxObjAppResvSize {
        type uint32;
        units "kilo-bytes";
        description
          "The value of tmnxObjAppResvSize indicates operational value of reserved
           size of the associated object (MDA or port).
           
           This is used by tmnxResvCbsPoolThreshGreen, tmnxResvCbsPoolThreshAmber
           and tmnxResvCbsPoolThreshRed notifications.";
        smiv2:max-access "accessible-for-notify";
        smiv2:oid "1.3.6.1.4.1.6527.3.1.2.2.7.16";
      }
    }
    container object-8 {
      leaf tmnxObjAppSumOfQResvSize {
        type uint32;
        units "kilo-bytes";
        description
          "The value of tmnxObjAppSumOfQResvSize indicates sum of the reserved
           CBS queue size of reserved CBS of the associated object (MDA or port).
            
           This is used by tmnxResvCbsPoolThreshGreen, tmnxResvCbsPoolThreshAmber
           and tmnxResvCbsPoolThreshRed notifications.";
        smiv2:max-access "accessible-for-notify";
        smiv2:oid "1.3.6.1.4.1.6527.3.1.2.2.7.19";
      }
    }
    container object-9 {
      leaf tmnxObjAppResvCbsOld {
        type uint32;
        units "percent";
        description
          "The value of tmnxObjAppResvCbsOld indicates old value of reserved
           CBS of the associated object (MDA or port). When tmnxObjAppResvCbsOld 
           is set to '4294967295', tmnxObjAppResvCbsOld indicates invalid reserved
           size value.
           
           This is used by tmnxResvCbsPoolThreshGreen, tmnxResvCbsPoolThreshAmber
           and tmnxResvCbsPoolThreshRed notifications.";
        smiv2:max-access "accessible-for-notify";
        smiv2:oid "1.3.6.1.4.1.6527.3.1.2.2.7.17";
      }
    }
    container object-10 {
      leaf tmnxObjAppResvCbsNew {
        type uint32;
        units "percent";
        description
          "The value of tmnxObjAppResvCbsNew indicates new value of reserved
           CBS of the associated object (MDA or port).
           
           This is used by tmnxResvCbsPoolThreshGreen, tmnxResvCbsPoolThreshAmber
           and tmnxResvCbsPoolThreshRed notifications.";
        smiv2:max-access "accessible-for-notify";
        smiv2:oid "1.3.6.1.4.1.6527.3.1.2.2.7.18";
      }
    }
    container object-11 {
      leaf tmnxObjAppResvSizeOld {
        type uint32;
        units "kilo-bytes";
        description
          "The value of tmnxObjAppResvSizeOld indicates old value of reserved
           size of the associated object (MDA or port). When tmnxObjAppResvSizeOld 
           is set to '4294967295', tmnxObjAppResvSizeOld indicates invalid reserved
           size value.
           
           This is used by tmnxResvCbsPoolThreshGreen, tmnxResvCbsPoolThreshAmber
           and tmnxResvCbsPoolThreshRed notifications.";
        smiv2:max-access "accessible-for-notify";
        smiv2:oid "1.3.6.1.4.1.6527.3.1.2.2.7.30";
      }
    }
  }
  notification tmnxResvCbsPoolThreshRed {
    description
      "The notification tmnxResvCbsPoolThreshAmber is generated when a
       reserved-CBS of an object (MDA or port) has crossed threshold value
       specified by tmnxObjectAppRedAlrmThresh or tQ1NamedPoolRedAlrmThresh.
       
       [EFFECT] This is a critical event and the traffic may be affected.
       
       [RECOVERY] The value of tmnxObjectAppResvCbs
       or TIMETRA-QOS-MIB::tQ1NamedPoolReservedCbs may need to be adjusted.";
    smiv2:oid "1.3.6.1.4.1.6527.3.1.3.2.2.0.51";
    container object-1 {
      leaf tmnxObjType {
        type enumeration {
          enum "mda" {
            value 1;
          }
          enum "port" {
            value 2;
          }
          enum "unused" {
            value 3;
          }
          enum "bundle" {
            value 4;
          }
        }
        description
          "The object tmnxObjType defines the type of object for which this
           notification is sent.";
        smiv2:max-access "accessible-for-notify";
        smiv2:oid "1.3.6.1.4.1.6527.3.1.2.2.7.20";
      }
    }
    container object-2 {
      leaf tmnxObjPortId {
        type timetra-tc:TmnxPortID;
        description
          "The object tmnxObjPortId is used to identify the specific Port object.";
        smiv2:max-access "accessible-for-notify";
        smiv2:oid "1.3.6.1.4.1.6527.3.1.2.2.7.21";
      }
    }
    container object-3 {
      leaf tmnxObjMdaId {
        type timetra-tc:TmnxPortID;
        description
          "The tmnxObjMdaId is used to identify the specific MDA object.
           If tmnxObjType is 'mda', then the tmnxObjMdaId is encoded as a
           physical port with the port being '0'.";
        smiv2:max-access "accessible-for-notify";
        smiv2:oid "1.3.6.1.4.1.6527.3.1.2.2.7.22";
      }
    }
    container object-4 {
      leaf tmnxObjAppType {
        type enumeration {
          enum "accessIngress" {
            value 1;
          }
          enum "accessEgress" {
            value 2;
          }
          enum "networkIngress" {
            value 3;
          }
          enum "networkEgress" {
            value 4;
          }
          enum "ingress" {
            value 5;
          }
          enum "egress" {
            value 6;
          }
        }
        description
          "The object tmnxObjAppType specifies the nature of usage the pool
           tmnxObjAppPool is used for. The pools could be used for access or
           network traffic at either ingress or egress.
           
           The value of 'ingress' and 'egress' is used with objects using
           named-pool policy.";
        smiv2:max-access "accessible-for-notify";
        smiv2:oid "1.3.6.1.4.1.6527.3.1.2.2.7.23";
      }
    }
    container object-5 {
      leaf tmnxObjAppPool {
        type timetra-tc:TNamedItemOrEmpty;
        description
          "The object tmnxObjAppPool specifies the name of the pool being used.";
        smiv2:max-access "accessible-for-notify";
        smiv2:oid "1.3.6.1.4.1.6527.3.1.2.2.7.24";
      }
    }
    container object-6 {
      leaf tmnxObjNamedPoolPolicy {
        type timetra-tc:TNamedItemOrEmpty;
        description
          "The value of tmnxObjNamedPoolPolicy indicates the name of 
           the tmnxPortIngNamedPoolPlcy or tmnxPortEgrNamedPoolPlcy object
           to which this notification belongs.";
        smiv2:max-access "accessible-for-notify";
        smiv2:oid "1.3.6.1.4.1.6527.3.1.2.2.7.25";
      }
    }
    container object-7 {
      leaf tmnxObjAppResvSize {
        type uint32;
        units "kilo-bytes";
        description
          "The value of tmnxObjAppResvSize indicates operational value of reserved
           size of the associated object (MDA or port).
           
           This is used by tmnxResvCbsPoolThreshGreen, tmnxResvCbsPoolThreshAmber
           and tmnxResvCbsPoolThreshRed notifications.";
        smiv2:max-access "accessible-for-notify";
        smiv2:oid "1.3.6.1.4.1.6527.3.1.2.2.7.16";
      }
    }
    container object-8 {
      leaf tmnxObjAppSumOfQResvSize {
        type uint32;
        units "kilo-bytes";
        description
          "The value of tmnxObjAppSumOfQResvSize indicates sum of the reserved
           CBS queue size of reserved CBS of the associated object (MDA or port).
            
           This is used by tmnxResvCbsPoolThreshGreen, tmnxResvCbsPoolThreshAmber
           and tmnxResvCbsPoolThreshRed notifications.";
        smiv2:max-access "accessible-for-notify";
        smiv2:oid "1.3.6.1.4.1.6527.3.1.2.2.7.19";
      }
    }
    container object-9 {
      leaf tmnxObjAppResvCbsOld {
        type uint32;
        units "percent";
        description
          "The value of tmnxObjAppResvCbsOld indicates old value of reserved
           CBS of the associated object (MDA or port). When tmnxObjAppResvCbsOld 
           is set to '4294967295', tmnxObjAppResvCbsOld indicates invalid reserved
           size value.
           
           This is used by tmnxResvCbsPoolThreshGreen, tmnxResvCbsPoolThreshAmber
           and tmnxResvCbsPoolThreshRed notifications.";
        smiv2:max-access "accessible-for-notify";
        smiv2:oid "1.3.6.1.4.1.6527.3.1.2.2.7.17";
      }
    }
    container object-10 {
      leaf tmnxObjAppResvCbsNew {
        type uint32;
        units "percent";
        description
          "The value of tmnxObjAppResvCbsNew indicates new value of reserved
           CBS of the associated object (MDA or port).
           
           This is used by tmnxResvCbsPoolThreshGreen, tmnxResvCbsPoolThreshAmber
           and tmnxResvCbsPoolThreshRed notifications.";
        smiv2:max-access "accessible-for-notify";
        smiv2:oid "1.3.6.1.4.1.6527.3.1.2.2.7.18";
      }
    }
    container object-11 {
      leaf tmnxObjAppResvSizeOld {
        type uint32;
        units "kilo-bytes";
        description
          "The value of tmnxObjAppResvSizeOld indicates old value of reserved
           size of the associated object (MDA or port). When tmnxObjAppResvSizeOld 
           is set to '4294967295', tmnxObjAppResvSizeOld indicates invalid reserved
           size value.
           
           This is used by tmnxResvCbsPoolThreshGreen, tmnxResvCbsPoolThreshAmber
           and tmnxResvCbsPoolThreshRed notifications.";
        smiv2:max-access "accessible-for-notify";
        smiv2:oid "1.3.6.1.4.1.6527.3.1.2.2.7.30";
      }
    }
  }
  notification tmnxEqPortEtherCrcAlarm {
    description
      "tmnxEqPortEtherCrcAlarm is generated when an Ethernet port CRC alarm
       condition is detected. It is generated only when the type of alarm
       being raised is enabled on the port.
       
       [EFFECT] On a signal failure (SF) fault, the port is taken out of
       service until the CRC alarm condition is cleared.
       
       [RECOVERY] tmnxEqPortEtherCrcAlarm is cleared by taking the port out of
       service (eg. shutdown, card/mda reset, physical link loss), or
       changing/disabling the associated threshold/multiplier values.
       
       Signal Degradation is self clearing and will clear once the error rate
       drops below 1/10th of the configured rate.";
    smiv2:oid "1.3.6.1.4.1.6527.3.1.3.2.2.0.52";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
    container object-2 {
      leaf tmnxPortNotifyEtherCrcThreshold {
        type uint32;
        description
          "The value of tmnxPortNotifyEtherCrcThreshold indicates the threshold
           value used in a Ethernet Port CRC Monitoring alarm.";
        smiv2:max-access "accessible-for-notify";
        smiv2:oid "1.3.6.1.4.1.6527.3.1.2.2.7.27";
      }
    }
    container object-3 {
      leaf tmnxPortNotifyEtherCrcMultiplier {
        type uint32;
        description
          "The value of tmnxPortNotifyEtherCrcMultiplier indicates the threshold
           multiplier value used in a Ethernet Port CRC Monitoring alarm.";
        smiv2:max-access "accessible-for-notify";
        smiv2:oid "1.3.6.1.4.1.6527.3.1.2.2.7.28";
      }
    }
    container object-4 {
      leaf tmnxPortNotifyEtherCrcAlarmValue {
        type timetra-port:TmnxPortEtherCrcMonReportValue;
        description
          "The value of tmnxPortNotifyEtherCrcAlarmValue indicates the enumerated
           alarm raised or cleared in a Ethernet Port CRC Monitoring alarm.";
        smiv2:max-access "accessible-for-notify";
        smiv2:oid "1.3.6.1.4.1.6527.3.1.2.2.7.29";
      }
    }
  }
  notification tmnxEqPortEtherCrcAlarmClear {
    description
      "tmnxEqPortEtherCrcAlarmClear is generated when an Ethernet port CRC
       alarm condition is cleared or disabled.";
    smiv2:oid "1.3.6.1.4.1.6527.3.1.3.2.2.0.53";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
    container object-2 {
      leaf tmnxPortNotifyEtherCrcThreshold {
        type uint32;
        description
          "The value of tmnxPortNotifyEtherCrcThreshold indicates the threshold
           value used in a Ethernet Port CRC Monitoring alarm.";
        smiv2:max-access "accessible-for-notify";
        smiv2:oid "1.3.6.1.4.1.6527.3.1.2.2.7.27";
      }
    }
    container object-3 {
      leaf tmnxPortNotifyEtherCrcMultiplier {
        type uint32;
        description
          "The value of tmnxPortNotifyEtherCrcMultiplier indicates the threshold
           multiplier value used in a Ethernet Port CRC Monitoring alarm.";
        smiv2:max-access "accessible-for-notify";
        smiv2:oid "1.3.6.1.4.1.6527.3.1.2.2.7.28";
      }
    }
    container object-4 {
      leaf tmnxPortNotifyEtherCrcAlarmValue {
        type timetra-port:TmnxPortEtherCrcMonReportValue;
        description
          "The value of tmnxPortNotifyEtherCrcAlarmValue indicates the enumerated
           alarm raised or cleared in a Ethernet Port CRC Monitoring alarm.";
        smiv2:max-access "accessible-for-notify";
        smiv2:oid "1.3.6.1.4.1.6527.3.1.2.2.7.29";
      }
    }
  }
  notification tmnxEqPortEtherInternalAlarm {
    description
      "tmnxEqPortEtherInternalAlarm is generated when an Ethernet port
       experiences excessive internal MAC tx errors.  It is generated only
       when tmnxPortEtherDownOnInternalError is enabled on the port.
       
       [EFFECT] A port experiencing excessive internal MAC tx errors will
       take the port out of service while the alarm condition is in affect.
       
       [RECOVERY] tmnxEqPortEtherInternalAlarm is cleared by taking the port
       out of service (eg. shutdown, card/mda reset, physical link loss), or
       setting tmnxPortEtherDownOnInternalError to the value 'false'.";
    smiv2:oid "1.3.6.1.4.1.6527.3.1.3.2.2.0.54";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
  }
  notification tmnxEqPortEtherInternalAlarmClr {
    description
      "tmnxEqPortEtherInternalAlarmClr is generated when an Ethernet port no
       longer experiences excessive internal MAC tx errors.";
    smiv2:oid "1.3.6.1.4.1.6527.3.1.3.2.2.0.55";
    container object-1 {
      leaf tmnxPortNotifyPortId {
        type timetra-tc:TmnxPortID;
        description
          "Used by tmnx port Notifications, the OID indicates the
           port or sonet path associated with the alarm.";
        smiv2:max-access "accessible-for-notify";
        smiv2:oid "1.3.6.1.4.1.6527.3.1.2.2.7.1";
      }
    }
  }
  notification tmnxEqCohOptPortAlarm {
    description
      "The tmnxEqCohOptPortAlarm notification indicates that a coherent
       optical port has experienced either a raising or a clearing of an
       alarm as indicated by the value of tmnxCohOptPortAlarmState. Further
       details can be obtained from the value of tmnxCohOptPortDefectPoints.";
    smiv2:oid "1.3.6.1.4.1.6527.3.1.3.2.2.0.56";
    container object-1 {
      leaf tmnxChassisIndex {
        type leafref {
          path "/timetra-chassis:TIMETRA-CHASSIS-MIB/timetra-chassis:tmnxChassisTable/timetra-chassis:tmnxChassisEntry/timetra-chassis:tmnxChassisIndex";
        }
      }
      leaf tmnxPortPortID {
        type leafref {
          path "/timetra-port:TIMETRA-PORT-MIB/timetra-port:tmnxPortTable/timetra-port:tmnxPortEntry/timetra-port:tmnxPortPortID";
        }
      }
      leaf tmnxCohOptPortAlarmState {
        type leafref {
          path "/timetra-port:TIMETRA-PORT-MIB/timetra-port:tmnxCohOptPortOperTable/timetra-port:tmnxCohOptPortOperEntry/timetra-port:tmnxCohOptPortAlarmState";
        }
      }
    }
    container object-2 {
      leaf tmnxChassisIndex {
        type leafref {
          path "/timetra-chassis:TIMETRA-CHASSIS-MIB/timetra-chassis:tmnxChassisTable/timetra-chassis:tmnxChassisEntry/timetra-chassis:tmnxChassisIndex";
        }
      }
      leaf tmnxPortPortID {
        type leafref {
          path "/timetra-port:TIMETRA-PORT-MIB/timetra-port:tmnxPortTable/timetra-port:tmnxPortEntry/timetra-port:tmnxPortPortID";
        }
      }
      leaf tmnxCohOptPortDefectPoints {
        type leafref {
          path "/timetra-port:TIMETRA-PORT-MIB/timetra-port:tmnxCohOptPortOperTable/timetra-port:tmnxCohOptPortOperEntry/timetra-port:tmnxCohOptPortDefectPoints";
        }
      }
    }
  }
  smiv2:alias "tmnxPortMIBModule" {
    smiv2:oid "1.3.6.1.4.1.6527.1.1.3.25";
  }
  smiv2:alias "tmnxPortConformance" {
    smiv2:oid "1.3.6.1.4.1.6527.3.1.1.2.2";
  }
  smiv2:alias "tmnxPortCompliances" {
    smiv2:oid "1.3.6.1.4.1.6527.3.1.1.2.2.1";
  }
  smiv2:alias "tmnxPortComp7750" {
    smiv2:oid "1.3.6.1.4.1.6527.3.1.1.2.2.1.3";
  }
  smiv2:alias "tmnxPortComp7450" {
    smiv2:oid "1.3.6.1.4.1.6527.3.1.1.2.2.1.4";
  }
  smiv2:alias "tmnxPortComp7710" {
    smiv2:oid "1.3.6.1.4.1.6527.3.1.1.2.2.1.5";
  }
  smiv2:alias "tmnxPortGroups" {
    smiv2:oid "1.3.6.1.4.1.6527.3.1.1.2.2.2";
  }
  smiv2:alias "tmnxPortObjs" {
    smiv2:oid "1.3.6.1.4.1.6527.3.1.2.2.4";
  }
  smiv2:alias "tmnxPortScalarObjs" {
    smiv2:oid "1.3.6.1.4.1.6527.3.1.2.2.4.19";
  }
  smiv2:alias "tmnxPortPlcyObjs" {
    smiv2:oid "1.3.6.1.4.1.6527.3.1.2.2.4.67";
  }
  smiv2:alias "tmnxPortNotificationObjects" {
    smiv2:oid "1.3.6.1.4.1.6527.3.1.2.2.7";
  }
  smiv2:alias "tmnxFRObjs" {
    smiv2:oid "1.3.6.1.4.1.6527.3.1.2.2.9";
  }
  smiv2:alias "tmnxQosAppObjs" {
    smiv2:oid "1.3.6.1.4.1.6527.3.1.2.2.10";
  }
  smiv2:alias "tmnxATMObjs" {
    smiv2:oid "1.3.6.1.4.1.6527.3.1.2.2.11";
  }
  smiv2:alias "tmnxPortStatsObjs" {
    smiv2:oid "1.3.6.1.4.1.6527.3.1.2.2.12";
  }
  smiv2:alias "tmnxPortNotifyPrefix" {
    smiv2:oid "1.3.6.1.4.1.6527.3.1.3.2.2";
  }
  smiv2:alias "tmnxPortNotification" {
    smiv2:oid "1.3.6.1.4.1.6527.3.1.3.2.2.0";
  }
}
