TIMETRA-DIAMETER-MIB DEFINITIONS ::= BEGIN

IMPORTS
    InetAddress, InetAddressType,
    InetPortNumber
                                                         FROM INET-ADDRESS-MIB
    MODULE-COMPLIANCE, NOTIFICATION-GROUP,
    OBJECT-GROUP
                                                         FROM SNMPv2-CONF
    Counter32, Gauge32, MODULE-IDENTITY,
    NOTIFICATION-TYPE, OBJECT-TYPE,
    Unsigned32
                                                         FROM SNMPv2-SMI
    DisplayString, MacAddress, RowStatus,
    TEXTUAL-CONVENTION, TimeStamp,
    TruthValue
                                                         FROM SNMPv2-TC
    timetraSRMIBModules, tmnxSRConfs,
    tmnxSRNotifyPrefix, tmnxSRObjs
                                                         FROM TIMETRA-GLOBAL-MIB
    TEgressQueueId, TItemDescription,
    TNamedItem, TNamedItemOrEmpty,
    TPolicyID, TmnxAuthPassword,
    TmnxBinarySpecification,
    TmnxDiamCcFailureHndlng,
    TmnxEnabledDisabledAdminState,
    TmnxMacSpecification,
    TmnxSubAuthPlcyUserNameOp,
    TmnxSubCallingStationIdType,
    TmnxSubCreditVolumeUnit,
    TmnxSubNasPortPrefixType,
    TmnxSubNasPortSuffixType,
    TmnxSubNasPortTypeType, TmnxVRtrID,
    TmnxVRtrIDOrZero
                                                         FROM TIMETRA-TC-MIB
    ;

timetraDiameterMIBModule         MODULE-IDENTITY
    LAST-UPDATED "201701010000Z"
    ORGANIZATION "Nokia"
    CONTACT-INFO
        "Nokia SROS Support
         Web: http://www.nokia.com"
    DESCRIPTION
        "This document is the SNMP MIB module to manage and provision DIAMETER
         on the Nokia SROS device.

         Copyright 2008-2017 Nokia. All rights reserved. Reproduction of this
         document is authorized on the condition that the foregoing copyright
         notice is included.

         This SNMP MIB module (Specification) embodies Nokia's
         proprietary intellectual property.  Nokia retains
         all title and ownership in the Specification, including any
         revisions.

         Nokia grants all interested parties a non-exclusive license to use and
         distribute an unmodified copy of this Specification in connection with
         management of Nokia products, and without fee, provided this copyright
         notice and license appear on all copies.

         This Specification is supplied 'as is', and Nokia makes no warranty,
         either express or implied, as to the use, operation, condition, or
         performance of the Specification."

    REVISION    "201701010000Z"
    DESCRIPTION
        "Rev 15.0                1 Jan 2017 00:00
         15.0 release of the TIMETRA-DIAMETER-MIB."

    REVISION    "201601010000Z"
    DESCRIPTION
        "Rev 14.0                1 Jan 2016 00:00
         14.0 release of the TIMETRA-DIAMETER-MIB."

    REVISION    "201501010000Z"
    DESCRIPTION
        "Rev 13.0                1 Jan 2015 00:00
         13.0 release of the TIMETRA-DIAMETER-MIB."

    REVISION    "201401010000Z"
    DESCRIPTION
        "Rev 12.0                1 Jan 2014 00:00
         12.0 release of the TIMETRA-DIAMETER-MIB."

    REVISION    "201202280000Z"
    DESCRIPTION
        "Rev 10.0               28 Feb 2012 12:00
         10.0 release of the TIMETRA-DIAMETER-MIB."

    REVISION    "201102010000Z"
    DESCRIPTION
        "Rev 9.0                 1 Feb 2011 00:00
         9.0 release of the TIMETRA-DIAMETER-MIB."

    REVISION    "200902280000Z"
    DESCRIPTION
        "Rev 7.0                28 Feb 2009 00:00
         7.0 release of the TIMETRA-DIAMETER-MIB."

    REVISION    "200807010000Z"
    DESCRIPTION
        "Rev 0.1                01 July 2008 00:00
         Initial version of the TIMETRA-DIAMETER-MIB."

    ::= { timetraSRMIBModules 58 }

TmnxDiamPeerTransportProt        ::= TEXTUAL-CONVENTION
    STATUS      current
    DESCRIPTION
        "The TmnxDiamPeerTransportProt data type is an enumerated integer that
         describes the different transport protocols that can be used to setup
         a DIAMETER connection."
    SYNTAX      INTEGER {
        tcp (1)
    }

TmnxDiamDccaApplicationType      ::= TEXTUAL-CONVENTION
    STATUS      current
    DESCRIPTION
        "The TmnxDiamDccaApplicationType data type is an enumerated integer
         that identifies the different DCCA (Diameter Credit Control
         Application) application types.

         A particular value of TmnxDiamDccaApplicationType is associated with a
         set of values for the Authentication-Application-Id AVP (Attribute
         Value Pair) in Diameter messages."
    SYNTAX      INTEGER {
        vfDccaV2 (1),
        gx       (2)
    }

TmnxDiamPlcyVendorSupportType    ::= TEXTUAL-CONVENTION
    STATUS      current
    DESCRIPTION
        "The TmnxDiamPlcyVendorSupportType data type is an enumerated integer
         that describes which vendor specific attributes are used in DCCA
         sessions."
    SYNTAX      INTEGER {
        vodafone (1),
        threeGpp (2)
    }

TmnxDiamPlcyDccaAvpOriginType    ::= TEXTUAL-CONVENTION
    STATUS      current
    DESCRIPTION
        "The TmnxDiamPlcyDccaAvpOriginType data type is an enumerated integer
         that describes the origin of the information to send in the AVP."
    SYNTAX      INTEGER {
        disabled          (0),
        subscriberId      (1),
        circuitId         (2),
        imsi              (3),
        msisdn            (4),
        imei              (5),
        dualStackRemoteId (6),
        mac               (7),
        username          (8),
        nasPortId         (9)
    }

TmnxDiamProxyState               ::= TEXTUAL-CONVENTION
    STATUS      current
    DESCRIPTION
        "The TmnxDiamProxyState data type is an enumerated integer that
         describes the MCS (Multi-Chassis redundancy Synchronization) state of
         the Diameter proxy function.

         The states 'active' and 'standby' are normal states where Diameter
         communication is possible through the proxy.

         init:                the proxy is setting up the MCS communication with
                              its partner;
         activeWait:          the proxy is setting up the TCP connection with
                              the Diameter server;
         standbyWait:         the proxy is waiting for its MCS partner to become
                              active;
         proxySwitchoverReq:  the proxy was active and is becoming standby."
    SYNTAX      INTEGER {
        init               (1),
        active             (2),
        standby            (3),
        activeWait         (4),
        standbyWait        (5),
        proxySwitchoverReq (6)
    }

TmnxDiamSessionId                ::= TEXTUAL-CONVENTION
    STATUS      current
    DESCRIPTION
        "The TmnxDiamSessionId uniquely identifies a user session. This string
         starts with the tmnxDiamPlcyOriginHost, followed by two numbers
         delimited by a ';' character."
    SYNTAX      DisplayString (SIZE (1..102))

TmnxDiamFqdn                     ::= TEXTUAL-CONVENTION
    STATUS      current
    DESCRIPTION
        "A Fully Qualified Domain Name (FQDN). The FQDN is unique if no
         case-insensitive matching FQDN exist."
    SYNTAX      DisplayString (SIZE (1..80))

TmnxDiamFqdnOrEmpty              ::= TEXTUAL-CONVENTION
    STATUS      current
    DESCRIPTION
        "A Fully Qualified Domain Name (FQDN). The FQDN is unique if no
         case-insensitive matching FQDN exist."
    SYNTAX      DisplayString (SIZE (0..80))

TmnxDiamApGx3gqmAADlMappingType  ::= TEXTUAL-CONVENTION
    STATUS      current
    DESCRIPTION
        "The QoS information in the CCA/RAR msgs is mapped to a qos-override object.
         The TmnxDiamApGx3gqmAADlMappingType data type is an enumerated integer
         that indicates the kind of SR OS qos object the override applies to.
         For the downlink, this can be an aggregate rate, an arbiter, a policer,
         a queue or a scheduler.
         (This is used to determine the value for the APN-AMBR.)
         - noMapping           (0): No mapping.
         - arbiter             (1): Map to an arbiter.
         - policer             (2): Map to a policer.
         - queue               (3): Map to a queue.
         - scheduler           (4): Map to a scheduler.
         - aggregateRate       (5): Map to an aggregate rate.
         - hsSlaAggregateRate  (6): Map to an hs sla aggregate rate."
    SYNTAX      INTEGER {
        noMapping          (0),
        arbiter            (1),
        policer            (2),
        queue              (3),
        scheduler          (4),
        aggregateRate      (5),
        hsSlaAggregateRate (6)
    }

TmnxDiamApGx3gqmAAUlMappingType  ::= TEXTUAL-CONVENTION
    STATUS      current
    DESCRIPTION
        "The QoS information in the CCA/RAR msgs is mapped to a qos-override object.
         The TmnxDiamApGx3gqmAAUlMappingType data type is an enumerated integer
         that indicates the kind of SR OS qos object the override applies to.
         For the uplink, this can be an arbiter, a policer, a queue or a scheduler.
         (This is used to determine the value for the APN-AMBR.)
         - noMapping         (0): No mapping.
         - arbiter           (1): Map to an arbiter.
         - policer           (2): Map to a policer.
         - queue             (3): Map to a queue.
         - scheduler         (4): Map to a scheduler."
    SYNTAX      INTEGER {
        noMapping (0),
        arbiter   (1),
        policer   (2),
        queue     (3),
        scheduler (4)
    }

tmnxDiameter                     OBJECT IDENTIFIER ::= { tmnxSRObjs 58 }

tmnxDiameterBaseObjects          OBJECT IDENTIFIER ::= { tmnxDiameter 1 }

tmnxDiameterPlcyTableLastChngd   OBJECT-TYPE
    SYNTAX      TimeStamp
    MAX-ACCESS  read-only
    STATUS      current
    DESCRIPTION
        "The value of tmnxDiameterPlcyTableLastChngd indicates the sysUpTime at
         the time of the most recent management-initiated change to the
         tmnxDiameterPlcyTable."
    ::= { tmnxDiameterBaseObjects 1 }

tmnxDiameterPlcyTable            OBJECT-TYPE
    SYNTAX      SEQUENCE OF TmnxDiameterPlcyEntry
    MAX-ACCESS  not-accessible
    STATUS      current
    DESCRIPTION
        "The tmnxDiameterPlcyTable has an entry for each DIAMETER  Peer policy
         configured in the system."
    ::= { tmnxDiameterBaseObjects 2 }

tmnxDiameterPlcyEntry            OBJECT-TYPE
    SYNTAX      TmnxDiameterPlcyEntry
    MAX-ACCESS  not-accessible
    STATUS      current
    DESCRIPTION
        "Each row entry represents a DIAMETER peer policy configured in the
         system.

         Entries can be created and deleted via SNMP SET operations on the
         object tmnxDiamPlcyRowStatus."
    INDEX       { tmnxDiamPlcyName }
    ::= { tmnxDiameterPlcyTable 1 }

TmnxDiameterPlcyEntry            ::= SEQUENCE
{
    tmnxDiamPlcyName                 TNamedItem,
    tmnxDiamPlcyRowStatus            RowStatus,
    tmnxDiamPlcyLastMgmtChange       TimeStamp,
    tmnxDiamPlcyDescription          TItemDescription,
    tmnxDiamPlcyOriginHost           DisplayString,
    tmnxDiamPlcyOriginRealm          DisplayString,
    tmnxDiamPlcyRouter               TmnxVRtrID,
    tmnxDiamPlcySourceAddrType       InetAddressType,
    tmnxDiamPlcySourceAddr           InetAddress,
    tmnxDiamPlcyWatchdogTimer        Unsigned32,
    tmnxDiamPlcyConnectionTimer      Unsigned32,
    tmnxDiamPlcyTransactionTimer     Unsigned32,
    tmnxDiamPlcyVendorSupport        TmnxDiamPlcyVendorSupportType,
    tmnxDiamPlcyApplications         BITS,
    tmnxDiamPlcyPythonPolicy         TNamedItemOrEmpty,
    tmnxDiamPlcyRole                 INTEGER,
    tmnxDiamPlcyV6SourceAddrType     InetAddressType,
    tmnxDiamPlcyV6SourceAddr         InetAddress
}

tmnxDiamPlcyName                 OBJECT-TYPE
    SYNTAX      TNamedItem
    MAX-ACCESS  not-accessible
    STATUS      current
    DESCRIPTION
        "The value of tmnxDiamPlcyName specifies the name of the DIAMETER
         policy."
    ::= { tmnxDiameterPlcyEntry 1 }

tmnxDiamPlcyRowStatus            OBJECT-TYPE
    SYNTAX      RowStatus
    MAX-ACCESS  read-create
    STATUS      current
    DESCRIPTION
        "The value of tmnxDiamPlcyRowStatus controls the creation and deletion
         of rows in this table."
    ::= { tmnxDiameterPlcyEntry 2 }

tmnxDiamPlcyLastMgmtChange       OBJECT-TYPE
    SYNTAX      TimeStamp
    MAX-ACCESS  read-only
    STATUS      current
    DESCRIPTION
        "The value of tmnxDiamPlcyLastMgmtChange indicates the sysUpTime at the
         time of the most recent management-initiated change to this table row."
    ::= { tmnxDiameterPlcyEntry 3 }

tmnxDiamPlcyDescription          OBJECT-TYPE
    SYNTAX      TItemDescription
    MAX-ACCESS  read-create
    STATUS      current
    DESCRIPTION
        "The value of tmnxDiamPlcyDescription specifies the user provided
         description of this DIAMETER policy."
    DEFVAL      { "" }
    ::= { tmnxDiameterPlcyEntry 4 }

tmnxDiamPlcyOriginHost           OBJECT-TYPE
    SYNTAX      DisplayString (SIZE (0..80))
    MAX-ACCESS  read-create
    STATUS      current
    DESCRIPTION
        "The value of tmnxDiamPlcyOriginHost specifies the Origin-Host AVP
         (Attribute Value Pair) used by this DIAMETER policy."
    DEFVAL      { "" }
    ::= { tmnxDiameterPlcyEntry 5 }

tmnxDiamPlcyOriginRealm          OBJECT-TYPE
    SYNTAX      DisplayString (SIZE (0..80))
    MAX-ACCESS  read-create
    STATUS      current
    DESCRIPTION
        "The value of tmnxDiamPlcyOriginRealm specifies the Origin-Realm AVP
         (Attribute Value Pair) used by this DIAMETER policy."
    DEFVAL      { "" }
    ::= { tmnxDiameterPlcyEntry 6 }

tmnxDiamPlcyRouter               OBJECT-TYPE
    SYNTAX      TmnxVRtrID
    MAX-ACCESS  read-create
    STATUS      current
    DESCRIPTION
        "The value of tmnxDiamPlcyRouter specifies the virtual router in which
         the DIAMETER connection(s) will be established by this DIAMETER
         policy."
    DEFVAL      { 1 }
    ::= { tmnxDiameterPlcyEntry 7 }

tmnxDiamPlcySourceAddrType       OBJECT-TYPE
    SYNTAX      InetAddressType
    MAX-ACCESS  read-create
    STATUS      current
    DESCRIPTION
        "The value of tmnxDiamPlcySourceAddrType specifies the type of address
         contained in tmnxDiamPlcySourceAddr."
    DEFVAL      { unknown }
    ::= { tmnxDiameterPlcyEntry 8 }

tmnxDiamPlcySourceAddr           OBJECT-TYPE
    SYNTAX      InetAddress (SIZE (0|4))
    MAX-ACCESS  read-create
    STATUS      current
    DESCRIPTION
        "The value of tmnxDiamPlcySourceAddr specifies the source IP address
         used to setup DIAMETER connection in this DIAMETER policy."
    DEFVAL      { ''H }
    ::= { tmnxDiameterPlcyEntry 9 }

tmnxDiamPlcyWatchdogTimer        OBJECT-TYPE
    SYNTAX      Unsigned32 (1..1000)
    UNITS       "seconds"
    MAX-ACCESS  read-create
    STATUS      current
    DESCRIPTION
        "The value of tmnxDiamPlcyWatchdogTimer specifies the device watchdog
         timer (TW) (in seconds) used on all connections by this DIAMETER
         policy."
    DEFVAL      { 30 }
    ::= { tmnxDiameterPlcyEntry 10 }

tmnxDiamPlcyConnectionTimer      OBJECT-TYPE
    SYNTAX      Unsigned32 (1..1000)
    UNITS       "seconds"
    MAX-ACCESS  read-create
    STATUS      current
    DESCRIPTION
        "The value of tmnxDiamPlcyConnectionTimer specifies the connection
         timer (TC) (in seconds) used by this DIAMETER policy. It defines the
         time the systems waits before attempting to reconnect to a peer after
         the connection was lost."
    DEFVAL      { 30 }
    ::= { tmnxDiameterPlcyEntry 11 }

tmnxDiamPlcyTransactionTimer     OBJECT-TYPE
    SYNTAX      Unsigned32 (1..1000)
    UNITS       "seconds"
    MAX-ACCESS  read-create
    STATUS      current
    DESCRIPTION
        "The value of tmnxDiamPlcyTransactionTimer specifies the transaction
         timer (in seconds) used by this DIAMETER policy. This timer defines
         how long the system will wait for an answer from the peer after
         sending a request."
    DEFVAL      { 30 }
    ::= { tmnxDiameterPlcyEntry 12 }

tmnxDiamPlcyVendorSupport        OBJECT-TYPE
    SYNTAX      TmnxDiamPlcyVendorSupportType
    MAX-ACCESS  read-create
    STATUS      current
    DESCRIPTION
        "The value of tmnxDiamPlcyVendorSupport specifies which vendor specific
         attributes are used in DCCA sessions for this DIAMETER policy."
    DEFVAL      { threeGpp }
    ::= { tmnxDiameterPlcyEntry 13 }

tmnxDiamPlcyApplications         OBJECT-TYPE
    SYNTAX      BITS {
        gx     (0),
        gy     (1),
        nasreq (2)
    }
    MAX-ACCESS  read-create
    STATUS      current
    DESCRIPTION
        "The value of tmnxDiamPlcyApplications specifies the supported
         applications of this DIAMETER peer policy."
    DEFVAL      { {} }
    ::= { tmnxDiameterPlcyEntry 15 }

tmnxDiamPlcyPythonPolicy         OBJECT-TYPE
    SYNTAX      TNamedItemOrEmpty
    MAX-ACCESS  read-create
    STATUS      current
    DESCRIPTION
        "The value of tmnxDiamPlcyPythonPolicy specifies the Python policy used
         by this DIAMETER policy for modifying DIAMETER messages.

         The specified Python policy needs to exists in the
         TIMETRA-PYTHON-MIB::tmnxPythonPolicyTable."
    DEFVAL      { "" }
    ::= { tmnxDiameterPlcyEntry 16 }

tmnxDiamPlcyRole                 OBJECT-TYPE
    SYNTAX      INTEGER {
        client (0),
        proxy  (1)
    }
    MAX-ACCESS  read-create
    STATUS      current
    DESCRIPTION
        "The value of tmnxDiamPlcyRole specifies the role this DIAMETER peer
         policy performs.

         In the 'client' role, this policy is applied to transmitting and
         receiving DIAMETER messages to a server, on behalf of a client
         application within this system.

         In the 'proxy' role, this policy is applied to transmitting and
         receiving DIAMETER messages to a server, on behalf of another system
         performing the 'client' role.

         The value of tmnxDiamPlcyRole can only be modified while creating this
         conceptual row."
    DEFVAL      { client }
    ::= { tmnxDiameterPlcyEntry 17 }

tmnxDiamPlcyV6SourceAddrType     OBJECT-TYPE
    SYNTAX      InetAddressType
    MAX-ACCESS  read-create
    STATUS      current
    DESCRIPTION
        "The value of tmnxDiamPlcyV6SourceAddrType specifies the type of
         address contained in tmnxDiamPlcyV6SourceAddr."
    DEFVAL      { unknown }
    ::= { tmnxDiameterPlcyEntry 18 }

tmnxDiamPlcyV6SourceAddr         OBJECT-TYPE
    SYNTAX      InetAddress (SIZE (0|16))
    MAX-ACCESS  read-create
    STATUS      current
    DESCRIPTION
        "The value of tmnxDiamPlcyV6SourceAddr specifies the source IPv6
         address used to setup DIAMETER connection in this DIAMETER policy."
    DEFVAL      { ''H }
    ::= { tmnxDiameterPlcyEntry 19 }

tmnxDiamPlcyPeerTableLastChngd   OBJECT-TYPE
    SYNTAX      TimeStamp
    MAX-ACCESS  read-only
    STATUS      current
    DESCRIPTION
        "The value of tmnxDiamPlcyPeerTableLastChngd indicates the sysUpTime at
         the time of the most recent management-initiated change to the
         tmnxDiameterPlcyPeerTable."
    ::= { tmnxDiameterBaseObjects 3 }

tmnxDiameterPlcyPeerTable        OBJECT-TYPE
    SYNTAX      SEQUENCE OF TmnxDiameterPlcyPeerEntry
    MAX-ACCESS  not-accessible
    STATUS      current
    DESCRIPTION
        "The tmnxDiameterPlcyPeerTable has an entry for each peer defined in a
         DIAMETER policy configured in the system."
    ::= { tmnxDiameterBaseObjects 4 }

tmnxDiameterPlcyPeerEntry        OBJECT-TYPE
    SYNTAX      TmnxDiameterPlcyPeerEntry
    MAX-ACCESS  not-accessible
    STATUS      current
    DESCRIPTION
        "Each row entry represents a peer configured in a DIAMETER policy
         configured in the system.

         Entries can be created and deleted via SNMP SET operations on the
         object tmnxDiamPlcyPeerRowStatus."
    INDEX       {
        tmnxDiamPlcyName,
        tmnxDiamPlcyPeerName
    }
    ::= { tmnxDiameterPlcyPeerTable 1 }

TmnxDiameterPlcyPeerEntry        ::= SEQUENCE
{
    tmnxDiamPlcyPeerName             TNamedItem,
    tmnxDiamPlcyPeerRowStatus        RowStatus,
    tmnxDiamPlcyPeerLastMgmtChange   TimeStamp,
    tmnxDiamPlcyPeerAdminState       TmnxEnabledDisabledAdminState,
    tmnxDiamPlcyPeerAddrType         InetAddressType,
    tmnxDiamPlcyPeerAddr             InetAddress,
    tmnxDiamPlcyPeerTransportProt    TmnxDiamPeerTransportProt,
    tmnxDiamPlcyPeerTransportPort    Unsigned32,
    tmnxDiamPlcyPeerDestHost         DisplayString,
    tmnxDiamPlcyPeerDestRealm        DisplayString,
    tmnxDiamPlcyPeerWatchdogTimer    Unsigned32,
    tmnxDiamPlcyPeerConnectionTimer  Unsigned32,
    tmnxDiamPlcyPeerTransactTimer    Unsigned32,
    tmnxDiamPlcyPeerPreference       Unsigned32
}

tmnxDiamPlcyPeerName             OBJECT-TYPE
    SYNTAX      TNamedItem
    MAX-ACCESS  not-accessible
    STATUS      current
    DESCRIPTION
        "The value of tmnxDiamPlcyPeerName specifies the name of the peer
         within a DIAMETER policy."
    ::= { tmnxDiameterPlcyPeerEntry 1 }

tmnxDiamPlcyPeerRowStatus        OBJECT-TYPE
    SYNTAX      RowStatus
    MAX-ACCESS  read-create
    STATUS      current
    DESCRIPTION
        "The value of tmnxDiamPlcyPeerRowStatus controls the creation and
         deletion of rows in this table."
    ::= { tmnxDiameterPlcyPeerEntry 2 }

tmnxDiamPlcyPeerLastMgmtChange   OBJECT-TYPE
    SYNTAX      TimeStamp
    MAX-ACCESS  read-only
    STATUS      current
    DESCRIPTION
        "The value of tmnxDiamPlcyPeerLastMgmtChange indicates the sysUpTime at
         the time of the most recent management-initiated change to this table
         row."
    ::= { tmnxDiameterPlcyPeerEntry 3 }

tmnxDiamPlcyPeerAdminState       OBJECT-TYPE
    SYNTAX      TmnxEnabledDisabledAdminState
    MAX-ACCESS  read-create
    STATUS      current
    DESCRIPTION
        "The value of the object tmnxDiamPlcyPeerAdminState specifies the
         administrative state of the DIAMETER Policy peer."
    DEFVAL      { disabled }
    ::= { tmnxDiameterPlcyPeerEntry 4 }

tmnxDiamPlcyPeerAddrType         OBJECT-TYPE
    SYNTAX      InetAddressType
    MAX-ACCESS  read-create
    STATUS      current
    DESCRIPTION
        "The value of tmnxDiamPlcyPeerAddrType specifies the type of address
         contained in tmnxDiamPlcyPeerAddr."
    DEFVAL      { unknown }
    ::= { tmnxDiameterPlcyPeerEntry 5 }

tmnxDiamPlcyPeerAddr             OBJECT-TYPE
    SYNTAX      InetAddress (SIZE (0|4|16))
    MAX-ACCESS  read-create
    STATUS      current
    DESCRIPTION
        "The value of tmnxDiamPlcyPeerAddr specifies the IP address of this
         DIAMETER policy peer."
    DEFVAL      { ''H }
    ::= { tmnxDiameterPlcyPeerEntry 6 }

tmnxDiamPlcyPeerTransportProt    OBJECT-TYPE
    SYNTAX      TmnxDiamPeerTransportProt
    MAX-ACCESS  read-create
    STATUS      current
    DESCRIPTION
        "The value of tmnxDiamPlcyPeerTransportProt specifies the transport
         protocol used towards this DIAMETER policy peer."
    DEFVAL      { tcp }
    ::= { tmnxDiameterPlcyPeerEntry 7 }

tmnxDiamPlcyPeerTransportPort    OBJECT-TYPE
    SYNTAX      Unsigned32 (1..65535)
    MAX-ACCESS  read-create
    STATUS      current
    DESCRIPTION
        "The value of tmnxDiamPlcyPeerTransportPort specifies the transport
         protocol port number used towards this DIAMETER policy peer."
    DEFVAL      { 3868 }
    ::= { tmnxDiameterPlcyPeerEntry 8 }

tmnxDiamPlcyPeerDestHost         OBJECT-TYPE
    SYNTAX      DisplayString (SIZE (0..80))
    MAX-ACCESS  read-create
    STATUS      current
    DESCRIPTION
        "The value of tmnxDiamPlcyPeerDestHost specifies the Destination-Host
         AVP used by this DIAMETER policy peer."
    DEFVAL      { "" }
    ::= { tmnxDiameterPlcyPeerEntry 9 }

tmnxDiamPlcyPeerDestRealm        OBJECT-TYPE
    SYNTAX      DisplayString (SIZE (0..80))
    MAX-ACCESS  read-create
    STATUS      current
    DESCRIPTION
        "The value of tmnxDiamPlcyPeerDestRealm specifies the Destination-Realm
         AVP used by this DIAMETER policy peer."
    DEFVAL      { "" }
    ::= { tmnxDiameterPlcyPeerEntry 10 }

tmnxDiamPlcyPeerWatchdogTimer    OBJECT-TYPE
    SYNTAX      Unsigned32 (0..1000)
    UNITS       "seconds"
    MAX-ACCESS  read-create
    STATUS      current
    DESCRIPTION
        "The value of tmnxDiamPlcyPeerWatchdogTimer specifies the device
         watchdog timer (in seconds) used by this DIAMETER policy peer.

         A value '0' will cause the peer to use the watchdog timer defined at
         DIAMETER base level (tmnxDiamPlcyWatchdogTimer)."
    DEFVAL      { 0 }
    ::= { tmnxDiameterPlcyPeerEntry 11 }

tmnxDiamPlcyPeerConnectionTimer  OBJECT-TYPE
    SYNTAX      Unsigned32 (0..1000)
    UNITS       "seconds"
    MAX-ACCESS  read-create
    STATUS      current
    DESCRIPTION
        "The value of tmnxDiamPlcyPeerConnectionTimer specifies the device
         connection timer (in seconds) used by this DIAMETER policy peer.

         A value '0' will cause the peer to use the connection timer defined at
         DIAMETER base level (tmnxDiamPlcyConnectionTimer)."
    DEFVAL      { 0 }
    ::= { tmnxDiameterPlcyPeerEntry 12 }

tmnxDiamPlcyPeerTransactTimer    OBJECT-TYPE
    SYNTAX      Unsigned32 (0..1000)
    UNITS       "seconds"
    MAX-ACCESS  read-create
    STATUS      current
    DESCRIPTION
        "The value of tmnxDiamPlcyPeerTransactTimer specifies the device
         transaction timer (in seconds) used by this DIAMETER policy peer.

         A value '0' will cause the peer to use the transaction timer defined
         at DIAMETER base level (tmnxDiamPlcyTransactionTimer)."
    DEFVAL      { 0 }
    ::= { tmnxDiameterPlcyPeerEntry 13 }

tmnxDiamPlcyPeerPreference       OBJECT-TYPE
    SYNTAX      Unsigned32 (1..100)
    MAX-ACCESS  read-create
    STATUS      current
    DESCRIPTION
        "The value of tmnxDiamPlcyPeerPreference specifies the preference given
         to this DIAMETER policy peer with respect to the other peers
         associated with this DIAMETER policy.

         If multiple peers are available for this policy, only the available
         peer with the highest preference will be used.

         If multiple peers with the same preference are available, one of them
         will be used.

         The highest preference is specified by the value '1'."
    DEFVAL      { 50 }
    ::= { tmnxDiameterPlcyPeerEntry 14 }

tmnxDiamPlcyPeerInfoTable        OBJECT-TYPE
    SYNTAX      SEQUENCE OF TmnxDiamPlcyPeerInfoEntry
    MAX-ACCESS  not-accessible
    STATUS      current
    DESCRIPTION
        "The tmnxDiamPlcyPeerInfoTable contains detailed runtime information
         about the peers defined in a DIAMETER policy."
    ::= { tmnxDiameterBaseObjects 5 }

tmnxDiamPlcyPeerInfoEntry        OBJECT-TYPE
    SYNTAX      TmnxDiamPlcyPeerInfoEntry
    MAX-ACCESS  not-accessible
    STATUS      current
    DESCRIPTION
        "Each conceptual row contains detailed runtime information about a peer
         defined in a DIAMETER policy.

         Entries in this table are created and removed automatically by the
         system"
    AUGMENTS    { tmnxDiameterPlcyPeerEntry }
    ::= { tmnxDiamPlcyPeerInfoTable 1 }

TmnxDiamPlcyPeerInfoEntry        ::= SEQUENCE
{
    tmnxDiamPeerPsmState             INTEGER,
    tmnxDiamPeerConnectionSuspended  TruthValue,
    tmnxDiamPeerCooldownSeqStage     INTEGER,
    tmnxDiamPeerOrder                Unsigned32,
    tmnxDiamPeerPrimarySecondary     INTEGER,
    tmnxDiamPeerTcTimerTimeLeft      Unsigned32,
    tmnxDiamPeerTtTimerTimeLeft      Unsigned32,
    tmnxDiamPeerTwTimerTimeLeft      Unsigned32,
    tmnxDiamPeerWatchdogAlgActive    TruthValue,
    tmnxDiamPeerWatchdogAnswPending  TruthValue,
    tmnxDiamPeerCooldownSeqPending   TruthValue,
    tmnxDiamPeerCooldownSeqActive    TruthValue,
    tmnxDiamPeerPeerRemovalPending   TruthValue,
    tmnxDiamPeerPendingMsgsPMQ       Gauge32
}

tmnxDiamPeerPsmState             OBJECT-TYPE
    SYNTAX      INTEGER {
        closed        (0),
        wait-conn-ack (1),
        wait-i-cea    (2),
        i-open        (3),
        closing       (4)
    }
    MAX-ACCESS  read-only
    STATUS      current
    DESCRIPTION
        "The value of tmnxDiamPeerPsmState indicates the current state of the
         DIAMETER peer's state machine."
    ::= { tmnxDiamPlcyPeerInfoEntry 1 }

tmnxDiamPeerConnectionSuspended  OBJECT-TYPE
    SYNTAX      TruthValue
    MAX-ACCESS  read-only
    STATUS      current
    DESCRIPTION
        "The value of tmnxDiamPeerConnectionSuspended indicates whether the
         peer's DIAMETER connection that is in I-Open state has been
         temporarily put on suspension."
    ::= { tmnxDiamPlcyPeerInfoEntry 2 }

tmnxDiamPeerCooldownSeqStage     OBJECT-TYPE
    SYNTAX      INTEGER {
        stage1 (0),
        stage2 (1),
        stage3 (2)
    }
    MAX-ACCESS  read-only
    STATUS      current
    DESCRIPTION
        "While the value of tmnxDiamPeerCooldownSeqActive is 'true', the value
         of tmnxDiamPeerCooldownSeqStage indicates the current stage of the
         cooling down sequence."
    ::= { tmnxDiamPlcyPeerInfoEntry 3 }

tmnxDiamPeerOrder                OBJECT-TYPE
    SYNTAX      Unsigned32
    MAX-ACCESS  read-only
    STATUS      current
    DESCRIPTION
        "The value of tmnxDiamPeerOrder indicates the runtime order of the
         DIAMETER policy's peers. It is determined both by the configuration
         level preference and other runtime conditions.

         A value of zero indicates this field is currently not applicable for
         this peer."
    ::= { tmnxDiamPlcyPeerInfoEntry 4 }

tmnxDiamPeerPrimarySecondary     OBJECT-TYPE
    SYNTAX      INTEGER {
        none      (0),
        primary   (1),
        secondary (2)
    }
    MAX-ACCESS  read-only
    STATUS      current
    DESCRIPTION
        "The value of tmnxDiamPeerPrimarySecondary indicates whether the
         DIAMETER peer figures as primary or secondary peer in its policy."
    ::= { tmnxDiamPlcyPeerInfoEntry 5 }

tmnxDiamPeerTcTimerTimeLeft      OBJECT-TYPE
    SYNTAX      Unsigned32
    MAX-ACCESS  read-only
    STATUS      current
    DESCRIPTION
        "The value of tmnxDiamPeerTcTimerTimeLeft indicates the current
         countdown progress of the DIAMETER peer's connection timer."
    ::= { tmnxDiamPlcyPeerInfoEntry 6 }

tmnxDiamPeerTtTimerTimeLeft      OBJECT-TYPE
    SYNTAX      Unsigned32
    MAX-ACCESS  read-only
    STATUS      current
    DESCRIPTION
        "The value of tmnxDiamPeerTtTimerTimeLeft indicates the current
         countdown progress of the DIAMETER peer's transaction timer."
    ::= { tmnxDiamPlcyPeerInfoEntry 7 }

tmnxDiamPeerTwTimerTimeLeft      OBJECT-TYPE
    SYNTAX      Unsigned32
    MAX-ACCESS  read-only
    STATUS      current
    DESCRIPTION
        "The value of tmnxDiamPeerTwTimerTimeLeft indicates the current
         countdown progress of the DIAMETER peer's watchdog timer."
    ::= { tmnxDiamPlcyPeerInfoEntry 8 }

tmnxDiamPeerWatchdogAlgActive    OBJECT-TYPE
    SYNTAX      TruthValue
    MAX-ACCESS  read-only
    STATUS      current
    DESCRIPTION
        "The value of tmnxDiamPeerWatchdogAlgActive indicates whether the
         DIAMETER application-layer watchdog algorithm is currently running."
    ::= { tmnxDiamPlcyPeerInfoEntry 9 }

tmnxDiamPeerWatchdogAnswPending  OBJECT-TYPE
    SYNTAX      TruthValue
    MAX-ACCESS  read-only
    STATUS      current
    DESCRIPTION
        "The value of tmnxDiamPeerWatchdogAnswPending indicates whether
         reception of a DIAMETER Device Watchdog Answer (DWA) is expected for a
         corresponding Device Watchdog Request (DWR) waiting in the Pending
         Message Queue (PMQ)."
    ::= { tmnxDiamPlcyPeerInfoEntry 10 }

tmnxDiamPeerCooldownSeqPending   OBJECT-TYPE
    SYNTAX      TruthValue
    MAX-ACCESS  read-only
    STATUS      current
    DESCRIPTION
        "The value of tmnxDiamPeerCooldownSeqPending indicates whether the
         DIAMETER peer's connection manages to get in a non-suspended I-Open
         state."
    ::= { tmnxDiamPlcyPeerInfoEntry 11 }

tmnxDiamPeerCooldownSeqActive    OBJECT-TYPE
    SYNTAX      TruthValue
    MAX-ACCESS  read-only
    STATUS      current
    DESCRIPTION
        "The value of tmnxDiamPeerCooldownSeqActive indicates whether the
         DIAMETER Cooldown Sequence is currently running."
    ::= { tmnxDiamPlcyPeerInfoEntry 12 }

tmnxDiamPeerPeerRemovalPending   OBJECT-TYPE
    SYNTAX      TruthValue
    MAX-ACCESS  read-only
    STATUS      current
    DESCRIPTION
        "The value of tmnxDiamPeerPeerRemovalPending indicates whether the
         execution of a DIAMETER peer's removal is still pending until the
         disconnect-peer roundtrip has finished."
    ::= { tmnxDiamPlcyPeerInfoEntry 13 }

tmnxDiamPeerPendingMsgsPMQ       OBJECT-TYPE
    SYNTAX      Gauge32
    MAX-ACCESS  read-only
    STATUS      current
    DESCRIPTION
        "The value of tmnxDiamPeerPendingMsgsPMQ indicates the number of
         request messages in the Pending Message Queue waiting to be matched
         with the corresponding answer messages from the server."
    ::= { tmnxDiamPlcyPeerInfoEntry 14 }

tmnxDiamPlcyPeerStatsTable       OBJECT-TYPE
    SYNTAX      SEQUENCE OF TmnxDiamPlcyPeerStatsEntry
    MAX-ACCESS  not-accessible
    STATUS      obsolete
    DESCRIPTION
        "The tmnxDiamPlcyPeerStatsTable contains detailed statistics about the
         peers defined in a DIAMETER policy.

         This table was made obsolete in release 14.0. Is is replaced by
         tmnxDiamPeerStatsTable."
    ::= { tmnxDiameterBaseObjects 6 }

tmnxDiamPlcyPeerStatsEntry       OBJECT-TYPE
    SYNTAX      TmnxDiamPlcyPeerStatsEntry
    MAX-ACCESS  not-accessible
    STATUS      obsolete
    DESCRIPTION
        "Each conceptual row contains detailed statistics about a peer defined
         in a DIAMETER policy.

         Entries in this table are created and removed automatically by the
         system"
    AUGMENTS    { tmnxDiameterPlcyPeerEntry }
    ::= { tmnxDiamPlcyPeerStatsTable 1 }

TmnxDiamPlcyPeerStatsEntry       ::= SEQUENCE
{
    tmnxDiamPeerStatsLastClearTime   TimeStamp,
    tmnxDiamPeerStCiTcpSendFailed    Counter32,
    tmnxDiamPeerStCiDiamRxDropCnt    Counter32,
    tmnxDiamPeerStCiDiamTxReqs       Counter32,
    tmnxDiamPeerStCiDiamRxResps      Counter32,
    tmnxDiamPeerStCiPendMsgsPMQ      Counter32,
    tmnxDiamPeerStCiReqTimeoutsPMQ   Counter32,
    tmnxDiamPeerStSiTcpSendFailed    Counter32,
    tmnxDiamPeerStSiDiamRxDropCnt    Counter32,
    tmnxDiamPeerStSiDiamRxReqs       Counter32,
    tmnxDiamPeerStSiDiamTxResps      Counter32,
    tmnxDiamPeerStErrHdlDiamTxErrCnt Counter32,
    tmnxDiamPeerStErrHdlDiamRxErrCnt Counter32,
    tmnxDiamPeerStCcrInitialTx       Counter32,
    tmnxDiamPeerStCcaInitialRx       Counter32,
    tmnxDiamPeerStCcrUpdateTx        Counter32,
    tmnxDiamPeerStCcaUpdateRx        Counter32,
    tmnxDiamPeerStCcrTerminateTx     Counter32,
    tmnxDiamPeerStCcaTerminateRx     Counter32,
    tmnxDiamPeerStCerTx              Counter32,
    tmnxDiamPeerStCeaRx              Counter32,
    tmnxDiamPeerStWdrTx              Counter32,
    tmnxDiamPeerStWdaRx              Counter32,
    tmnxDiamPeerStWdrRx              Counter32,
    tmnxDiamPeerStWdaTx              Counter32,
    tmnxDiamPeerStAsrRx              Counter32,
    tmnxDiamPeerStAsaTx              Counter32,
    tmnxDiamPeerStRarRx              Counter32,
    tmnxDiamPeerStRaaTx              Counter32,
    tmnxDiamPeerStDprTx              Counter32,
    tmnxDiamPeerStDpaRx              Counter32,
    tmnxDiamPeerStDprRx              Counter32,
    tmnxDiamPeerStDpaTx              Counter32,
    tmnxDiamPeerStAarTx              Counter32,
    tmnxDiamPeerStAaaRx              Counter32
}

tmnxDiamPeerStatsLastClearTime   OBJECT-TYPE
    SYNTAX      TimeStamp
    MAX-ACCESS  read-only
    STATUS      obsolete
    DESCRIPTION
        "The value of tmnxDiamPeerStatsLastClearTime indicates the sysUpTime
         when the counters of this row were last reset. A value of zero for
         this object indicates that the counters have not been reset since the
         system has last been initialized."
    ::= { tmnxDiamPlcyPeerStatsEntry 1 }

tmnxDiamPeerStCiTcpSendFailed    OBJECT-TYPE
    SYNTAX      Counter32
    MAX-ACCESS  read-only
    STATUS      obsolete
    DESCRIPTION
        "The value of tmnxDiamPeerStCiTcpSendFailed indicates client initiated
         roundtrip DIAMETER statistics regarding the number of TCP send
         failures."
    ::= { tmnxDiamPlcyPeerStatsEntry 2 }

tmnxDiamPeerStCiDiamRxDropCnt    OBJECT-TYPE
    SYNTAX      Counter32
    MAX-ACCESS  read-only
    STATUS      obsolete
    DESCRIPTION
        "The value of tmnxDiamPeerStCiDiamRxDropCnt indicates client initiated
         roundtrip DIAMETER statistics regarding the number of dropped response
         messages upon reception from server."
    ::= { tmnxDiamPlcyPeerStatsEntry 3 }

tmnxDiamPeerStCiDiamTxReqs       OBJECT-TYPE
    SYNTAX      Counter32
    MAX-ACCESS  read-only
    STATUS      obsolete
    DESCRIPTION
        "The value of tmnxDiamPeerStCiDiamTxReqs indicates client initiated
         roundtrip DIAMETER statistics regarding the number of request messages
         sent to server."
    ::= { tmnxDiamPlcyPeerStatsEntry 4 }

tmnxDiamPeerStCiDiamRxResps      OBJECT-TYPE
    SYNTAX      Counter32
    MAX-ACCESS  read-only
    STATUS      obsolete
    DESCRIPTION
        "The value of tmnxDiamPeerStCiDiamRxResps indicates client initiated
         roundtrip DIAMETER statistics regarding the number of response
         messages received from server."
    ::= { tmnxDiamPlcyPeerStatsEntry 5 }

tmnxDiamPeerStCiPendMsgsPMQ      OBJECT-TYPE
    SYNTAX      Counter32
    MAX-ACCESS  read-only
    STATUS      obsolete
    DESCRIPTION
        "The value of tmnxDiamPeerStCiPendMsgsPMQ indicates client initiated
         roundtrip DIAMETER statistics regarding the number of request messages
         in the Pending Message Queue waiting to be matched with corresponding
         response messages from the server.

         This object is made obsolete in release 14.0. It is replaced by
         tmnxDiamPeerPendingMsgsPMQ."
    ::= { tmnxDiamPlcyPeerStatsEntry 6 }

tmnxDiamPeerStCiReqTimeoutsPMQ   OBJECT-TYPE
    SYNTAX      Counter32
    MAX-ACCESS  read-only
    STATUS      obsolete
    DESCRIPTION
        "The value of tmnxDiamPeerStCiReqTimeoutsPMQ indicates client initiated
         roundtrip DIAMETER statistics regarding the number of request messages
         that were removed from the Pending Message Queue due to a match
         timeout."
    ::= { tmnxDiamPlcyPeerStatsEntry 7 }

tmnxDiamPeerStSiTcpSendFailed    OBJECT-TYPE
    SYNTAX      Counter32
    MAX-ACCESS  read-only
    STATUS      obsolete
    DESCRIPTION
        "The value of tmnxDiamPeerStSiTcpSendFailed indicates client initiated
         roundtrip DIAMETER statistics regarding the number of TCP send
         failures."
    ::= { tmnxDiamPlcyPeerStatsEntry 8 }

tmnxDiamPeerStSiDiamRxDropCnt    OBJECT-TYPE
    SYNTAX      Counter32
    MAX-ACCESS  read-only
    STATUS      obsolete
    DESCRIPTION
        "The value of tmnxDiamPeerStSiDiamRxDropCnt indicates client initiated
         roundtrip DIAMETER statistics regarding the number of dropped request
         messages upon reception from server."
    ::= { tmnxDiamPlcyPeerStatsEntry 9 }

tmnxDiamPeerStSiDiamRxReqs       OBJECT-TYPE
    SYNTAX      Counter32
    MAX-ACCESS  read-only
    STATUS      obsolete
    DESCRIPTION
        "The value of tmnxDiamPeerStSiDiamRxReqs indicates client initiated
         roundtrip DIAMETER statistics regarding the number of request messages
         received from server."
    ::= { tmnxDiamPlcyPeerStatsEntry 10 }

tmnxDiamPeerStSiDiamTxResps      OBJECT-TYPE
    SYNTAX      Counter32
    MAX-ACCESS  read-only
    STATUS      obsolete
    DESCRIPTION
        "The value of tmnxDiamPeerStSiDiamTxResps indicates client initiated
         roundtrip DIAMETER statistics regarding the number of response
         messages sent to server."
    ::= { tmnxDiamPlcyPeerStatsEntry 11 }

tmnxDiamPeerStErrHdlDiamTxErrCnt OBJECT-TYPE
    SYNTAX      Counter32
    MAX-ACCESS  read-only
    STATUS      obsolete
    DESCRIPTION
        "The value of this object is always equal to zero."
    ::= { tmnxDiamPlcyPeerStatsEntry 12 }

tmnxDiamPeerStErrHdlDiamRxErrCnt OBJECT-TYPE
    SYNTAX      Counter32
    MAX-ACCESS  read-only
    STATUS      obsolete
    DESCRIPTION
        "The value of this object is always equal to zero."
    ::= { tmnxDiamPlcyPeerStatsEntry 13 }

tmnxDiamPeerStCcrInitialTx       OBJECT-TYPE
    SYNTAX      Counter32
    MAX-ACCESS  read-only
    STATUS      obsolete
    DESCRIPTION
        "The value of tmnxDiamPeerStCcrInitialTx indicates the number of Credit
         Control Request messages with CC-Request-Type AVP equal to
         INITIAL_REQUEST that are transmitted to the server."
    REFERENCE
        "RFC 4006  Diameter Credit-Control Application,
         section 8.3 and Appendix A1."
    ::= { tmnxDiamPlcyPeerStatsEntry 14 }

tmnxDiamPeerStCcaInitialRx       OBJECT-TYPE
    SYNTAX      Counter32
    MAX-ACCESS  read-only
    STATUS      obsolete
    DESCRIPTION
        "The value of tmnxDiamPeerStCcaInitialRx indicates the number of Credit
         Control Answer messages in response to the CCR INITIAL_REQUEST that
         are received from the server."
    REFERENCE
        "RFC 4006  Diameter Credit-Control Application,
         section 8.3 and Appendix A1."
    ::= { tmnxDiamPlcyPeerStatsEntry 15 }

tmnxDiamPeerStCcrUpdateTx        OBJECT-TYPE
    SYNTAX      Counter32
    MAX-ACCESS  read-only
    STATUS      obsolete
    DESCRIPTION
        "The value of tmnxDiamPeerStCcrUpdateTx indicates the number of Credit
         Control Request messages with CC-Request-Type AVP equal to
         UPDATE_REQUEST that are transmitted to the server."
    REFERENCE
        "RFC 4006  Diameter Credit-Control Application,
         section 8.3 and Appendix A1."
    ::= { tmnxDiamPlcyPeerStatsEntry 16 }

tmnxDiamPeerStCcaUpdateRx        OBJECT-TYPE
    SYNTAX      Counter32
    MAX-ACCESS  read-only
    STATUS      obsolete
    DESCRIPTION
        "The value of tmnxDiamPeerStCcaUpdateRx indicates the number of Credit
         Control Answer messages in response to the CCR UPDATE_REQUEST that are
         received from the server."
    REFERENCE
        "RFC 4006  Diameter Credit-Control Application,
         section 8.3 and Appendix A1."
    ::= { tmnxDiamPlcyPeerStatsEntry 17 }

tmnxDiamPeerStCcrTerminateTx     OBJECT-TYPE
    SYNTAX      Counter32
    MAX-ACCESS  read-only
    STATUS      obsolete
    DESCRIPTION
        "The value of tmnxDiamPeerStCcrTerminateTx indicates the number of
         Credit Control Request messages with CC-Request-Type AVP equal to
         TERMINATION_REQUEST that are transmitted to the server."
    REFERENCE
        "RFC 4006  Diameter Credit-Control Application,
         section 8.3 and Appendix A1."
    ::= { tmnxDiamPlcyPeerStatsEntry 18 }

tmnxDiamPeerStCcaTerminateRx     OBJECT-TYPE
    SYNTAX      Counter32
    MAX-ACCESS  read-only
    STATUS      obsolete
    DESCRIPTION
        "The value of tmnxDiamPeerStCcaTerminateRx indicates the number of
         Credit Control Answer messages in response to the CCR
         TERMINATION_REQUEST that are received from the server."
    REFERENCE
        "RFC 4006  Diameter Credit-Control Application,
         section 8.3 and Appendix A1."
    ::= { tmnxDiamPlcyPeerStatsEntry 19 }

tmnxDiamPeerStCerTx              OBJECT-TYPE
    SYNTAX      Counter32
    MAX-ACCESS  read-only
    STATUS      obsolete
    DESCRIPTION
        "The value of tmnxDiamPeerStCerTx indicates the number of
         Capabilities-Exchange-Request messages that are transmitted to the
         server."
    REFERENCE
        "RFC 3588 Diameter Based Protocol,
         section 5.3.1."
    ::= { tmnxDiamPlcyPeerStatsEntry 20 }

tmnxDiamPeerStCeaRx              OBJECT-TYPE
    SYNTAX      Counter32
    MAX-ACCESS  read-only
    STATUS      obsolete
    DESCRIPTION
        "The value of tmnxDiamPeerStCeaRx indicates the number of
         Capabilities-Exchange-Answer messages that are received from the
         server."
    REFERENCE
        "RFC 3588 Diameter Based Protocol,
         section 5.3.2."
    ::= { tmnxDiamPlcyPeerStatsEntry 21 }

tmnxDiamPeerStWdrTx              OBJECT-TYPE
    SYNTAX      Counter32
    MAX-ACCESS  read-only
    STATUS      obsolete
    DESCRIPTION
        "The value of tmnxDiamPeerStWdrTx indicates the number of
         Device-Watchdog-Request messages that are transmitted to the server."
    REFERENCE
        "RFC 3588 Diameter Based Protocol,
         section 5.5.1."
    ::= { tmnxDiamPlcyPeerStatsEntry 24 }

tmnxDiamPeerStWdaRx              OBJECT-TYPE
    SYNTAX      Counter32
    MAX-ACCESS  read-only
    STATUS      obsolete
    DESCRIPTION
        "The value of tmnxDiamPeerStWdaRx indicates the number of
         Device-Watchdog-Answer messages that are received from the server."
    REFERENCE
        "RFC 3588 Diameter Based Protocol,
         section 5.5.2."
    ::= { tmnxDiamPlcyPeerStatsEntry 25 }

tmnxDiamPeerStWdrRx              OBJECT-TYPE
    SYNTAX      Counter32
    MAX-ACCESS  read-only
    STATUS      obsolete
    DESCRIPTION
        "The value of tmnxDiamPeerStWdrRx indicates the number of
         Device-Watchdog-Request messages that are received from the server."
    REFERENCE
        "RFC 3588 Diameter Based Protocol,
         section 5.5.1."
    ::= { tmnxDiamPlcyPeerStatsEntry 26 }

tmnxDiamPeerStWdaTx              OBJECT-TYPE
    SYNTAX      Counter32
    MAX-ACCESS  read-only
    STATUS      obsolete
    DESCRIPTION
        "The value of tmnxDiamPeerStWdaTx indicates the number of
         Device-Watchdog-Answer messages that are transmitted to the server."
    REFERENCE
        "RFC 3588 Diameter Based Protocol,
         section 5.5.2."
    ::= { tmnxDiamPlcyPeerStatsEntry 27 }

tmnxDiamPeerStAsrRx              OBJECT-TYPE
    SYNTAX      Counter32
    MAX-ACCESS  read-only
    STATUS      obsolete
    DESCRIPTION
        "The value of tmnxDiamPeerStAsrRx indicates the number of
         Abort-Session-Request messages that are received from the server."
    REFERENCE
        "RFC 3588 Diameter Based Protocol,
         section 8.5.1."
    ::= { tmnxDiamPlcyPeerStatsEntry 30 }

tmnxDiamPeerStAsaTx              OBJECT-TYPE
    SYNTAX      Counter32
    MAX-ACCESS  read-only
    STATUS      obsolete
    DESCRIPTION
        "The value of tmnxDiamPeerStAsaTx indicates the number of
         Abort-Session-Answer messages that are transmitted to the server."
    REFERENCE
        "RFC 3588 Diameter Based Protocol,
         section 8.5.2."
    ::= { tmnxDiamPlcyPeerStatsEntry 31 }

tmnxDiamPeerStRarRx              OBJECT-TYPE
    SYNTAX      Counter32
    MAX-ACCESS  read-only
    STATUS      obsolete
    DESCRIPTION
        "The value of tmnxDiamPeerStRarRx indicates the number of
         Re-Auth-Request messages that are received from the server."
    REFERENCE
        "RFC 3588 Diameter Based Protocol,
         section 8.3.1."
    ::= { tmnxDiamPlcyPeerStatsEntry 34 }

tmnxDiamPeerStRaaTx              OBJECT-TYPE
    SYNTAX      Counter32
    MAX-ACCESS  read-only
    STATUS      obsolete
    DESCRIPTION
        "The value of tmnxDiamPeerStRaaTx indicates the number of
         Re-Auth-Answer messages that are transmitted to the server."
    REFERENCE
        "RFC 3588 Diameter Based Protocol,
         section 8.3.2."
    ::= { tmnxDiamPlcyPeerStatsEntry 35 }

tmnxDiamPeerStDprTx              OBJECT-TYPE
    SYNTAX      Counter32
    MAX-ACCESS  read-only
    STATUS      obsolete
    DESCRIPTION
        "The value of tmnxDiamPeerStDprTx indicates the number of
         Disconnect-Peer-Request messages that are transmitted to the server."
    REFERENCE
        "RFC 3588 Diameter Based Protocol,
         section 5.4.1."
    ::= { tmnxDiamPlcyPeerStatsEntry 36 }

tmnxDiamPeerStDpaRx              OBJECT-TYPE
    SYNTAX      Counter32
    MAX-ACCESS  read-only
    STATUS      obsolete
    DESCRIPTION
        "The value of tmnxDiamPeerStDpaRx indicates the number of
         Disconnect-Peer-Answer messages that are received from the server."
    REFERENCE
        "RFC 3588 Diameter Based Protocol,
         section 5.4.2."
    ::= { tmnxDiamPlcyPeerStatsEntry 37 }

tmnxDiamPeerStDprRx              OBJECT-TYPE
    SYNTAX      Counter32
    MAX-ACCESS  read-only
    STATUS      obsolete
    DESCRIPTION
        "The value of tmnxDiamPeerStDprRx indicates the number of
         Disconnect-Peer-Request messages that are received from the server."
    REFERENCE
        "RFC 3588 Diameter Based Protocol,
         section 5.4.1."
    ::= { tmnxDiamPlcyPeerStatsEntry 38 }

tmnxDiamPeerStDpaTx              OBJECT-TYPE
    SYNTAX      Counter32
    MAX-ACCESS  read-only
    STATUS      obsolete
    DESCRIPTION
        "The value of tmnxDiamPeerStDpaTx indicates the number of
         Disconnect-Peer-Answer messages that are transmitted to the server."
    REFERENCE
        "RFC 3588 Diameter Based Protocol,
         section 5.4.2."
    ::= { tmnxDiamPlcyPeerStatsEntry 39 }

tmnxDiamPeerStAarTx              OBJECT-TYPE
    SYNTAX      Counter32
    MAX-ACCESS  read-only
    STATUS      obsolete
    DESCRIPTION
        "The value of tmnxDiamPeerStAarTx indicates the number of AA-Request
         messages that are transmitted to the server."
    REFERENCE
        "RFC 7155 Diameter Network Access Server Application,
         section 3.1. AA-Request (AAR) Command"
    ::= { tmnxDiamPlcyPeerStatsEntry 40 }

tmnxDiamPeerStAaaRx              OBJECT-TYPE
    SYNTAX      Counter32
    MAX-ACCESS  read-only
    STATUS      obsolete
    DESCRIPTION
        "The value of tmnxDiamPeerStAaaRx indicates the number of AA-Answer
         messages that are received from the server."
    REFERENCE
        "RFC 7155 Diameter Network Access Server Application,
         section 3.2. AA-Answer (AAA) Command"
    ::= { tmnxDiamPlcyPeerStatsEntry 41 }

tmnxDiameterDccaObjects          OBJECT IDENTIFIER ::= { tmnxDiameter 2 }

tmnxDiamPlcyDccaTableLastChngd   OBJECT-TYPE
    SYNTAX      TimeStamp
    MAX-ACCESS  read-only
    STATUS      obsolete
    DESCRIPTION
        "The value of tmnxDiamPlcyDccaTableLastChngd indicates the sysUpTime at
         the time of the most recent management-initiated change to the
         tmnxDiameterPlcyDccaTable. DCCA = Diameter Credit Control Application."
    ::= { tmnxDiameterDccaObjects 1 }

tmnxDiameterPlcyDccaTable        OBJECT-TYPE
    SYNTAX      SEQUENCE OF TmnxDiameterPlcyDccaEntry
    MAX-ACCESS  not-accessible
    STATUS      obsolete
    DESCRIPTION
        "The tmnxDiameterPlcyDccaTable is obsolete.

         Use the tmnxDiamApGyTable instead."
    ::= { tmnxDiameterDccaObjects 2 }

tmnxDiameterPlcyDccaEntry        OBJECT-TYPE
    SYNTAX      TmnxDiameterPlcyDccaEntry
    MAX-ACCESS  not-accessible
    STATUS      obsolete
    DESCRIPTION
        "The tmnxDiameterPlcyDccaEntry is obsolete.

         Use the tmnxDiamApGyEntry instead."
    AUGMENTS    { tmnxDiameterPlcyEntry }
    ::= { tmnxDiameterPlcyDccaTable 1 }

TmnxDiameterPlcyDccaEntry        ::= SEQUENCE
{
    tmnxDiamPlcyDccaLastMgmtChange   TimeStamp,
    tmnxDiamPlcyDccaFailover         TruthValue,
    tmnxDiamPlcyDccaFailureHndlng    TmnxDiamCcFailureHndlng,
    tmnxDiamPlcyDccaTxTimer          Unsigned32,
    tmnxDiamPlcyDccaAvpServCntxtId   DisplayString,
    tmnxDiamPlcyDccaAvpCldStationId  DisplayString,
    tmnxDiamPlcyDccaAvpRadiusUsrNme  TruthValue,
    tmnxDiamPlcyDccaAvpSubIdOrg      TmnxDiamPlcyDccaAvpOriginType,
    tmnxDiamPlcyDccaAvpSubIdType     INTEGER,
    tmnxDiamPlcyDccaAvpNasP          TruthValue,
    tmnxDiamPlcyDccaAvpNasPPfixType  TmnxSubNasPortPrefixType,
    tmnxDiamPlcyDccaAvpNasPPfixStr   DisplayString,
    tmnxDiamPlcyDccaAvpNasPSfixType  TmnxSubNasPortSuffixType,
    tmnxDiamPlcyDccaAvpNasPType      TruthValue,
    tmnxDiamPlcyDccaAvpImsiOrg       TmnxDiamPlcyDccaAvpOriginType,
    tmnxDiamPlcyDccaApplicationType  TmnxDiamDccaApplicationType,
    tmnxDiamPlcyDccaMaxPendingReq    Unsigned32,
    tmnxDiamPlcyDccaTxRetryLimit     Unsigned32,
    tmnxDiamPlcyDccaOutOfCreditRep   INTEGER
}

tmnxDiamPlcyDccaLastMgmtChange   OBJECT-TYPE
    SYNTAX      TimeStamp
    MAX-ACCESS  read-only
    STATUS      obsolete
    DESCRIPTION
        "The value of tmnxDiamPlcyDccaLastMgmtChange indicates the sysUpTime at
         the time of the most recent management-initiated change to this table
         row."
    ::= { tmnxDiameterPlcyDccaEntry 1 }

tmnxDiamPlcyDccaFailover         OBJECT-TYPE
    SYNTAX      TruthValue
    MAX-ACCESS  read-create
    STATUS      obsolete
    DESCRIPTION
        "The value of tmnxDiamPlcyDccaFailover specifies if moving the message
         stream to a backup server during an ongoing session is supported for
         this DIAMETER policy."
    DEFVAL      { true }
    ::= { tmnxDiameterPlcyDccaEntry 2 }

tmnxDiamPlcyDccaFailureHndlng    OBJECT-TYPE
    SYNTAX      TmnxDiamCcFailureHndlng
    MAX-ACCESS  read-create
    STATUS      obsolete
    DESCRIPTION
        "The value of tmnxDiamPlcyDccaFailureHndlng specifies what action to
         take in case of a session failure for this DIAMETER policy."
    DEFVAL      { terminate }
    ::= { tmnxDiameterPlcyDccaEntry 3 }

tmnxDiamPlcyDccaTxTimer          OBJECT-TYPE
    SYNTAX      Unsigned32 (10..1000)
    UNITS       "seconds"
    MAX-ACCESS  read-create
    STATUS      obsolete
    DESCRIPTION
        "The value of tmnxDiamPlcyDccaTxTimer specifies the DCCA Tx Timer (in
         seconds) for this DIAMETER policy."
    DEFVAL      { 10 }
    ::= { tmnxDiameterPlcyDccaEntry 4 }

tmnxDiamPlcyDccaAvpServCntxtId   OBJECT-TYPE
    SYNTAX      DisplayString (SIZE (0..32))
    MAX-ACCESS  read-create
    STATUS      obsolete
    DESCRIPTION
        "The value of tmnxDiamPlcyDccaAvpServCntxtId specifies the DCCA
         Service-Context-Id AVP. If set the AVP will be included in CCR (Credit
         Control Request) messages."
    DEFVAL      { "" }
    ::= { tmnxDiameterPlcyDccaEntry 5 }

tmnxDiamPlcyDccaAvpCldStationId  OBJECT-TYPE
    SYNTAX      DisplayString (SIZE (0..64))
    MAX-ACCESS  read-create
    STATUS      obsolete
    DESCRIPTION
        "The value of tmnxDiamPlcyDccaAvpCldStationId specifies the RADIUS
         Called-Station-Id AVP. If set, the AVP will be included in CCR (Credit
         Control Request) messages."
    DEFVAL      { "" }
    ::= { tmnxDiameterPlcyDccaEntry 6 }

tmnxDiamPlcyDccaAvpRadiusUsrNme  OBJECT-TYPE
    SYNTAX      TruthValue
    MAX-ACCESS  read-create
    STATUS      obsolete
    DESCRIPTION
        "The value of tmnxDiamPlcyDccaAvpRadiusUsrNme specifies  whether or
         not the DIAMETER User-Name AVP will be included in CCR(Credit Control
         Request) messages."
    DEFVAL      { false }
    ::= { tmnxDiameterPlcyDccaEntry 7 }

tmnxDiamPlcyDccaAvpSubIdOrg      OBJECT-TYPE
    SYNTAX      TmnxDiamPlcyDccaAvpOriginType
    MAX-ACCESS  read-create
    STATUS      obsolete
    DESCRIPTION
        "The value of tmnxDiamPlcyDccaAvpSubIdOrg specifies the origin of the
         information to send in the Subscription-Id-Data AVP."
    REFERENCE
        "RFC 4006 Diameter Credit-Control Application
         section 8.48. Subscription-Id-Data AVP."
    DEFVAL      { subscriberId }
    ::= { tmnxDiameterPlcyDccaEntry 8 }

tmnxDiamPlcyDccaAvpSubIdType     OBJECT-TYPE
    SYNTAX      INTEGER {
        endUserE164    (0),
        endUserImsi    (1),
        endUserPrivate (4)
    }
    MAX-ACCESS  read-create
    STATUS      obsolete
    DESCRIPTION
        "The value of tmnxDiamPlcyDccaAvpSubIdType specifies the type of the
         identifier stored in the Subscription-Id-Data AVP."
    REFERENCE
        "RFC 4006 Diameter Credit-Control Application
         section 8.47. Subscription-Id-Type AVP."
    DEFVAL      { endUserPrivate }
    ::= { tmnxDiameterPlcyDccaEntry 9 }

tmnxDiamPlcyDccaAvpNasP          OBJECT-TYPE
    SYNTAX      TruthValue
    MAX-ACCESS  read-create
    STATUS      obsolete
    DESCRIPTION
        "The value of tmnxDiamPlcyDccaAvpNasP specifies if the NAS-Port-Id AVP
         will be included in applicable DIAMETER messages."
    DEFVAL      { false }
    ::= { tmnxDiameterPlcyDccaEntry 10 }

tmnxDiamPlcyDccaAvpNasPPfixType  OBJECT-TYPE
    SYNTAX      TmnxSubNasPortPrefixType
    MAX-ACCESS  read-create
    STATUS      obsolete
    DESCRIPTION
        "The value of tmnxDiamPlcyDccaAvpNasPPfixType specifies what type of
         prefix will be added to the NAS-Port AVP if included in DIAMETER
         messages."
    DEFVAL      { none }
    ::= { tmnxDiameterPlcyDccaEntry 11 }

tmnxDiamPlcyDccaAvpNasPPfixStr   OBJECT-TYPE
    SYNTAX      DisplayString (SIZE (0..8))
    MAX-ACCESS  read-create
    STATUS      obsolete
    DESCRIPTION
        "The value of tmnxDiamPlcyDccaAvpNasPPfixStr specifies the user
         configurable string to be added as prefix to the NAS-Port AVP if
         included in DIAMETER messages.

         This field is only applicable  if tmnxDiamPlcyDccaAvpNasPPfixType
         is set to 'userString'."
    DEFVAL      { "" }
    ::= { tmnxDiameterPlcyDccaEntry 12 }

tmnxDiamPlcyDccaAvpNasPSfixType  OBJECT-TYPE
    SYNTAX      TmnxSubNasPortSuffixType
    MAX-ACCESS  read-create
    STATUS      obsolete
    DESCRIPTION
        "The value of tmnxDiamPlcyDccaAvpNasPSfixType specifies what type of
         suffix will be added to the NAS-Port attribute NAS-Port AVP if
         included in DIAMETER messages."
    DEFVAL      { none }
    ::= { tmnxDiameterPlcyDccaEntry 13 }

tmnxDiamPlcyDccaAvpNasPType      OBJECT-TYPE
    SYNTAX      TruthValue
    MAX-ACCESS  read-create
    STATUS      obsolete
    DESCRIPTION
        "The value of tmnxDiamPlcyDccaAvpNasPType specifies if the
         NAS-Port-Type AVP will be included in applicable DIAMETER messages."
    DEFVAL      { false }
    ::= { tmnxDiameterPlcyDccaEntry 14 }

tmnxDiamPlcyDccaAvpImsiOrg       OBJECT-TYPE
    SYNTAX      TmnxDiamPlcyDccaAvpOriginType
    MAX-ACCESS  read-create
    STATUS      obsolete
    DESCRIPTION
        "The value of tmnxDiamPlcyDccaAvpImsiOrg specifies the origin of the
         information to send in the International Mobile Subscriber Identity
         (IMSI) AVP."
    DEFVAL      { subscriberId }
    ::= { tmnxDiameterPlcyDccaEntry 15 }

tmnxDiamPlcyDccaApplicationType  OBJECT-TYPE
    SYNTAX      TmnxDiamDccaApplicationType
    MAX-ACCESS  read-create
    STATUS      obsolete
    DESCRIPTION
        "The value of tmnxDiamPlcyDccaApplicationType specifies the application
         type associated with this policy.

         It defines the set of supported values for the Auth-Application-Id
         AVP.

         tmnxDiamPlcyDccaApplicationType | Auth-Application-Id
         --------------------------------|-------------------------------------
                                vfDccaV2 | 4        (standard)
                                      gx | 16777238 (vendor-specific 3GPP)"
    REFERENCE
        "RFC 3588 Diameter Based Protocol
         section 6.8. Auth-Application-Id AVP.

         IANA Authentication, Authorization, and Accounting (AAA) Parameters."
    DEFVAL      { vfDccaV2 }
    ::= { tmnxDiameterPlcyDccaEntry 50 }

tmnxDiamPlcyDccaMaxPendingReq    OBJECT-TYPE
    SYNTAX      Unsigned32 (10..131072)
    MAX-ACCESS  read-create
    STATUS      obsolete
    DESCRIPTION
        "The value of tmnxDiamPlcyDccaMaxPendingReq specifies the maximum
         number of pending requests for this DIAMETER policy.

         If the maximum number of pending requests has been exceeded, further
         requests are buffered or dropped."
    DEFVAL      { 10 }
    ::= { tmnxDiameterPlcyDccaEntry 51 }

tmnxDiamPlcyDccaTxRetryLimit     OBJECT-TYPE
    SYNTAX      Unsigned32 (0..3)
    MAX-ACCESS  read-create
    STATUS      obsolete
    DESCRIPTION
        "The value of tmnxDiamPlcyDccaTxRetryLimit specifies the maximum number
         of retries for a CCR message associated with this DIAMETER policy."
    DEFVAL      { 0 }
    ::= { tmnxDiameterPlcyDccaEntry 52 }

tmnxDiamPlcyDccaOutOfCreditRep   OBJECT-TYPE
    SYNTAX      INTEGER {
        final          (1),
        quotaExhausted (2)
    }
    MAX-ACCESS  read-create
    STATUS      obsolete
    DESCRIPTION
        "The value of tmnxDiamPlcyDccaOutOfCreditRep specifies the reporting
         reason in an intermediate interrogation when the final granted units
         have been consumed and a corresponding out-of-credit-action different
         from 'disconnect-host' is started."
    DEFVAL      { final }
    ::= { tmnxDiameterPlcyDccaEntry 53 }

tmnxDiameterObjects              OBJECT IDENTIFIER ::= { tmnxDiameter 3 }

tmnxDiamAppPlcyTableLastCh       OBJECT-TYPE
    SYNTAX      TimeStamp
    MAX-ACCESS  read-only
    STATUS      current
    DESCRIPTION
        "The value of tmnxDiamAppPlcyTableLastCh indicates the sysUpTime at the
         time of the most recent management-initiated change to the
         tmnxDiamAppPlcyTable."
    ::= { tmnxDiameterObjects 1 }

tmnxDiamAppPlcyTable             OBJECT-TYPE
    SYNTAX      SEQUENCE OF TmnxDiamAppPlcyEntry
    MAX-ACCESS  not-accessible
    STATUS      current
    DESCRIPTION
        "The tmnxDiamAppPlcyTable contains objects to configure DIAMETER
         application specific policies."
    ::= { tmnxDiameterObjects 2 }

tmnxDiamAppPlcyEntry             OBJECT-TYPE
    SYNTAX      TmnxDiamAppPlcyEntry
    MAX-ACCESS  not-accessible
    STATUS      current
    DESCRIPTION
        "Each conceptual row represents information about a particular DIAMETER
         application policy.

         Entries in this table can be created or deleted by means of SNMP
         operations."
    INDEX       { IMPLIED tmnxDiamAppPlcyId }
    ::= { tmnxDiamAppPlcyTable 1 }

TmnxDiamAppPlcyEntry             ::= SEQUENCE
{
    tmnxDiamAppPlcyId                TNamedItem,
    tmnxDiamAppPlcyRowStatus         RowStatus,
    tmnxDiamAppPlcyLastMgmtChange    TimeStamp,
    tmnxDiamAppPlcyFailover          TruthValue,
    tmnxDiamAppPlcyFailureHndlng     TmnxDiamCcFailureHndlng,
    tmnxDiamAppPlcyPeerPlcy          TNamedItemOrEmpty,
    tmnxDiamAppPlcyApplication       INTEGER,
    tmnxDiamAppPlcyTxTimer           Unsigned32,
    tmnxDiamAppPlcyDescription       TItemDescription
}

tmnxDiamAppPlcyId                OBJECT-TYPE
    SYNTAX      TNamedItem
    MAX-ACCESS  not-accessible
    STATUS      current
    DESCRIPTION
        "The value of tmnxDiamAppPlcyId specifies the name of the DIAMETER
         application policy."
    ::= { tmnxDiamAppPlcyEntry 1 }

tmnxDiamAppPlcyRowStatus         OBJECT-TYPE
    SYNTAX      RowStatus
    MAX-ACCESS  read-create
    STATUS      current
    DESCRIPTION
        "The value of tmnxDiamAppPlcyRowStatus specifies the row status of this
         row."
    ::= { tmnxDiamAppPlcyEntry 2 }

tmnxDiamAppPlcyLastMgmtChange    OBJECT-TYPE
    SYNTAX      TimeStamp
    MAX-ACCESS  read-only
    STATUS      current
    DESCRIPTION
        "The value of tmnxDiamAppPlcyLastMgmtChange indicates the sysUpTime at
         the time of the most recent management-initiated change to this table
         row."
    ::= { tmnxDiamAppPlcyEntry 3 }

tmnxDiamAppPlcyFailover          OBJECT-TYPE
    SYNTAX      TruthValue
    MAX-ACCESS  read-create
    STATUS      current
    DESCRIPTION
        "The value of tmnxDiamAppPlcyFailover specifies whether or not moving
         the CC message stream to a backup server during an ongoing CC session
         is supported for this DIAMETER application policy."
    DEFVAL      { true }
    ::= { tmnxDiamAppPlcyEntry 4 }

tmnxDiamAppPlcyFailureHndlng     OBJECT-TYPE
    SYNTAX      TmnxDiamCcFailureHndlng
    MAX-ACCESS  read-create
    STATUS      current
    DESCRIPTION
        "The value of tmnxDiamAppPlcyFailureHndlng specifies what action to
         take in case of a DCCA session failure for this DIAMETER policy."
    DEFVAL      { terminate }
    ::= { tmnxDiamAppPlcyEntry 5 }

tmnxDiamAppPlcyPeerPlcy          OBJECT-TYPE
    SYNTAX      TNamedItemOrEmpty
    MAX-ACCESS  read-create
    STATUS      current
    DESCRIPTION
        "The value of tmnxDiamAppPlcyPeerPlcy specifies the name of the
         DIAMETER peer policy to be used with this DIAMETER application policy.

         A corresponding row in the tmnxDiameterPlcyTable must exist while the
         value of tmnxDiamAppPlcyPeerPlcy is not empty."
    DEFVAL      { "" }
    ::= { tmnxDiamAppPlcyEntry 6 }

tmnxDiamAppPlcyApplication       OBJECT-TYPE
    SYNTAX      INTEGER {
        none   (0),
        gx     (1),
        gy     (2),
        nasreq (3)
    }
    MAX-ACCESS  read-create
    STATUS      current
    DESCRIPTION
        "The value of tmnxDiamAppPlcyApplication specifies what application
         this policy is used for."
    DEFVAL      { none }
    ::= { tmnxDiamAppPlcyEntry 7 }

tmnxDiamAppPlcyTxTimer           OBJECT-TYPE
    SYNTAX      Unsigned32 (10..1000)
    UNITS       "seconds"
    MAX-ACCESS  read-create
    STATUS      current
    DESCRIPTION
        "The value of tmnxDiamAppPlcyTxTimer specifies the maximum time that
         this system waits for the DIAMETER application server while a client
         is pending.

         The action taken when the timer expires may depend on the application;
         by default of a more specific rule, the value of the object
         tmnxDiamAppPlcyFailureHndlng specifies the action."
    REFERENCE
        "RFC 4006 Diameter Credit-Control Application
         section 13 Tx timer."
    DEFVAL      { 10 }
    ::= { tmnxDiamAppPlcyEntry 8 }

tmnxDiamAppPlcyDescription       OBJECT-TYPE
    SYNTAX      TItemDescription
    MAX-ACCESS  read-create
    STATUS      current
    DESCRIPTION
        "The value of tmnxDiamAppPlcyDescription specifies the description of
         this DIAMETER application policy."
    DEFVAL      { "" }
    ::= { tmnxDiamAppPlcyEntry 9 }

tmnxDiamApGyTableLastCh          OBJECT-TYPE
    SYNTAX      TimeStamp
    MAX-ACCESS  read-only
    STATUS      current
    DESCRIPTION
        "The value of tmnxDiamApGyTableLastCh indicates the sysUpTime at the
         time of the most recent management-initiated change to the
         tmnxDiamApGyTable."
    ::= { tmnxDiameterObjects 3 }

tmnxDiamApGyTable                OBJECT-TYPE
    SYNTAX      SEQUENCE OF TmnxDiamApGyEntry
    MAX-ACCESS  not-accessible
    STATUS      current
    DESCRIPTION
        "The tmnxDiamApGyTable contains objects to configure Gy for DIAMETER
         Application Policies."
    ::= { tmnxDiameterObjects 4 }

tmnxDiamApGyEntry                OBJECT-TYPE
    SYNTAX      TmnxDiamApGyEntry
    MAX-ACCESS  not-accessible
    STATUS      current
    DESCRIPTION
        "Each conceptual row represents Gy information about a particular
         DIAMETER application policy.

         Entries in this table are created and destroyed automatically by the
         system, by setting or clearing the 'gy' bit in the object
         tmnxDiamAppPlcyApplication."
    INDEX       { IMPLIED tmnxDiamAppPlcyId }
    ::= { tmnxDiamApGyTable 1 }

TmnxDiamApGyEntry                ::= SEQUENCE
{
    tmnxDiamApGyLastMgmtChange       TimeStamp,
    tmnxDiamApGyAvpServCntxtId       DisplayString,
    tmnxDiamApGyAvpCldStationId      DisplayString,
    tmnxDiamApGyAvpRadiusUsrNme      TruthValue,
    tmnxDiamApGyAvpImsiOrg           TmnxDiamPlcyDccaAvpOriginType,
    tmnxDiamApGyOutOfCreditRep       INTEGER,
    tmnxDiamApGyVendorSupport        TmnxDiamPlcyVendorSupportType,
    tmnxDiamApGySubIdOrg             TmnxDiamPlcyDccaAvpOriginType,
    tmnxDiamApGySubIdType            INTEGER,
    tmnxDiamApGyInc3GppGgsnAddr      TruthValue,
    tmnxDiamApGyInc3GppGgsnIPv6Addr  TruthValue,
    tmnxDiamApGyMacFormat            TmnxMacSpecification,
    tmnxDiamApGyIncAddressAvp        TruthValue,
    tmnxDiamApGyInc3GppChargingId    INTEGER,
    tmnxDiamApGyInc3GppGprsNQosProf  TruthValue,
    tmnxDiamApGyInc3GppNsapi         TruthValue,
    tmnxDiamApGyInc3GppSessionStopIn TruthValue,
    tmnxDiamApGyInc3GppSelectionMode TruthValue,
    tmnxDiamApGyInc3GppChargingChara TruthValue,
    tmnxDiamApGyInc3GppRatType       Unsigned32,
    tmnxDiamApGyIncGgsnAddress       INTEGER,
    tmnxDiamApGyIncPsInformation     TruthValue,
    tmnxDiamApGyIncChargingRBaseName TruthValue,
    tmnxDiamApGyChargingRuleBaseName DisplayString,
    tmnxDiamApGyIncPdpContextType    TruthValue,
    tmnxDiamApGyIncUserEqInfoType    INTEGER
}

tmnxDiamApGyLastMgmtChange       OBJECT-TYPE
    SYNTAX      TimeStamp
    MAX-ACCESS  read-only
    STATUS      current
    DESCRIPTION
        "The value of tmnxDiamApGyLastMgmtChange indicates the sysUpTime at the
         time of the most recent management-initiated change to this table row."
    ::= { tmnxDiamApGyEntry 1 }

tmnxDiamApGyAvpServCntxtId       OBJECT-TYPE
    SYNTAX      DisplayString (SIZE (0..32))
    MAX-ACCESS  read-create
    STATUS      current
    DESCRIPTION
        "The value of tmnxDiamApGyAvpServCntxtId specifies the DCCA
         Service-Context-Id AVP. If set the AVP will be included in CCR (Credit
         Control Request) messages."
    DEFVAL      { "" }
    ::= { tmnxDiamApGyEntry 2 }

tmnxDiamApGyAvpCldStationId      OBJECT-TYPE
    SYNTAX      DisplayString (SIZE (0..64))
    MAX-ACCESS  read-create
    STATUS      current
    DESCRIPTION
        "The value of tmnxDiamApGyAvpCldStationId specifies the RADIUS
         Called-Station-Id AVP. If set, the AVP will be included in CCR (Credit
         Control Request) messages."
    DEFVAL      { "" }
    ::= { tmnxDiamApGyEntry 3 }

tmnxDiamApGyAvpRadiusUsrNme      OBJECT-TYPE
    SYNTAX      TruthValue
    MAX-ACCESS  read-create
    STATUS      current
    DESCRIPTION
        "The value of tmnxDiamApGyAvpRadiusUsrNme specifies  whether or
         not the DIAMETER User-Name AVP will be included in CCR(Credit Control
         Request) messages."
    DEFVAL      { false }
    ::= { tmnxDiamApGyEntry 4 }

tmnxDiamApGyAvpImsiOrg           OBJECT-TYPE
    SYNTAX      TmnxDiamPlcyDccaAvpOriginType { disabled (0), subscriberId (1), circuitId (2), imsi (3) }
    MAX-ACCESS  read-create
    STATUS      current
    DESCRIPTION
        "The value of tmnxDiamApGyAvpImsiOrg specifies the origin of the
         information to send in the International Mobile Subscriber Identity
         (IMSI) AVP.

         When the value of this object is set to 'disabled(0)', this AVP is not
         included in DIAMETER Gy CCR messages."
    DEFVAL      { subscriberId }
    ::= { tmnxDiamApGyEntry 5 }

tmnxDiamApGyOutOfCreditRep       OBJECT-TYPE
    SYNTAX      INTEGER {
        final          (1),
        quotaExhausted (2)
    }
    MAX-ACCESS  read-create
    STATUS      current
    DESCRIPTION
        "The value of tmnxDiamApGyOutOfCreditRep specifies the reporting reason
         in an intermediate interrogation when the final granted units have
         been consumed and a corresponding out-of-credit-action different from
         'disconnect-host' is started."
    DEFVAL      { final }
    ::= { tmnxDiamApGyEntry 6 }

tmnxDiamApGyVendorSupport        OBJECT-TYPE
    SYNTAX      TmnxDiamPlcyVendorSupportType
    MAX-ACCESS  read-create
    STATUS      current
    DESCRIPTION
        "The value of tmnxDiamApGyVendorSupport specifies which vendor specific
         attributes are used in Gy sessions for this DIAMETER application
         policy."
    DEFVAL      { threeGpp }
    ::= { tmnxDiamApGyEntry 7 }

tmnxDiamApGySubIdOrg             OBJECT-TYPE
    SYNTAX      TmnxDiamPlcyDccaAvpOriginType { subscriberId (1), circuitId (2), imsi (3), msisdn (4), imei (5), dualStackRemoteId (6), mac (7), username (8), nasPortId (9) }
    MAX-ACCESS  read-create
    STATUS      current
    DESCRIPTION
        "The value of tmnxDiamApGySubIdOrg specifies the origin of the
         information to send in the Subscription-Id-Data AVP."
    REFERENCE
        "RFC 4006 Diameter Credit-Control Application
         section 8.48. Subscription-Id-Data AVP."
    DEFVAL      { subscriberId }
    ::= { tmnxDiamApGyEntry 8 }

tmnxDiamApGySubIdType            OBJECT-TYPE
    SYNTAX      INTEGER {
        e164    (0),
        imsi    (1),
        nai     (3),
        private (4)
    }
    MAX-ACCESS  read-create
    STATUS      current
    DESCRIPTION
        "The value of tmnxDiamApGySubIdType specifies the type of the
         identifier stored in the Subscription-Id-Data AVP."
    REFERENCE
        "RFC 4006 Diameter Credit-Control Application
         section 8.47. Subscription-Id-Type AVP."
    DEFVAL      { private }
    ::= { tmnxDiamApGyEntry 9 }

tmnxDiamApGyInc3GppGgsnAddr      OBJECT-TYPE
    SYNTAX      TruthValue
    MAX-ACCESS  read-create
    STATUS      current
    DESCRIPTION
        "The value of tmnxDiamApGyInc3GppGgsnAddr specifies whether or not the
         3GPP-GGSN-Address attribute-value-pair (AVP 7, vendor Id 10415) will
         be included in the DIAMETER Gy CCR message.

         The value of the AVP contains the value of tmnxDiamPlcySourceAddr if
         configured, otherwise it contains the system IPv4 address, or the
         management port IPv4 address."
    REFERENCE
        "3GPP TS 29.061
         section 16.4.7 Sub-attributes of the 3GPP Vendor-Specific attribute"
    DEFVAL      { true }
    ::= { tmnxDiamApGyEntry 10 }

tmnxDiamApGyInc3GppGgsnIPv6Addr  OBJECT-TYPE
    SYNTAX      TruthValue
    MAX-ACCESS  read-create
    STATUS      current
    DESCRIPTION
        "The value of tmnxDiamApGyInc3GppGgsnIPv6Addr specifies whether or not
         the 3GPP-GGSN-Ipv6-Address attribute-value-pair (AVP 16, vendor Id
         10415) will be included in the DIAMETER Gy CCR message.

         The value of the AVP contains the value of tmnxDiamPlcyV6SourceAddr if
         configured, otherwise it contains the system IPv6 address, or the
         management port IPv6 address."
    REFERENCE
        "3GPP TS 29.061
         section 16.4.7 Sub-attributes of the 3GPP Vendor-Specific attribute"
    DEFVAL      { false }
    ::= { tmnxDiamApGyEntry 11 }

tmnxDiamApGyMacFormat            OBJECT-TYPE
    SYNTAX      TmnxMacSpecification (SIZE (2..7))
    MAX-ACCESS  read-create
    STATUS      current
    DESCRIPTION
        "The value of tmnxDiamApGyMacFormat specifies how a MAC address is
         represented when contacting a DIAMETER server.

         Examples:

         'ab:'               00:0c:f1:99:85:b8  Nokia SROS style
         'XY-'               00-0C-F1-99-85-B8  IEEE canonical style
         'mmmm.'             0002.03aa.abff     Cisco style."
    DEFVAL      { "aa:" }
    ::= { tmnxDiamApGyEntry 12 }

tmnxDiamApGyIncAddressAvp        OBJECT-TYPE
    SYNTAX      TruthValue
    MAX-ACCESS  read-create
    STATUS      current
    DESCRIPTION
        "The value of tmnxDiamApGyIncAddressAvp specifies whether or not the
         DCCA attribute-value-pairs containing the host address or prefix are
         included in the DIAMETER Gy CCR message.

         When the value of this object is set to 'true', following
         attribute-value-pairs are included : Framed-IP-Address (AVP 8),
         Framed-IPv6-Prefix (AVP 97), Delegated-IPv6-Prefix (AVP 123),
         Alc-IPv6-Address (AVP 99, vendor Id 6527)."
    DEFVAL      { true }
    ::= { tmnxDiamApGyEntry 13 }

tmnxDiamApGyInc3GppChargingId    OBJECT-TYPE
    SYNTAX      INTEGER {
        disabled (0),
        auto     (1),
        esmInfo  (2),
        id       (3)
    }
    MAX-ACCESS  read-create
    STATUS      current
    DESCRIPTION
        "The value of tmnxDiamApGyInc3GppChargingId specifies the
         3GPP-Charging-Id attribute-value-pair (AVP 2, vendor Id 10415)
         included in DIAMETER Gy CCR messages.

         disabled : do not include this AVP in the DIAMETER Gy CCR message;
         auto     : let the system chose the value based on the value configured
                    in tmnxDiamApGyVendorSupport;
         esmInfo  : include subscriber-id, sap-id, sla-profile;
         id       : include a unique 32 bit integer value."
    DEFVAL      { auto }
    ::= { tmnxDiamApGyEntry 14 }

tmnxDiamApGyInc3GppGprsNQosProf  OBJECT-TYPE
    SYNTAX      TruthValue
    MAX-ACCESS  read-create
    STATUS      current
    DESCRIPTION
        "The value of tmnxDiamApGyInc3GppGprsNQosProf specifies whether or not
         the 3GPP-GPRS-Negotiated-QoS-profile attribute-value-pair (AVP 5,
         vendor Id 10415-5) is included in the DIAMETER Gy CCR message."
    DEFVAL      { true }
    ::= { tmnxDiamApGyEntry 15 }

tmnxDiamApGyInc3GppNsapi         OBJECT-TYPE
    SYNTAX      TruthValue
    MAX-ACCESS  read-create
    STATUS      current
    DESCRIPTION
        "The value of tmnxDiamApGyInc3GppNsapi specifies whether or not the
         3GPP-NSAPI attribute-value-pair (AVP 10, vendor Id 10415) is included
         in the DIAMETER Gy CCR message."
    DEFVAL      { true }
    ::= { tmnxDiamApGyEntry 16 }

tmnxDiamApGyInc3GppSessionStopIn OBJECT-TYPE
    SYNTAX      TruthValue
    MAX-ACCESS  read-create
    STATUS      current
    DESCRIPTION
        "The value of tmnxDiamApGyInc3GppSessionStopIn specifies whether or not
         the 3GPP-Session-Stop-Indicator attribute-value-pair (AVP 11 vendor Id
         10415) is included in the DIAMETER Gy CCR message."
    DEFVAL      { true }
    ::= { tmnxDiamApGyEntry 17 }

tmnxDiamApGyInc3GppSelectionMode OBJECT-TYPE
    SYNTAX      TruthValue
    MAX-ACCESS  read-create
    STATUS      current
    DESCRIPTION
        "The value of tmnxDiamApGyInc3GppSelectionMode specifies whether or not
         the 3GPP-Selection-Mode attribute-value-pair (AVP 12 vendor Id 10415)
         is included in the DIAMETER Gy CCR message."
    DEFVAL      { true }
    ::= { tmnxDiamApGyEntry 18 }

tmnxDiamApGyInc3GppChargingChara OBJECT-TYPE
    SYNTAX      TruthValue
    MAX-ACCESS  read-create
    STATUS      current
    DESCRIPTION
        "The value of tmnxDiamApGyInc3GppChargingChara specifies whether or not
         the 3GPP-Charging-Characteristics attribute-value-pair (AVP 13, vendor
         Id 10415) is included in the DIAMETER Gy CCR message."
    DEFVAL      { true }
    ::= { tmnxDiamApGyEntry 19 }

tmnxDiamApGyInc3GppRatType       OBJECT-TYPE
    SYNTAX      Unsigned32 (0 | 1..255)
    MAX-ACCESS  read-create
    STATUS      current
    DESCRIPTION
        "The value of tmnxDiamApGyInc3GppRatType specifies the value for the
         3GPP-RAT-Type attribute-value-pair (AVP 21, vendor Id 10415) is
         included in the DIAMETER Gy CCR message.

         This AVP is not included in the DIAMETER Gy CCR message when the value
         of this object is set to zero."
    REFERENCE
        "3GPP TS 29.061"
    DEFVAL      { 0 }
    ::= { tmnxDiamApGyEntry 20 }

tmnxDiamApGyIncGgsnAddress       OBJECT-TYPE
    SYNTAX      INTEGER {
        disabled (0),
        ipv4     (1),
        ipv6     (2)
    }
    MAX-ACCESS  read-create
    STATUS      current
    DESCRIPTION
        "The value of tmnxDiamApGyIncGgsnAddress specifies whether or not the
         GGSN-Address attribute-value-pair (AVP 847, vendor Id 10415) is
         included in the DIAMETER Gy CCR message.

         This AVP is included in the DIAMETER Gy CCR message when the value of
         this object is set to 'ipv4 (1)' or 'ipv6 (2)'."
    DEFVAL      { disabled }
    ::= { tmnxDiamApGyEntry 21 }

tmnxDiamApGyIncPsInformation     OBJECT-TYPE
    SYNTAX      TruthValue
    MAX-ACCESS  read-create
    STATUS      current
    DESCRIPTION
        "The value of tmnxDiamApGyIncPsInformation specifies whether or not the
         included attribute-value-pairs are grouped in the PS-Information (AVP
         874, vendor Id 10415) attribute-value-pair."
    DEFVAL      { false }
    ::= { tmnxDiamApGyEntry 22 }

tmnxDiamApGyIncChargingRBaseName OBJECT-TYPE
    SYNTAX      TruthValue
    MAX-ACCESS  read-create
    STATUS      current
    DESCRIPTION
        "The value of tmnxDiamApGyIncChargingRBaseName specifies whether or not
         the Charging-Rule-Base-Name attribute-value-pair  (AVP 1004, vendor Id
         10415) is included in the DIAMETER Gy CCR message.

         When the value of this object is set to 'true' and the value of
         tmnxDiamApGyChargingRuleBaseName is set to the empty string, the
         category-map-name is used for this AVP."
    DEFVAL      { true }
    ::= { tmnxDiamApGyEntry 23 }

tmnxDiamApGyChargingRuleBaseName OBJECT-TYPE
    SYNTAX      DisplayString (SIZE (0..64))
    MAX-ACCESS  read-create
    STATUS      current
    DESCRIPTION
        "The value of tmnxDiamApGyChargingRuleBaseName specifies the value for
         the Charging-Rule-Base-Name attribute-value-pair (AVP 1004, vendor Id
         10415) that is included in the DIAMETER Gy CCR message when
         tmnxDiamApGyIncChargingRBaseName is set to 'true'."
    DEFVAL      { "" }
    ::= { tmnxDiamApGyEntry 24 }

tmnxDiamApGyIncPdpContextType    OBJECT-TYPE
    SYNTAX      TruthValue
    MAX-ACCESS  read-create
    STATUS      current
    DESCRIPTION
        "The value of tmnxDiamApGyIncPdpContextType specifies whether or not
         the PDP-Context-Type attribute-value-pair (AVP 1247, vendor Id 10415)
         is included in the DIAMETER Gy CCR message."
    DEFVAL      { true }
    ::= { tmnxDiamApGyEntry 25 }

tmnxDiamApGyIncUserEqInfoType    OBJECT-TYPE
    SYNTAX      INTEGER {
        disabled (0),
        imeisv   (1)
    }
    MAX-ACCESS  read-create
    STATUS      current
    DESCRIPTION
        "The value of tmnxDiamApGyIncUserEqInfoType specifies if the
         User-Equipment-Info attribute-value-pair (AVP 458) is included in
         DIAMETER Gy CCR messages.

         disabled : do not include this AVP in the DIAMETER Gy CCR message;
         imeisv   : indicates that the User-Equipment-Info-Type (AVP 459)
                    is set to imeisv and the User-Eguipment-Info-Value (AVP 460)
                    contains the imei value."
    DEFVAL      { disabled }
    ::= { tmnxDiamApGyEntry 26 }

tmnxDiamApGxTableLastCh          OBJECT-TYPE
    SYNTAX      TimeStamp
    MAX-ACCESS  read-only
    STATUS      current
    DESCRIPTION
        "The value of tmnxDiamApGxTableLastCh indicates the sysUpTime at the
         time of the most recent management-initiated change to the
         tmnxDiamApGxTable."
    ::= { tmnxDiameterObjects 5 }

tmnxDiamApGxTable                OBJECT-TYPE
    SYNTAX      SEQUENCE OF TmnxDiamApGxEntry
    MAX-ACCESS  not-accessible
    STATUS      current
    DESCRIPTION
        "The tmnxDiamApGxTable contains objects to configure Gx for DIAMETER
         Application Policies."
    REFERENCE
        "3GPP TS 29.212 Policy and Charging Control (PCC); Reference points
         section 4 Gx reference point."
    ::= { tmnxDiameterObjects 6 }

tmnxDiamApGxEntry                OBJECT-TYPE
    SYNTAX      TmnxDiamApGxEntry
    MAX-ACCESS  not-accessible
    STATUS      current
    DESCRIPTION
        "Each conceptual row represents Gx information about a particular
         DIAMETER application policy.

         Entries in this table are created and destroyed automatically by the
         system., by setting or clearing the 'gx' bit in the object
         tmnxDiamAppPlcyApplication"
    INDEX       { IMPLIED tmnxDiamAppPlcyId }
    ::= { tmnxDiamApGxTable 1 }

TmnxDiamApGxEntry                ::= SEQUENCE
{
    tmnxDiamApGxLastMgmtChange       TimeStamp,
    tmnxDiamApGxAvp                  BITS,
    tmnxDiamApGxAvpClngStationIdType TmnxSubCallingStationIdType,
    tmnxDiamApGxAvpNasPortBitspec    TmnxBinarySpecification,
    tmnxDiamApGxAvpNasPortIdPfixType TmnxSubNasPortPrefixType,
    tmnxDiamApGxAvpNasPortIdPfixStr  DisplayString,
    tmnxDiamApGxAvpNasPortIdSfixType INTEGER,
    tmnxDiamApGxAvpNasPortTypeValue  Unsigned32,
    tmnxDiamApGxAvpUeInfoType        INTEGER,
    tmnxDiamApGxSubIdOrg             TmnxDiamPlcyDccaAvpOriginType,
    tmnxDiamApGxSubIdType            INTEGER,
    tmnxDiamApGxMacFormat            TmnxMacSpecification,
    tmnxDiamApGxReportIpAddrEvent    TruthValue,
    tmnxDiamApGxAvpNasPortIdSfixStr  DisplayString,
    tmnxDiamApGxCcrtReplayInterval   Unsigned32
}

tmnxDiamApGxLastMgmtChange       OBJECT-TYPE
    SYNTAX      TimeStamp
    MAX-ACCESS  read-only
    STATUS      current
    DESCRIPTION
        "The value of tmnxDiamApGxLastMgmtChange indicates the sysUpTime at the
         time of the most recent management-initiated change to this table row."
    ::= { tmnxDiamApGxEntry 1 }

tmnxDiamApGxAvp                  OBJECT-TYPE
    SYNTAX      BITS {
        anGwAddress       (0),
        callingStationId  (1),
        calledStationId   (2),
        ipCanType         (3),
        logicalAccessId   (4),
        nasPort           (5),
        nasPortId         (6),
        nasPortType       (7),
        physicalAccessId  (8),
        ratType           (9),
        supportedFeatures (10),
        userEquipmentInfo (11),
        apnAmbr           (12),
        reserved13        (13),
        reserved14        (14),
        pdnConnectionId   (15),
        rai               (16),
        reserved17        (17),
        sgsnMccMnc        (18),
        userLocationInfo  (19)
    }
    MAX-ACCESS  read-create
    STATUS      current
    DESCRIPTION
        "The value of tmnxDiamApGxAvp specifies what DIAMETER
         attribute-value-pairs the system should include into DIAMETER Gx
         messages."
    REFERENCE
        "RFC 4006 Diameter Credit-Control Application
         section 8. Credit-Control AVPs.

         RFC 4005 Diameter Network Access Server Application
         section 4 NAS Session AVPs.

         3GPP TS 29.212 Policy and Charging Control (PCC); Reference points
         section 4 Gx reference point."
    DEFVAL      { {} }
    ::= { tmnxDiamApGxEntry 2 }

tmnxDiamApGxAvpClngStationIdType OBJECT-TYPE
    SYNTAX      TmnxSubCallingStationIdType
    MAX-ACCESS  read-create
    STATUS      current
    DESCRIPTION
        "The value of tmnxDiamApGxAvpClngStationIdType specifies what string
         will be put in the DIAMETER Calling-Station-Id attribute if included
         in DIAMETER Gx messages.

         This field is only applicable if the 'callingStationId' bit is set in
         tmnxDiamApGxAvp."
    REFERENCE
        "RFC 4005 Diameter Network Access Server Application
         section 4.6.  Calling-Station-Id AVP."
    DEFVAL      { sapString }
    ::= { tmnxDiamApGxEntry 3 }

tmnxDiamApGxAvpNasPortBitspec    OBJECT-TYPE
    SYNTAX      TmnxBinarySpecification
    MAX-ACCESS  read-create
    STATUS      current
    DESCRIPTION
        "The value of tmnxDiamApGxAvpNasPortBitspec specifies what number will
         be put in the DIAMETER NAS-Port attribute if included in DIAMETER Gx
         messages.

         This field is only applicable if the 'nasPort' bit is set in
         tmnxDiamApGxAvp.

         <origin>               ::= 'o' | 'i' | 's' | 'm' | 'p' | 'v' | 'c'

         'c' - ATM VCI (Virtual Channel Identifier) 'i' - inner VLAN ID 'm' -
         MDA number 'o' - outer VLAN ID 'p' - port number 's' - slot number 'v'
         - ATM VPI (Virtual Path Identifier)

         Maximum 32 bits can be specified.

         If less than 32 bits are specified, the least significant bits are
         used and the omitted higher bits are set to zero.

         Example:  *12o*12i*2s01 means 'the 12 least significant bits of the
         outer VLAN ID, followed by the 12 least significant bits of the inner
         VLAN ID, followed by the two least significant bits of the slot number,
         followed by a zero and a one-bit', stored in network order in the least
         significant bits: 0000ooooooooooooiiiiiiiiiiiiss01."
    REFERENCE
        "RFC 4005 Diameter Network Access Server Application
         section 4.2.  NAS-Port AVP."
    DEFVAL      { "" }
    ::= { tmnxDiamApGxEntry 4 }

tmnxDiamApGxAvpNasPortIdPfixType OBJECT-TYPE
    SYNTAX      TmnxSubNasPortPrefixType
    MAX-ACCESS  read-create
    STATUS      current
    DESCRIPTION
        "The value of tmnxDiamApGxAvpNasPortIdPfixType specifies what type of
         prefix will be added to the NAS-Port-Id attribute if included in
         DIAMETER Gx messages.

         This field is only applicable if the 'nasPortId' bit is set in
         tmnxDiamApGxAvp."
    REFERENCE
        "RFC 4005 Diameter Network Access Server Application
         section 4.3.  NAS-Port-Id AVP."
    DEFVAL      { none }
    ::= { tmnxDiamApGxEntry 5 }

tmnxDiamApGxAvpNasPortIdPfixStr  OBJECT-TYPE
    SYNTAX      DisplayString (SIZE (0..8))
    MAX-ACCESS  read-create
    STATUS      current
    DESCRIPTION
        "The value of tmnxDiamApGxAvpNasPortIdPfixStr specifies the user
         configurable string to be added as prefix to the NAS-Port-Id attribute
         if included in DIAMETER Gx messages.

         This field is only applicable if the 'nasPortId' bit is set in
         tmnxDiamApGxAvp and tmnxDiamApGxAvpNasPortIdPfixType is set to
         'userString'."
    DEFVAL      { "" }
    ::= { tmnxDiamApGxEntry 6 }

tmnxDiamApGxAvpNasPortIdSfixType OBJECT-TYPE
    SYNTAX      INTEGER {
        none       (0),
        circuitId  (1),
        remoteId   (2),
        userString (3)
    }
    MAX-ACCESS  read-create
    STATUS      current
    DESCRIPTION
        "The value of tmnxDiamApGxAvpNasPortIdSfixType specifies what type of
         suffix will be added to the NAS-Port-Id attribute if included in
         DIAMETER Gx messages.

         This field is only applicable if the 'nasPortId' bit is set in
         tmnxDiamApGxAvp."
    DEFVAL      { none }
    ::= { tmnxDiamApGxEntry 7 }

tmnxDiamApGxAvpNasPortTypeValue  OBJECT-TYPE
    SYNTAX      Unsigned32 (0..255)
    MAX-ACCESS  read-create
    STATUS      current
    DESCRIPTION
        "The value of tmnxDiamApGxAvpNasPortTypeValue specifies what value will
         be put in the DIAMETER NAS-Port-Type attribute if included in DIAMETER
         Gx messages.

         This field is only applicable if the 'nasPortType' bit is set in
         tmnxDiamApGxAvp."
    REFERENCE
        "RFC 4005 Diameter Network Access Server Application
         section 4.4.  NAS-Port-Type AVP."
    DEFVAL      { 0 }
    ::= { tmnxDiamApGxEntry 8 }

tmnxDiamApGxAvpUeInfoType        OBJECT-TYPE
    SYNTAX      INTEGER {
        imeisv        (0),
        mac           (1),
        eui64         (2),
        modifiedEui64 (3)
    }
    MAX-ACCESS  read-create
    STATUS      current
    DESCRIPTION
        "The value of tmnxDiamApGxAvpUeInfoType specifies what will be put in
         the DIAMETER User-Equipment-Info attribute if included in DIAMETER Gx
         messages.

         This field is only applicable if the 'userEquipmentInfo' bit is set in
         tmnxDiamApGxAvp."
    REFERENCE
        "RFC 4006 Diameter Credit-Control Application
         section 8.50.  User-Equipment-Info-Type AVP."
    DEFVAL      { mac }
    ::= { tmnxDiamApGxEntry 9 }

tmnxDiamApGxSubIdOrg             OBJECT-TYPE
    SYNTAX      TmnxDiamPlcyDccaAvpOriginType { subscriberId (1), circuitId (2), imsi (3), msisdn (4), imei (5), dualStackRemoteId (6), mac (7), username (8), nasPortId (9) }
    MAX-ACCESS  read-create
    STATUS      current
    DESCRIPTION
        "The value of tmnxDiamApGxSubIdOrg specifies the origin of the
         information to send in the Subscription-Id-Data AVP."
    REFERENCE
        "RFC 4006 Diameter Credit-Control Application
         section 8.48. Subscription-Id-Data AVP."
    DEFVAL      { subscriberId }
    ::= { tmnxDiamApGxEntry 10 }

tmnxDiamApGxSubIdType            OBJECT-TYPE
    SYNTAX      INTEGER {
        e164    (0),
        imsi    (1),
        nai     (3),
        private (4)
    }
    MAX-ACCESS  read-create
    STATUS      current
    DESCRIPTION
        "The value of tmnxDiamApGxSubIdType specifies the type of the
         identifier stored in the Subscription-Id-Data AVP."
    REFERENCE
        "RFC 4006 Diameter Credit-Control Application
         section 8.47. Subscription-Id-Type AVP."
    DEFVAL      { private }
    ::= { tmnxDiamApGxEntry 11 }

tmnxDiamApGxMacFormat            OBJECT-TYPE
    SYNTAX      TmnxMacSpecification (SIZE (2..7))
    MAX-ACCESS  read-create
    STATUS      current
    DESCRIPTION
        "The value of tmnxDiamApGxMacFormat specifies how a MAC address is
         represented when contacting a DIAMETER server.

         Examples:

         'ab:'               00:0c:f1:99:85:b8  Nokia SROS style
         'XY-'               00-0C-F1-99-85-B8  IEEE canonical style
         'mmmm.'             0002.03aa.abff     Cisco style."
    DEFVAL      { "aa:" }
    ::= { tmnxDiamApGxEntry 12 }

tmnxDiamApGxReportIpAddrEvent    OBJECT-TYPE
    SYNTAX      TruthValue
    MAX-ACCESS  read-create
    STATUS      current
    DESCRIPTION
        "The value of tmnxDiamApGxReportIpAddrEvent specifies if this system
         sends CCR-u messages based on IP address allocation/de-allocation
         events for the subscriber.

         This is applicable to dual-stack subscribers (subscribers that have an
         IPv4 host and an IPv6 host).

         If the value of the object tmnxDiamApGxReportIpAddrEvent is equal to
         'false', this system will transmit only a CCR-i containing the IP
         address that triggered the subscriber context creation.

         If the value of the object tmnxDiamApGxReportIpAddrEvent is equal to
         'true', this system will transmit additional CCR-u upon address
         requests for the other family."
    DEFVAL      { true }
    ::= { tmnxDiamApGxEntry 13 }

tmnxDiamApGxAvpNasPortIdSfixStr  OBJECT-TYPE
    SYNTAX      DisplayString (SIZE (0..64))
    MAX-ACCESS  read-create
    STATUS      current
    DESCRIPTION
        "The value of tmnxDiamApGxAvpNasPortIdSfixStr specifies the user
         configurable string to be added as suffix to the NAS-Port-Id attribute
         if included in DIAMETER Gx messages.

         This field is only applicable if the 'nasPortId' bit is set in
         tmnxDiamApGxAvp and tmnxDiamApGxAvpNasPortIdPfixType is set to
         'userString'."
    DEFVAL      { "" }
    ::= { tmnxDiamApGxEntry 14 }

tmnxDiamApGxCcrtReplayInterval   OBJECT-TYPE
    SYNTAX      Unsigned32 (0 | 60..86400)
    UNITS       "seconds"
    MAX-ACCESS  read-create
    STATUS      current
    DESCRIPTION
        "The value of tmnxDiamApGxCcrtReplayInterval specifies the interval
         between two consecutive CCR (Credit-Control-Request)
         Session-Terminate-Request replay attempts.

         If the value of this object is 0, the CCR-T replay functionality is
         disabled."
    DEFVAL      { 0 }
    ::= { tmnxDiamApGxEntry 15 }

tmnxDiamApNqTableLastCh          OBJECT-TYPE
    SYNTAX      TimeStamp
    MAX-ACCESS  read-only
    STATUS      current
    DESCRIPTION
        "The value of tmnxDiamApNqTableLastCh indicates the sysUpTime at the
         time of the most recent management-initiated change to the
         tmnxDiamApNqTable."
    ::= { tmnxDiameterObjects 7 }

tmnxDiamApNqTable                OBJECT-TYPE
    SYNTAX      SEQUENCE OF TmnxDiamApNqEntry
    MAX-ACCESS  not-accessible
    STATUS      current
    DESCRIPTION
        "The tmnxDiamApNqTable contains objects to configure the Diameter
         protocol application used for AAA in the Network Access Server (NAS)
         environment."
    REFERENCE
        "RFC 4005 Diameter Network Access Server Application (NASREQ)."
    ::= { tmnxDiameterObjects 8 }

tmnxDiamApNqEntry                OBJECT-TYPE
    SYNTAX      TmnxDiamApNqEntry
    MAX-ACCESS  not-accessible
    STATUS      current
    DESCRIPTION
        "Each conceptual row represents NASREQ information about a particular
         DIAMETER application policy.

         Entries in this table are created and destroyed automatically by the
         system., by setting or clearing the 'nasreq' bit in the object
         tmnxDiamAppPlcyApplication"
    INDEX       { IMPLIED tmnxDiamAppPlcyId }
    ::= { tmnxDiamApNqTable 1 }

TmnxDiamApNqEntry                ::= SEQUENCE
{
    tmnxDiamApNqLastMgmtChange       TimeStamp,
    tmnxDiamApNqAvp                  BITS,
    tmnxDiamApNqAvpClngStationIdType TmnxSubCallingStationIdType,
    tmnxDiamApNqAvpNasPortBitspec    TmnxBinarySpecification,
    tmnxDiamApNqAvpNasPortIdPfixType TmnxSubNasPortPrefixType,
    tmnxDiamApNqAvpNasPortIdPfixStr  DisplayString,
    tmnxDiamApNqAvpNasPortIdSfixType INTEGER,
    tmnxDiamApNqAvpNasPortIdSfixStr  DisplayString,
    tmnxDiamApNqAvpNasPortTypeType   TmnxSubNasPortTypeType,
    tmnxDiamApNqAvpNasPortTypeValue  Unsigned32,
    tmnxDiamApNqPassword             TmnxAuthPassword,
    tmnxDiamApNqUserNameFormat       INTEGER,
    tmnxDiamApNqUserNameOp           TmnxSubAuthPlcyUserNameOp,
    tmnxDiamApNqDomain               DisplayString,
    tmnxDiamApNqMacFormat            TmnxMacSpecification
}

tmnxDiamApNqLastMgmtChange       OBJECT-TYPE
    SYNTAX      TimeStamp
    MAX-ACCESS  read-only
    STATUS      current
    DESCRIPTION
        "The value of tmnxDiamApNqLastMgmtChange indicates the sysUpTime at the
         time of the most recent management-initiated change to this table row."
    ::= { tmnxDiamApNqEntry 1 }

tmnxDiamApNqAvp                  OBJECT-TYPE
    SYNTAX      BITS {
        circuitId        (0),
        remote-id        (1),
        calledStationId  (2),
        callingStationId (3),
        nasPort          (4),
        nasPortId        (5),
        nasPortType      (6),
        imei             (7),
        ratType          (8),
        userLocationInfo (9)
    }
    MAX-ACCESS  read-create
    STATUS      current
    DESCRIPTION
        "The value of tmnxDiamApNqAvp specifies what DIAMETER
         attribute-value-pairs the system should include into DIAMETER NASREQ
         messages."
    REFERENCE
        "RFC 4005 Diameter Network Access Server Application
         section 5. NAS Authentication AVPs."
    DEFVAL      { {} }
    ::= { tmnxDiamApNqEntry 2 }

tmnxDiamApNqAvpClngStationIdType OBJECT-TYPE
    SYNTAX      TmnxSubCallingStationIdType
    MAX-ACCESS  read-create
    STATUS      current
    DESCRIPTION
        "The value of tmnxDiamApNqAvpClngStationIdType specifies what string
         will be put in the DIAMETER Calling-Station-Id attribute if included
         in DIAMETER NASREQ messages.

         This field is only applicable if the 'callingStationId' bit is set in
         tmnxDiamApNqAvp."
    REFERENCE
        "RFC 4005 Diameter Network Access Server Application
         section 4.6.  Calling-Station-Id AVP."
    DEFVAL      { sapString }
    ::= { tmnxDiamApNqEntry 3 }

tmnxDiamApNqAvpNasPortBitspec    OBJECT-TYPE
    SYNTAX      TmnxBinarySpecification
    MAX-ACCESS  read-create
    STATUS      current
    DESCRIPTION
        "The value of tmnxDiamApNqAvpNasPortBitspec specifies what number will
         be put in the DIAMETER NAS-Port attribute if included in DIAMETER
         NASREQ messages.

         This field is only applicable if the 'nasPort' bit is set in
         tmnxDiamApNqAvp.

         <origin>               ::= 'o' | 'i' | 's' | 'm' | 'p' | 'v' | 'c'

         'c' - ATM VCI (Virtual Channel Identifier) 'i' - inner VLAN ID 'm' -
         MDA number 'o' - outer VLAN ID 'p' - port number 's' - slot number 'v'
         - ATM VPI (Virtual Path Identifier)

         Maximum 32 bits can be specified.

         If less than 32 bits are specified, the least significant bits are
         used and the omitted higher bits are set to zero.

         Example:  *12o*12i*2s01 means 'the 12 least significant bits of the
         outer VLAN ID, followed by the 12 least significant bits of the inner
         VLAN ID, followed by the two least significant bits of the slot number,
         followed by a zero and a one-bit', stored in network order in the least
         significant bits: 0000ooooooooooooiiiiiiiiiiiiss01."
    REFERENCE
        "RFC 4005 Diameter Network Access Server Application
         section 4.2.  NAS-Port AVP."
    DEFVAL      { "" }
    ::= { tmnxDiamApNqEntry 4 }

tmnxDiamApNqAvpNasPortIdPfixType OBJECT-TYPE
    SYNTAX      TmnxSubNasPortPrefixType
    MAX-ACCESS  read-create
    STATUS      current
    DESCRIPTION
        "The value of tmnxDiamApNqAvpNasPortIdPfixType specifies what type of
         prefix will be added to the NAS-Port-Id attribute if included in
         DIAMETER NASREQ messages.

         This field is only applicable if the 'nasPortId' bit is set in
         tmnxDiamApNqAvp."
    REFERENCE
        "RFC 4005 Diameter Network Access Server Application
         section 4.3.  NAS-Port-Id AVP."
    DEFVAL      { none }
    ::= { tmnxDiamApNqEntry 5 }

tmnxDiamApNqAvpNasPortIdPfixStr  OBJECT-TYPE
    SYNTAX      DisplayString (SIZE (0..8))
    MAX-ACCESS  read-create
    STATUS      current
    DESCRIPTION
        "The value of tmnxDiamApNqAvpNasPortIdPfixStr specifies the user
         configurable string to be added as prefix to the NAS-Port-Id attribute
         if included in DIAMETER NASREQ messages.

         This field is only applicable if the 'nasPortId' bit is set in
         tmnxDiamApNqAvp and tmnxDiamApNqAvpNasPortIdPfixType is set to
         'userString'."
    DEFVAL      { "" }
    ::= { tmnxDiamApNqEntry 6 }

tmnxDiamApNqAvpNasPortIdSfixType OBJECT-TYPE
    SYNTAX      INTEGER {
        none       (0),
        circuitId  (1),
        remoteId   (2),
        userString (3)
    }
    MAX-ACCESS  read-create
    STATUS      current
    DESCRIPTION
        "The value of tmnxDiamApNqAvpNasPortIdSfixType specifies what type of
         suffix will be added to the NAS-Port-Id attribute if included in
         DIAMETER NASREQ messages.

         This field is only applicable if the 'nasPortId' bit is set in
         tmnxDiamApNqAvp."
    DEFVAL      { none }
    ::= { tmnxDiamApNqEntry 7 }

tmnxDiamApNqAvpNasPortIdSfixStr  OBJECT-TYPE
    SYNTAX      DisplayString (SIZE (0..64))
    MAX-ACCESS  read-create
    STATUS      current
    DESCRIPTION
        "The value of tmnxDiamApNqAvpNasPortIdSfixStr specifies the user
         configurable string to be added as suffix to the NAS-Port-Id attribute
         if included in DIAMETER NASREQ messages.

         This field is only applicable if the 'nasPortId' bit is set in
         tmnxDiamApNqAvp and tmnxDiamApNqAvpNasPortIdSfixType is set to
         'userString'."
    DEFVAL      { "" }
    ::= { tmnxDiamApNqEntry 8 }

tmnxDiamApNqAvpNasPortTypeType   OBJECT-TYPE
    SYNTAX      TmnxSubNasPortTypeType
    MAX-ACCESS  read-create
    STATUS      current
    DESCRIPTION
        "The value of tmnxDiamApNqAvpNasPortTypeType specifies what kind of
         value will be put in the DIAMETER NAS-Port-Type attribute if included
         in DIAMETER NASREQ messages.

         This field is only applicable if the 'nasPortType' bit is set in
         tmnxDiamApNqAvp."
    DEFVAL      { standard }
    ::= { tmnxDiamApNqEntry 9 }

tmnxDiamApNqAvpNasPortTypeValue  OBJECT-TYPE
    SYNTAX      Unsigned32 (0..255)
    MAX-ACCESS  read-create
    STATUS      current
    DESCRIPTION
        "The value of tmnxDiamApNqAvpNasPortTypeValue specifies what value will
         be put in the DIAMETER NAS-Port-Type attribute if included in DIAMETER
         NASREQ messages.

         This field is only applicable if the 'nasPortType' bit is set in
         tmnxDiamApNqAvp and the value of the object
         tmnxDiamApNqAvpNasPortTypeType is equal to 'config'."
    REFERENCE
        "RFC 4005 Diameter Network Access Server Application
         section 4.4.  NAS-Port-Type AVP."
    DEFVAL      { 0 }
    ::= { tmnxDiamApNqEntry 10 }

tmnxDiamApNqPassword             OBJECT-TYPE
    SYNTAX      TmnxAuthPassword
    MAX-ACCESS  read-create
    STATUS      current
    DESCRIPTION
        "The value of tmnxDiamApNqPassword specifies the string to use in the
         DIAMETER User-Password AVP.

         A get request on this object always returns an empty string."
    REFERENCE
        "RFC 4005 Diameter Network Access Server Application,
         section 5.1. User-Password AVP"
    DEFVAL      { "" }
    ::= { tmnxDiamApNqEntry 11 }

tmnxDiamApNqUserNameFormat       OBJECT-TYPE
    SYNTAX      INTEGER {
        mac                     (1),
        circuitId               (2),
        tuple                   (3),
        asciiConvertedCircuitId (4),
        asciiConvertedTuple     (5),
        dhcpClientVendorOpts    (6),
        macGiaddr               (7),
        nasPortId               (8)
    }
    MAX-ACCESS  read-create
    STATUS      current
    DESCRIPTION
        "The value of tmnxDiamApNqUserNameFormat specifies the format used to
         identify the user towards the DIAMETER server."
    DEFVAL      { mac }
    ::= { tmnxDiamApNqEntry 12 }

tmnxDiamApNqUserNameOp           OBJECT-TYPE
    SYNTAX      TmnxSubAuthPlcyUserNameOp
    MAX-ACCESS  read-create
    STATUS      current
    DESCRIPTION
        "The value of tmnxDiamApNqUserNameOp specifies the operation to perform
         on the PAP/CHAP user name.

         When the value is 'appendDomain', the string specified by
         'tmnxDiamApNqDomain', preceded with a '@', is appended to the PAP/CHAP
         user name.

         When the value is 'stripDomain', any '@' character and all subsequent
         characters are removed from the PAP/CHAP user name.

         When the value is 'replaceDomain', all characters after a '@'
         delimiter are replaced with the string specified by
         'tmnxDiamApNqDomain'.

         When the value is 'defaultDomain', the same action is performed as
         with 'appendDomain', but only if the PAP/CHAP user name does not
         contain a domain name already."
    DEFVAL      { noOperation }
    ::= { tmnxDiamApNqEntry 13 }

tmnxDiamApNqDomain               OBJECT-TYPE
    SYNTAX      DisplayString (SIZE (0..128))
    MAX-ACCESS  read-create
    STATUS      current
    DESCRIPTION
        "The value of tmnxDiamApNqDomain specifies the domain name to use with
         user name operations.

         This object is only relevant while the value of the object
         'tmnxDiamApNqUserNameOp' is equal to 'appendDomain', 'replaceDomain'
         or 'defaultDomain'."
    DEFVAL      { "" }
    ::= { tmnxDiamApNqEntry 14 }

tmnxDiamApNqMacFormat            OBJECT-TYPE
    SYNTAX      TmnxMacSpecification (SIZE (2..7))
    MAX-ACCESS  read-create
    STATUS      current
    DESCRIPTION
        "The value of tmnxDiamApNqMacFormat specifies how a MAC address is
         represented when contacting a DIAMETER server.

         Examples:

         'ab:'               00:0c:f1:99:85:b8  Nokia SROS style
         'XY-'               00-0C-F1-99-85-B8  IEEE canonical style
         'mmmm.'             0002.03aa.abff     Cisco style."
    DEFVAL      { "aa:" }
    ::= { tmnxDiamApNqEntry 15 }

tmnxDiamPpPrxTableLastCh         OBJECT-TYPE
    SYNTAX      TimeStamp
    MAX-ACCESS  read-only
    STATUS      current
    DESCRIPTION
        "The value of tmnxDiamPpPrxTableLastCh indicates the sysUpTime at the
         time of the most recent management-initiated change to the
         tmnxDiamPpPrxTable."
    ::= { tmnxDiameterObjects 9 }

tmnxDiamPpPrxTable               OBJECT-TYPE
    SYNTAX      SEQUENCE OF TmnxDiamPpPrxEntry
    MAX-ACCESS  not-accessible
    STATUS      current
    DESCRIPTION
        "The tmnxDiamPpPrxTable contains objects to configure DIAMETER peer
         policies in the 'proxy' role."
    ::= { tmnxDiameterObjects 10 }

tmnxDiamPpPrxEntry               OBJECT-TYPE
    SYNTAX      TmnxDiamPpPrxEntry
    MAX-ACCESS  not-accessible
    STATUS      current
    DESCRIPTION
        "Each conceptual row represents proxy information about a particular
         DIAMETER peer policy.

         A row in this table is created and destroyed automatically by the
         system when a row in the tmnxDiameterPlcyTable is created with a value
         of 'proxy' for the tmnxDiamPlcyRole object."
    INDEX       { tmnxDiamPlcyName }
    ::= { tmnxDiamPpPrxTable 1 }

TmnxDiamPpPrxEntry               ::= SEQUENCE
{
    tmnxDiamPpPrxLastMgmtChange      TimeStamp,
    tmnxDiamPpPrxAdminState          TmnxEnabledDisabledAdminState,
    tmnxDiamPpPrxRouter              TmnxVRtrIDOrZero,
    tmnxDiamPpPrxAddrType            InetAddressType,
    tmnxDiamPpPrxAddr                InetAddress,
    tmnxDiamPpPrxOperState           INTEGER,
    tmnxDiamPpPrxMcLocState          TmnxDiamProxyState,
    tmnxDiamPpPrxMcLocOriginStateId  Unsigned32,
    tmnxDiamPpPrxMcLocMacAddress     MacAddress,
    tmnxDiamPpPrxMcLocCtrlMacAddress MacAddress,
    tmnxDiamPpPrxMcRemState          TmnxDiamProxyState,
    tmnxDiamPpPrxMcRemOriginStateId  Unsigned32,
    tmnxDiamPpPrxMcRemMacAddress     MacAddress,
    tmnxDiamPpPrxMcRemCtrlMacAddress MacAddress
}

tmnxDiamPpPrxLastMgmtChange      OBJECT-TYPE
    SYNTAX      TimeStamp
    MAX-ACCESS  read-only
    STATUS      current
    DESCRIPTION
        "The value of tmnxDiamPpPrxLastMgmtChange indicates the sysUpTime at
         the time of the most recent management-initiated change to this table
         row."
    ::= { tmnxDiamPpPrxEntry 1 }

tmnxDiamPpPrxAdminState          OBJECT-TYPE
    SYNTAX      TmnxEnabledDisabledAdminState
    MAX-ACCESS  read-create
    STATUS      current
    DESCRIPTION
        "The value of the object tmnxDiamPpPrxAdminState specifies the
         administrative state of the Diameter Proxy function in the virtual
         router instance specified by tmnxDiamPpPrxRouter."
    DEFVAL      { disabled }
    ::= { tmnxDiamPpPrxEntry 2 }

tmnxDiamPpPrxRouter              OBJECT-TYPE
    SYNTAX      TmnxVRtrIDOrZero
    MAX-ACCESS  read-create
    STATUS      current
    DESCRIPTION
        "The value of tmnxDiamPpPrxRouter specifies the virtual router instance
         where this Diameter Proxy function is communicating with the Diameter
         'client' peer."
    DEFVAL      { 0 }
    ::= { tmnxDiamPpPrxEntry 3 }

tmnxDiamPpPrxAddrType            OBJECT-TYPE
    SYNTAX      InetAddressType
    MAX-ACCESS  read-create
    STATUS      current
    DESCRIPTION
        "The value of tmnxDiamPpPrxAddrType specifies the address type of
         tmnxDiamPpPrxAddr."
    DEFVAL      { unknown }
    ::= { tmnxDiamPpPrxEntry 4 }

tmnxDiamPpPrxAddr                OBJECT-TYPE
    SYNTAX      InetAddress (SIZE (0|4|16))
    MAX-ACCESS  read-create
    STATUS      current
    DESCRIPTION
        "The value of tmnxDiamPpPrxAddr specifies the IP address of the
         Diameter Proxy function within the router instance specified by
         tmnxDiamPpPrxRouter."
    DEFVAL      { ''H }
    ::= { tmnxDiamPpPrxEntry 5 }

tmnxDiamPpPrxOperState           OBJECT-TYPE
    SYNTAX      INTEGER {
        inService    (1),
        outOfService (2)
    }
    MAX-ACCESS  read-only
    STATUS      current
    DESCRIPTION
        "The value of the object tmnxDiamPpPrxOperState indicates the
         operational state of the Diameter Proxy function in the virtual router
         instance specified by tmnxDiamPpPrxRouter."
    ::= { tmnxDiamPpPrxEntry 6 }

tmnxDiamPpPrxMcLocState          OBJECT-TYPE
    SYNTAX      TmnxDiamProxyState
    MAX-ACCESS  read-only
    STATUS      current
    DESCRIPTION
        "The value of the object tmnxDiamPpPrxMcLocState indicates the state of
         the Diameter Proxy function of this system."
    ::= { tmnxDiamPpPrxEntry 7 }

tmnxDiamPpPrxMcLocOriginStateId  OBJECT-TYPE
    SYNTAX      Unsigned32
    MAX-ACCESS  read-only
    STATUS      current
    DESCRIPTION
        "The value of the object tmnxDiamPpPrxMcLocOriginStateId indicates the
         value of the Origin-State-Id AVP that this system uses in
         multi-chassis operation."
    REFERENCE
        "RFC 3588 Diameter Based Protocol
         section 8.16. Origin-State-Id AVP"
    ::= { tmnxDiamPpPrxEntry 8 }

tmnxDiamPpPrxMcLocMacAddress     OBJECT-TYPE
    SYNTAX      MacAddress
    MAX-ACCESS  read-only
    STATUS      current
    DESCRIPTION
        "The value of the object tmnxDiamPpPrxMcLocMacAddress indicates the MAC
         address that this system uses as identifier in multi-chassis
         operation."
    ::= { tmnxDiamPpPrxEntry 9 }

tmnxDiamPpPrxMcLocCtrlMacAddress OBJECT-TYPE
    SYNTAX      MacAddress
    MAX-ACCESS  read-only
    STATUS      current
    DESCRIPTION
        "The value of the object tmnxDiamPpPrxMcLocCtrlMacAddress indicates the
         MAC address that this system considers to be the identifier of the
         multi-chassis controller."
    ::= { tmnxDiamPpPrxEntry 10 }

tmnxDiamPpPrxMcRemState          OBJECT-TYPE
    SYNTAX      TmnxDiamProxyState
    MAX-ACCESS  read-only
    STATUS      current
    DESCRIPTION
        "The value of the object tmnxDiamPpPrxMcRemState indicates the state of
         the Diameter Proxy function of the multi-chassis redundancy peer."
    ::= { tmnxDiamPpPrxEntry 11 }

tmnxDiamPpPrxMcRemOriginStateId  OBJECT-TYPE
    SYNTAX      Unsigned32
    MAX-ACCESS  read-only
    STATUS      current
    DESCRIPTION
        "The value of the object tmnxDiamPpPrxMcRemOriginStateId indicates the
         value of the Origin-State-Id AVP that the multi-chassis redundancy
         peer uses."
    REFERENCE
        "RFC 3588 Diameter Based Protocol
         section 8.16. Origin-State-Id AVP"
    ::= { tmnxDiamPpPrxEntry 12 }

tmnxDiamPpPrxMcRemMacAddress     OBJECT-TYPE
    SYNTAX      MacAddress
    MAX-ACCESS  read-only
    STATUS      current
    DESCRIPTION
        "The value of the object tmnxDiamPpPrxMcRemMacAddress indicates the MAC
         address that the peer system uses as identifier in multi-chassis
         operation.

         The value all zeroes indicates that the MAC address is not known."
    ::= { tmnxDiamPpPrxEntry 13 }

tmnxDiamPpPrxMcRemCtrlMacAddress OBJECT-TYPE
    SYNTAX      MacAddress
    MAX-ACCESS  read-only
    STATUS      current
    DESCRIPTION
        "The value of the object tmnxDiamPpPrxMcRemCtrlMacAddress indicates the
         MAC address that the peer considers to be the identifier of the
         multi-chassis controller."
    ::= { tmnxDiamPpPrxEntry 14 }

tmnxDiamPpPrxClientTable         OBJECT-TYPE
    SYNTAX      SEQUENCE OF TmnxDiamPpPrxClientEntry
    MAX-ACCESS  not-accessible
    STATUS      current
    DESCRIPTION
        "The tmnxDiamPpPrxClientTable contains information about the
         client-side peers of the Diameter proxy instances."
    ::= { tmnxDiameterObjects 11 }

tmnxDiamPpPrxClientEntry         OBJECT-TYPE
    SYNTAX      TmnxDiamPpPrxClientEntry
    MAX-ACCESS  not-accessible
    STATUS      current
    DESCRIPTION
        "Each conceptual row represents information about a client-side peer of
         a Diameter proxy instance.

         Rows in this table are created and removed automatically by the system"
    INDEX       {
        tmnxDiamPlcyName,
        tmnxDiamPpPrxClientIpAddrType,
        tmnxDiamPpPrxClientIpAddr,
        tmnxDiamPpPrxClientPort
    }
    ::= { tmnxDiamPpPrxClientTable 1 }

TmnxDiamPpPrxClientEntry         ::= SEQUENCE
{
    tmnxDiamPpPrxClientIpAddrType    InetAddressType,
    tmnxDiamPpPrxClientIpAddr        InetAddress,
    tmnxDiamPpPrxClientPort          InetPortNumber,
    tmnxDiamPpPrxClientPsmState      INTEGER,
    tmnxDiamPpPrxClientTransactions  Gauge32
}

tmnxDiamPpPrxClientIpAddrType    OBJECT-TYPE
    SYNTAX      InetAddressType
    MAX-ACCESS  not-accessible
    STATUS      current
    DESCRIPTION
        "The value of tmnxDiamPpPrxClientIpAddrType indicates the address type
         of tmnxDiamPpPrxClientIpAddr."
    ::= { tmnxDiamPpPrxClientEntry 1 }

tmnxDiamPpPrxClientIpAddr        OBJECT-TYPE
    SYNTAX      InetAddress (SIZE (4|16))
    MAX-ACCESS  not-accessible
    STATUS      current
    DESCRIPTION
        "The value of tmnxDiamPpPrxClientIpAddr indicates the source IP address
         present in Diameter messages received from the peer."
    ::= { tmnxDiamPpPrxClientEntry 2 }

tmnxDiamPpPrxClientPort          OBJECT-TYPE
    SYNTAX      InetPortNumber
    MAX-ACCESS  not-accessible
    STATUS      current
    DESCRIPTION
        "The value of tmnxDiamPpPrxClientPort indicates the TCP source port
         present in Diameter messages received from the peer."
    ::= { tmnxDiamPpPrxClientEntry 3 }

tmnxDiamPpPrxClientPsmState      OBJECT-TYPE
    SYNTAX      INTEGER {
        rOpen    (1),
        waitRcer (2)
    }
    MAX-ACCESS  read-only
    STATUS      current
    DESCRIPTION
        "The value of tmnxDiamPpPrxClientPsmState indicates the state of the
         peer's state machine."
    ::= { tmnxDiamPpPrxClientEntry 4 }

tmnxDiamPpPrxClientTransactions  OBJECT-TYPE
    SYNTAX      Gauge32
    MAX-ACCESS  read-only
    STATUS      current
    DESCRIPTION
        "The value of tmnxDiamPpPrxClientTransactions indicates the number of
         pending transactions."
    ::= { tmnxDiamPpPrxClientEntry 5 }

tmnxDiamPrxClStTable             OBJECT-TYPE
    SYNTAX      SEQUENCE OF TmnxDiamPrxClStEntry
    MAX-ACCESS  not-accessible
    STATUS      obsolete
    DESCRIPTION
        "The tmnxDiamPrxClStTable contains statistics information about the
         client-side peers of the Diameter proxy instances.

         This table was made obsolete in release 14.0. Is is replaced by
         tmnxDiamPeerStatsTable."
    ::= { tmnxDiameterObjects 12 }

tmnxDiamPrxClStEntry             OBJECT-TYPE
    SYNTAX      TmnxDiamPrxClStEntry
    MAX-ACCESS  not-accessible
    STATUS      obsolete
    DESCRIPTION
        "Each conceptual row represents statistics information about a
         client-side peer of a Diameter proxy instance.

         Rows in this table are created and removed automatically by the system"
    AUGMENTS    { tmnxDiamPpPrxClientEntry }
    ::= { tmnxDiamPrxClStTable 1 }

TmnxDiamPrxClStEntry             ::= SEQUENCE
{
    tmnxDiamPrxClStLastClearedTime   TimeStamp,
    tmnxDiamPrxClStCiTcpSendFailed   Counter32,
    tmnxDiamPrxClStCiDiamRxDropCnt   Counter32,
    tmnxDiamPrxClStCiDiamRxReqs      Counter32,
    tmnxDiamPrxClStCiDiamTxResps     Counter32,
    tmnxDiamPrxClStCiPendMsgsPmq     Counter32,
    tmnxDiamPrxClStCiReqTimeoutsPmq  Counter32,
    tmnxDiamPrxClStSiTcpSendFailed   Counter32,
    tmnxDiamPrxClStSiDiamRxDropCnt   Counter32,
    tmnxDiamPrxClStSiDiamTxReqs      Counter32,
    tmnxDiamPrxClStSiDiamRxResps     Counter32,
    tmnxDiamPrxClStCcrInitialRx      Counter32,
    tmnxDiamPrxClStCcaInitialTx      Counter32,
    tmnxDiamPrxClStCcrUpdateRx       Counter32,
    tmnxDiamPrxClStCcaUpdateTx       Counter32,
    tmnxDiamPrxClStCcrTerminateRx    Counter32,
    tmnxDiamPrxClStCcaTerminateTx    Counter32,
    tmnxDiamPrxClStCerRx             Counter32,
    tmnxDiamPrxClStCeaTx             Counter32,
    tmnxDiamPrxClStDwrRx             Counter32,
    tmnxDiamPrxClStDwaTx             Counter32,
    tmnxDiamPrxClStDwrTx             Counter32,
    tmnxDiamPrxClStDwaRx             Counter32,
    tmnxDiamPrxClStAsrTx             Counter32,
    tmnxDiamPrxClStAsaRx             Counter32,
    tmnxDiamPrxClStRarTx             Counter32,
    tmnxDiamPrxClStRaaRx             Counter32,
    tmnxDiamPrxClStDprTx             Counter32,
    tmnxDiamPrxClStDpaRx             Counter32,
    tmnxDiamPrxClStDprRx             Counter32,
    tmnxDiamPrxClStDpaTx             Counter32,
    tmnxDiamPrxClStAarRx             Counter32,
    tmnxDiamPrxClStAaaTx             Counter32
}

tmnxDiamPrxClStLastClearedTime   OBJECT-TYPE
    SYNTAX      TimeStamp
    MAX-ACCESS  read-only
    STATUS      obsolete
    DESCRIPTION
        "The value of tmnxDiamPrxClStLastClearedTime indicates the sysUpTime
         when the counters of this row were last reset.

         A zero value indicates that the counters have not been reset since the
         system has last been initialized."
    ::= { tmnxDiamPrxClStEntry 1 }

tmnxDiamPrxClStCiTcpSendFailed   OBJECT-TYPE
    SYNTAX      Counter32
    MAX-ACCESS  read-only
    STATUS      obsolete
    DESCRIPTION
        "The value of tmnxDiamPrxClStCiTcpSendFailed indicates client initiated
         roundtrip DIAMETER statistics regarding the number of TCP send
         failures."
    ::= { tmnxDiamPrxClStEntry 2 }

tmnxDiamPrxClStCiDiamRxDropCnt   OBJECT-TYPE
    SYNTAX      Counter32
    MAX-ACCESS  read-only
    STATUS      obsolete
    DESCRIPTION
        "The value of tmnxDiamPrxClStCiDiamRxDropCnt indicates client initiated
         roundtrip DIAMETER statistics regarding the number of dropped response
         messages upon reception from the client."
    ::= { tmnxDiamPrxClStEntry 3 }

tmnxDiamPrxClStCiDiamRxReqs      OBJECT-TYPE
    SYNTAX      Counter32
    MAX-ACCESS  read-only
    STATUS      obsolete
    DESCRIPTION
        "The value of tmnxDiamPrxClStCiDiamRxReqs indicates client initiated
         roundtrip DIAMETER statistics regarding the number of request messages
         received from the client."
    ::= { tmnxDiamPrxClStEntry 4 }

tmnxDiamPrxClStCiDiamTxResps     OBJECT-TYPE
    SYNTAX      Counter32
    MAX-ACCESS  read-only
    STATUS      obsolete
    DESCRIPTION
        "The value of tmnxDiamPrxClStCiDiamTxResps indicates client initiated
         roundtrip DIAMETER statistics regarding the number of response
         messages transmitted to the client."
    ::= { tmnxDiamPrxClStEntry 5 }

tmnxDiamPrxClStCiPendMsgsPmq     OBJECT-TYPE
    SYNTAX      Counter32
    MAX-ACCESS  read-only
    STATUS      obsolete
    DESCRIPTION
        "The value of tmnxDiamPrxClStCiPendMsgsPmq indicates client initiated
         roundtrip DIAMETER statistics regarding the number of request messages
         in the Pending Message Queue waiting to be matched with corresponding
         response messages from the client.

         This object is made obsolete in release 14.0. It is replaced by
         tmnxDiamPpPrxClientTransactions."
    ::= { tmnxDiamPrxClStEntry 6 }

tmnxDiamPrxClStCiReqTimeoutsPmq  OBJECT-TYPE
    SYNTAX      Counter32
    MAX-ACCESS  read-only
    STATUS      obsolete
    DESCRIPTION
        "The value of tmnxDiamPrxClStCiReqTimeoutsPmq indicates client
         initiated roundtrip DIAMETER statistics regarding the number of
         request messages that were removed from the Pending Message Queue due
         to a match timeout."
    ::= { tmnxDiamPrxClStEntry 7 }

tmnxDiamPrxClStSiTcpSendFailed   OBJECT-TYPE
    SYNTAX      Counter32
    MAX-ACCESS  read-only
    STATUS      obsolete
    DESCRIPTION
        "The value of tmnxDiamPrxClStSiTcpSendFailed indicates client initiated
         roundtrip DIAMETER statistics regarding the number of TCP send
         failures."
    ::= { tmnxDiamPrxClStEntry 8 }

tmnxDiamPrxClStSiDiamRxDropCnt   OBJECT-TYPE
    SYNTAX      Counter32
    MAX-ACCESS  read-only
    STATUS      obsolete
    DESCRIPTION
        "The value of tmnxDiamPrxClStSiDiamRxDropCnt indicates client initiated
         roundtrip DIAMETER statistics regarding the number of dropped request
         messages upon reception from the client."
    ::= { tmnxDiamPrxClStEntry 9 }

tmnxDiamPrxClStSiDiamTxReqs      OBJECT-TYPE
    SYNTAX      Counter32
    MAX-ACCESS  read-only
    STATUS      obsolete
    DESCRIPTION
        "The value of tmnxDiamPrxClStSiDiamTxReqs indicates client initiated
         roundtrip DIAMETER statistics regarding the number of request messages
         transmitted to the client."
    ::= { tmnxDiamPrxClStEntry 10 }

tmnxDiamPrxClStSiDiamRxResps     OBJECT-TYPE
    SYNTAX      Counter32
    MAX-ACCESS  read-only
    STATUS      obsolete
    DESCRIPTION
        "The value of tmnxDiamPrxClStSiDiamRxResps indicates client initiated
         roundtrip DIAMETER statistics regarding the number of response
         messages received from the client."
    ::= { tmnxDiamPrxClStEntry 11 }

tmnxDiamPrxClStCcrInitialRx      OBJECT-TYPE
    SYNTAX      Counter32
    MAX-ACCESS  read-only
    STATUS      obsolete
    DESCRIPTION
        "The value of tmnxDiamPrxClStCcrInitialRx indicates the number of
         Credit Control Request messages with CC-Request-Type AVP equal to
         UPDAT_REQUEST that are received from the client."
    REFERENCE
        "RFC 4006  Diameter Credit-Control Application,
         section 8.3 and Appendix A1."
    ::= { tmnxDiamPrxClStEntry 14 }

tmnxDiamPrxClStCcaInitialTx      OBJECT-TYPE
    SYNTAX      Counter32
    MAX-ACCESS  read-only
    STATUS      obsolete
    DESCRIPTION
        "The value of tmnxDiamPrxClStCcaInitialTx indicates the number of
         Credit Control Request messages with CC-Request-Type AVP equal to
         INITIAL_REQUEST that are transmitted to the client."
    REFERENCE
        "RFC 4006  Diameter Credit-Control Application,
         section 8.3 and Appendix A1."
    ::= { tmnxDiamPrxClStEntry 15 }

tmnxDiamPrxClStCcrUpdateRx       OBJECT-TYPE
    SYNTAX      Counter32
    MAX-ACCESS  read-only
    STATUS      obsolete
    DESCRIPTION
        "The value of tmnxDiamPrxClStCcrUpdateRx indicates the number of Credit
         Control Request messages with CC-Request-Type AVP equal to
         UPDATE_REQUEST that are received from the client."
    REFERENCE
        "RFC 4006  Diameter Credit-Control Application,
         section 8.3 and Appendix A1."
    ::= { tmnxDiamPrxClStEntry 16 }

tmnxDiamPrxClStCcaUpdateTx       OBJECT-TYPE
    SYNTAX      Counter32
    MAX-ACCESS  read-only
    STATUS      obsolete
    DESCRIPTION
        "The value of tmnxDiamPrxClStCcaUpdateTx indicates the number of Credit
         Control Request messages with CC-Request-Type AVP equal to
         UPDATE_REQUEST that are transmitted to the client."
    REFERENCE
        "RFC 4006  Diameter Credit-Control Application,
         section 8.3 and Appendix A1."
    ::= { tmnxDiamPrxClStEntry 17 }

tmnxDiamPrxClStCcrTerminateRx    OBJECT-TYPE
    SYNTAX      Counter32
    MAX-ACCESS  read-only
    STATUS      obsolete
    DESCRIPTION
        "The value of tmnxDiamPrxClStCcrTerminateRx indicates the number of
         Credit Control Request messages with CC-Request-Type AVP equal to
         TERMINATE_REQUEST that are received from the client."
    REFERENCE
        "RFC 4006  Diameter Credit-Control Application,
         section 8.3 and Appendix A1."
    ::= { tmnxDiamPrxClStEntry 18 }

tmnxDiamPrxClStCcaTerminateTx    OBJECT-TYPE
    SYNTAX      Counter32
    MAX-ACCESS  read-only
    STATUS      obsolete
    DESCRIPTION
        "The value of tmnxDiamPrxClStCcaTerminateTx indicates the number of
         Credit Control Request messages with CC-Request-Type AVP equal to
         TERMINATE_REQUEST that are transmitted to the client."
    REFERENCE
        "RFC 4006  Diameter Credit-Control Application,
         section 8.3 and Appendix A1."
    ::= { tmnxDiamPrxClStEntry 19 }

tmnxDiamPrxClStCerRx             OBJECT-TYPE
    SYNTAX      Counter32
    MAX-ACCESS  read-only
    STATUS      obsolete
    DESCRIPTION
        "The value of tmnxDiamPrxClStCerRx indicates the number of
         Capabilities-Exchange-Request messages that are received from the
         client."
    REFERENCE
        "RFC 3588 Diameter Based Protocol,
         section 5.3.1."
    ::= { tmnxDiamPrxClStEntry 20 }

tmnxDiamPrxClStCeaTx             OBJECT-TYPE
    SYNTAX      Counter32
    MAX-ACCESS  read-only
    STATUS      obsolete
    DESCRIPTION
        "The value of tmnxDiamPrxClStCeaTx indicates the number of
         Capabilities-Exchange-Answer messages that are transmitted to the
         client."
    REFERENCE
        "RFC 3588 Diameter Based Protocol,
         section 5.3.2."
    ::= { tmnxDiamPrxClStEntry 21 }

tmnxDiamPrxClStDwrRx             OBJECT-TYPE
    SYNTAX      Counter32
    MAX-ACCESS  read-only
    STATUS      obsolete
    DESCRIPTION
        "The value of tmnxDiamPrxClStDwrRx indicates the number of
         Device-Watchdog-Request messages that are received from the client."
    REFERENCE
        "RFC 3588 Diameter Based Protocol,
         section 5.5.1."
    ::= { tmnxDiamPrxClStEntry 22 }

tmnxDiamPrxClStDwaTx             OBJECT-TYPE
    SYNTAX      Counter32
    MAX-ACCESS  read-only
    STATUS      obsolete
    DESCRIPTION
        "The value of tmnxDiamPrxClStDwaTx indicates the number of
         Device-Watchdog-Answer messages that are transmitted to the client."
    REFERENCE
        "RFC 3588 Diameter Based Protocol,
         section 5.5.2."
    ::= { tmnxDiamPrxClStEntry 23 }

tmnxDiamPrxClStDwrTx             OBJECT-TYPE
    SYNTAX      Counter32
    MAX-ACCESS  read-only
    STATUS      obsolete
    DESCRIPTION
        "The value of tmnxDiamPrxClStDwrTx indicates the number of
         Device-Watchdog-Request messages that are transmitted to the client."
    REFERENCE
        "RFC 3588 Diameter Based Protocol,
         section 5.5.1."
    ::= { tmnxDiamPrxClStEntry 24 }

tmnxDiamPrxClStDwaRx             OBJECT-TYPE
    SYNTAX      Counter32
    MAX-ACCESS  read-only
    STATUS      obsolete
    DESCRIPTION
        "The value of tmnxDiamPrxClStDwaRx indicates the number of
         Device-Watchdog-Answer messages that are received from the client."
    REFERENCE
        "RFC 3588 Diameter Based Protocol,
         section 5.5.2."
    ::= { tmnxDiamPrxClStEntry 25 }

tmnxDiamPrxClStAsrTx             OBJECT-TYPE
    SYNTAX      Counter32
    MAX-ACCESS  read-only
    STATUS      obsolete
    DESCRIPTION
        "The value of tmnxDiamPrxClStAsrTx indicates the number of
         Abort-Session-Request messages that are transmitted to the client."
    REFERENCE
        "RFC 3588 Diameter Based Protocol,
         section 8.5.1."
    ::= { tmnxDiamPrxClStEntry 26 }

tmnxDiamPrxClStAsaRx             OBJECT-TYPE
    SYNTAX      Counter32
    MAX-ACCESS  read-only
    STATUS      obsolete
    DESCRIPTION
        "The value of tmnxDiamPrxClStAsaRx indicates the number of
         Abort-Session-Answer messages that are received from the client."
    REFERENCE
        "RFC 3588 Diameter Based Protocol,
         section 8.5.2."
    ::= { tmnxDiamPrxClStEntry 27 }

tmnxDiamPrxClStRarTx             OBJECT-TYPE
    SYNTAX      Counter32
    MAX-ACCESS  read-only
    STATUS      obsolete
    DESCRIPTION
        "The value of tmnxDiamPrxClStRarTx indicates the number of
         Re-Auth-Request messages that are transmitted to the client."
    REFERENCE
        "RFC 3588 Diameter Based Protocol,
         section 8.3.1."
    ::= { tmnxDiamPrxClStEntry 28 }

tmnxDiamPrxClStRaaRx             OBJECT-TYPE
    SYNTAX      Counter32
    MAX-ACCESS  read-only
    STATUS      obsolete
    DESCRIPTION
        "The value of tmnxDiamPrxClStRaaRx indicates the number of
         Re-Auth-Answer messages that are received from the client."
    REFERENCE
        "RFC 3588 Diameter Based Protocol,
         section 8.3.2."
    ::= { tmnxDiamPrxClStEntry 29 }

tmnxDiamPrxClStDprTx             OBJECT-TYPE
    SYNTAX      Counter32
    MAX-ACCESS  read-only
    STATUS      obsolete
    DESCRIPTION
        "The value of tmnxDiamPrxClStDprTx indicates the number of
         Disconnect-Peer-Request messages that are transmitted to the client."
    REFERENCE
        "RFC 3588 Diameter Based Protocol,
         section 5.4.1."
    ::= { tmnxDiamPrxClStEntry 30 }

tmnxDiamPrxClStDpaRx             OBJECT-TYPE
    SYNTAX      Counter32
    MAX-ACCESS  read-only
    STATUS      obsolete
    DESCRIPTION
        "The value of tmnxDiamPrxClStDpaRx indicates the number of
         Disconnect-Peer-Answer messages that are received from the client."
    REFERENCE
        "RFC 3588 Diameter Based Protocol,
         section 5.4.2."
    ::= { tmnxDiamPrxClStEntry 31 }

tmnxDiamPrxClStDprRx             OBJECT-TYPE
    SYNTAX      Counter32
    MAX-ACCESS  read-only
    STATUS      obsolete
    DESCRIPTION
        "The value of tmnxDiamPrxClStDprRx indicates the number of
         Disconnect-Peer-Request messages that are received from the client."
    REFERENCE
        "RFC 3588 Diameter Based Protocol,
         section 5.4.1."
    ::= { tmnxDiamPrxClStEntry 32 }

tmnxDiamPrxClStDpaTx             OBJECT-TYPE
    SYNTAX      Counter32
    MAX-ACCESS  read-only
    STATUS      obsolete
    DESCRIPTION
        "The value of tmnxDiamPrxClStDpaTx indicates the number of
         Disconnect-Peer-Answer messages that are transmitted to the client."
    REFERENCE
        "RFC 3588 Diameter Based Protocol,
         section 5.4.2."
    ::= { tmnxDiamPrxClStEntry 33 }

tmnxDiamPrxClStAarRx             OBJECT-TYPE
    SYNTAX      Counter32
    MAX-ACCESS  read-only
    STATUS      obsolete
    DESCRIPTION
        "The value of tmnxDiamPrxClStAarRx indicates the number of AA-Request
         messages that are received from the client."
    REFERENCE
        "RFC 7155 Diameter Network Access Server Application,
         section 3.1. AA-Request (AAR) Command"
    ::= { tmnxDiamPrxClStEntry 40 }

tmnxDiamPrxClStAaaTx             OBJECT-TYPE
    SYNTAX      Counter32
    MAX-ACCESS  read-only
    STATUS      obsolete
    DESCRIPTION
        "The value of tmnxDiamPrxClStAaaTx indicates the number of AA-Answer
         messages that are transmitted to the client."
    REFERENCE
        "RFC 7155 Diameter Network Access Server Application,
         section 3.2. AA-Answer (AAA) Command"
    ::= { tmnxDiamPrxClStEntry 41 }

tmnxDiamPeerStatsTable           OBJECT-TYPE
    SYNTAX      SEQUENCE OF TmnxDiamPeerStatsEntry
    MAX-ACCESS  not-accessible
    STATUS      current
    DESCRIPTION
        "The tmnxDiamPeerStatsTable contains statistics information about the
         peers defined in a Diameter Policy, and about the client-side peers of
         the Diameter Proxy instances."
    ::= { tmnxDiameterObjects 13 }

tmnxDiamPeerStatsEntry           OBJECT-TYPE
    SYNTAX      TmnxDiamPeerStatsEntry
    MAX-ACCESS  not-accessible
    STATUS      current
    DESCRIPTION
        "Each conceptual row represents statistics information about a Diameter
         policy peer, or a client-side peer of a Diameter proxy instance.

         Rows in this table are created and removed automatically by the
         system."
    INDEX       {
        tmnxDiamPlcyName,
        tmnxDiamPeerStatsPeerName,
        tmnxDiamPeerStatsPeerIpAddrType,
        tmnxDiamPeerStatsPeerIpAddr,
        tmnxDiamPeerStatsPeerPort,
        tmnxDiamPeerStatsDirection,
        tmnxDiamPeerStatsMessageType
    }
    ::= { tmnxDiamPeerStatsTable 1 }

TmnxDiamPeerStatsEntry           ::= SEQUENCE
{
    tmnxDiamPeerStatsPeerName        TNamedItemOrEmpty,
    tmnxDiamPeerStatsPeerIpAddrType  InetAddressType,
    tmnxDiamPeerStatsPeerIpAddr      InetAddress,
    tmnxDiamPeerStatsPeerPort        InetPortNumber,
    tmnxDiamPeerStatsDirection       INTEGER,
    tmnxDiamPeerStatsMessageType     INTEGER,
    tmnxDiamPeerStatsLastClearedTime TimeStamp,
    tmnxDiamPeerStatsTotalMessages   Counter32,
    tmnxDiamPeerStatsFailedMessages  Counter32,
    tmnxDiamPeerStatsBaseCe          Counter32,
    tmnxDiamPeerStatsBaseDp          Counter32,
    tmnxDiamPeerStatsBaseDw          Counter32,
    tmnxDiamPeerStatsNqAa            Counter32,
    tmnxDiamPeerStatsGyCcI           Counter32,
    tmnxDiamPeerStatsGyCcU           Counter32,
    tmnxDiamPeerStatsGyCcT           Counter32,
    tmnxDiamPeerStatsGyRa            Counter32,
    tmnxDiamPeerStatsGyAs            Counter32,
    tmnxDiamPeerStatsGxCcI           Counter32,
    tmnxDiamPeerStatsGxCcU           Counter32,
    tmnxDiamPeerStatsGxCcT           Counter32,
    tmnxDiamPeerStatsGxRa            Counter32,
    tmnxDiamPeerStatsGxAs            Counter32
}

tmnxDiamPeerStatsPeerName        OBJECT-TYPE
    SYNTAX      TNamedItemOrEmpty
    MAX-ACCESS  not-accessible
    STATUS      current
    DESCRIPTION
        "The value of tmnxDiamPeerStatsPeerName indicates the name of the peer
         within a DIAMETER policy, configured in object tmnxDiamPlcyPeerName."
    ::= { tmnxDiamPeerStatsEntry 1 }

tmnxDiamPeerStatsPeerIpAddrType  OBJECT-TYPE
    SYNTAX      InetAddressType
    MAX-ACCESS  not-accessible
    STATUS      current
    DESCRIPTION
        "The value of tmnxDiamPeerStatsPeerIpAddrType indicates the address
         type of tmnxDiamPeerStatsPeerIpAddr."
    ::= { tmnxDiamPeerStatsEntry 2 }

tmnxDiamPeerStatsPeerIpAddr      OBJECT-TYPE
    SYNTAX      InetAddress (SIZE (0|4|16))
    MAX-ACCESS  not-accessible
    STATUS      current
    DESCRIPTION
        "The value of tmnxDiamPeerStatsPeerIpAddr indicates the source IP
         address present in DIAMETER messages received from a client-side peer
         of a DIAMETER proxy instance."
    ::= { tmnxDiamPeerStatsEntry 3 }

tmnxDiamPeerStatsPeerPort        OBJECT-TYPE
    SYNTAX      InetPortNumber
    MAX-ACCESS  not-accessible
    STATUS      current
    DESCRIPTION
        "The value of tmnxDiamPeerStatsPeerPort indicates the TCP source port
         present in DIAMETER messages received from a client-side peer of a
         DIAMETER proxy instance."
    ::= { tmnxDiamPeerStatsEntry 4 }

tmnxDiamPeerStatsDirection       OBJECT-TYPE
    SYNTAX      INTEGER {
        rx (1),
        tx (2)
    }
    MAX-ACCESS  not-accessible
    STATUS      current
    DESCRIPTION
        "The value of tmnxDiamPeerStatsDirection indicates
         which direction packets are travelling in the system :
              rx  - Packets are being received by the system.
              tx  - Packets are being transmitted from the system."
    ::= { tmnxDiamPeerStatsEntry 5 }

tmnxDiamPeerStatsMessageType     OBJECT-TYPE
    SYNTAX      INTEGER {
        request (1),
        answer  (2)
    }
    MAX-ACCESS  not-accessible
    STATUS      current
    DESCRIPTION
        "The value of tmnxDiamPeerStatsMessageType indicates whether this
         message is a Request Message or whether this message is an Answer
         Message."
    ::= { tmnxDiamPeerStatsEntry 6 }

tmnxDiamPeerStatsLastClearedTime OBJECT-TYPE
    SYNTAX      TimeStamp
    MAX-ACCESS  read-only
    STATUS      current
    DESCRIPTION
        "The value of tmnxDiamPeerStatsLastClearedTime indicates the sysUpTime
         when the counters of this row were last reset.

         A zero value indicates that the counters have not been reset since the
         system has last been initialized."
    ::= { tmnxDiamPeerStatsEntry 7 }

tmnxDiamPeerStatsTotalMessages   OBJECT-TYPE
    SYNTAX      Counter32
    MAX-ACCESS  read-only
    STATUS      current
    DESCRIPTION
        "The value of tmnxDiamPeerStatsTotalMessages indicates the total number
         of messages."
    ::= { tmnxDiamPeerStatsEntry 10 }

tmnxDiamPeerStatsFailedMessages  OBJECT-TYPE
    SYNTAX      Counter32
    MAX-ACCESS  read-only
    STATUS      current
    DESCRIPTION
        "The value of tmnxDiamPeerStatsFailedMessages indicates the number of
         failed messages."
    ::= { tmnxDiamPeerStatsEntry 11 }

tmnxDiamPeerStatsBaseCe          OBJECT-TYPE
    SYNTAX      Counter32
    MAX-ACCESS  read-only
    STATUS      current
    DESCRIPTION
        "The value of tmnxDiamPeerStatsBaseCe indicates the number of
         Capabilities-Exchange messages."
    REFERENCE
        "RFC 3588 Diameter Based Protocol,
         section 5.3.1 and section 5.3.2."
    ::= { tmnxDiamPeerStatsEntry 20 }

tmnxDiamPeerStatsBaseDp          OBJECT-TYPE
    SYNTAX      Counter32
    MAX-ACCESS  read-only
    STATUS      current
    DESCRIPTION
        "The value of tmnxDiamPeerStatsBaseDp indicates the number of
         Disconnect-Peer messages."
    REFERENCE
        "RFC 3588 Diameter Based Protocol,
         section 5.4.1 and section 5.4.2."
    ::= { tmnxDiamPeerStatsEntry 21 }

tmnxDiamPeerStatsBaseDw          OBJECT-TYPE
    SYNTAX      Counter32
    MAX-ACCESS  read-only
    STATUS      current
    DESCRIPTION
        "The value of tmnxDiamPeerStatsBaseDw indicates the number of
         Device-Watchdog messages."
    REFERENCE
        "RFC 3588 Diameter Based Protocol,
         section 5.5.1 and section 5.5.2."
    ::= { tmnxDiamPeerStatsEntry 22 }

tmnxDiamPeerStatsNqAa            OBJECT-TYPE
    SYNTAX      Counter32
    MAX-ACCESS  read-only
    STATUS      current
    DESCRIPTION
        "The value of tmnxDiamPeerStatsNqAa indicates the number of AA
         messages."
    REFERENCE
        "RFC 7155 Diameter Network Access Server Application,
         section 3.1. AA-Request (AAR) Command and
         section 3.2. AA-Answer (AAA) Command."
    ::= { tmnxDiamPeerStatsEntry 30 }

tmnxDiamPeerStatsGyCcI           OBJECT-TYPE
    SYNTAX      Counter32
    MAX-ACCESS  read-only
    STATUS      current
    DESCRIPTION
        "The value of tmnxDiamPeerStatsGyCcI indicates the number of DIAMETER
         Gy Credit Control messages with CC-Request-Type AVP equal to
         INITIAL_REQUEST."
    REFERENCE
        "RFC 4006 Diameter Credit-Control Application,
         section 8.3 and Appendix A1."
    ::= { tmnxDiamPeerStatsEntry 40 }

tmnxDiamPeerStatsGyCcU           OBJECT-TYPE
    SYNTAX      Counter32
    MAX-ACCESS  read-only
    STATUS      current
    DESCRIPTION
        "The value of tmnxDiamPeerStatsGyCcU indicates the number of DIAMETER
         Gy Credit Control messages with CC-Request-Type AVP equal to
         UPDATE_REQUEST."
    REFERENCE
        "RFC 4006 Diameter Credit-Control Application,
         section 8.3 and Appendix A1."
    ::= { tmnxDiamPeerStatsEntry 41 }

tmnxDiamPeerStatsGyCcT           OBJECT-TYPE
    SYNTAX      Counter32
    MAX-ACCESS  read-only
    STATUS      current
    DESCRIPTION
        "The value of tmnxDiamPeerStatsGyCcT indicates the number of DIAMETER
         Gy Credit Control messages with CC-Request-Type AVP equal to
         TERMINATION_REQUEST."
    REFERENCE
        "RFC 4006 Diameter Credit-Control Application,
         section 8.3 and Appendix A1."
    ::= { tmnxDiamPeerStatsEntry 42 }

tmnxDiamPeerStatsGyRa            OBJECT-TYPE
    SYNTAX      Counter32
    MAX-ACCESS  read-only
    STATUS      current
    DESCRIPTION
        "The value of tmnxDiamPeerStatsGyRa indicates the number of DIAMETER Gy
         Re-Auth messages."
    REFERENCE
        "RFC 3588 Diameter Based Protocol,
         section 8.3.1 and section 8.3.2."
    ::= { tmnxDiamPeerStatsEntry 43 }

tmnxDiamPeerStatsGyAs            OBJECT-TYPE
    SYNTAX      Counter32
    MAX-ACCESS  read-only
    STATUS      current
    DESCRIPTION
        "The value of tmnxDiamPeerStatsGyAs indicates the number of DIAMETER Gy
         Abort-Session messages."
    REFERENCE
        "RFC 3588 Diameter Based Protocol,
         section 8.5.1 and section 8.5.2."
    ::= { tmnxDiamPeerStatsEntry 44 }

tmnxDiamPeerStatsGxCcI           OBJECT-TYPE
    SYNTAX      Counter32
    MAX-ACCESS  read-only
    STATUS      current
    DESCRIPTION
        "The value of tmnxDiamPeerStatsGxCcI indicates the number of DIAMETER
         Gx Credit Control messages with CC-Request-Type AVP equal to
         INITIAL_REQUEST."
    REFERENCE
        "RFC 4006 Diameter Credit-Control Application,
         section 8.3 and Appendix A1."
    ::= { tmnxDiamPeerStatsEntry 50 }

tmnxDiamPeerStatsGxCcU           OBJECT-TYPE
    SYNTAX      Counter32
    MAX-ACCESS  read-only
    STATUS      current
    DESCRIPTION
        "The value of tmnxDiamPeerStatsGxCcU indicates the number of DIAMETER
         Gx Credit Control messages with CC-Request-Type AVP equal to
         UPDATE_REQUEST."
    REFERENCE
        "RFC 4006 Diameter Credit-Control Application,
         section 8.3 and Appendix A1."
    ::= { tmnxDiamPeerStatsEntry 51 }

tmnxDiamPeerStatsGxCcT           OBJECT-TYPE
    SYNTAX      Counter32
    MAX-ACCESS  read-only
    STATUS      current
    DESCRIPTION
        "The value of tmnxDiamPeerStatsGxCcT indicates the number of DIAMETER
         Gx Credit Control messages with CC-Request-Type AVP equal to
         TERMINATION_REQUEST."
    REFERENCE
        "RFC 4006 Diameter Credit-Control Application,
         section 8.3 and Appendix A1."
    ::= { tmnxDiamPeerStatsEntry 52 }

tmnxDiamPeerStatsGxRa            OBJECT-TYPE
    SYNTAX      Counter32
    MAX-ACCESS  read-only
    STATUS      current
    DESCRIPTION
        "The value of tmnxDiamPeerStatsGxRa indicates the number of DIAMETER Gx
         Re-Auth messages."
    REFERENCE
        "RFC 3588 Diameter Based Protocol,
         section 8.3.1 and section 8.3.2."
    ::= { tmnxDiamPeerStatsEntry 53 }

tmnxDiamPeerStatsGxAs            OBJECT-TYPE
    SYNTAX      Counter32
    MAX-ACCESS  read-only
    STATUS      current
    DESCRIPTION
        "The value of tmnxDiamPeerStatsGxAs indicates the number of DIAMETER Gx
         Abort-Session messages."
    REFERENCE
        "RFC 3588 Diameter Based Protocol,
         section 8.5.1 and section 8.5.2."
    ::= { tmnxDiamPeerStatsEntry 54 }

tmnxDiamGyEfhTable               OBJECT-TYPE
    SYNTAX      SEQUENCE OF TmnxDiamGyEfhEntry
    MAX-ACCESS  not-accessible
    STATUS      current
    DESCRIPTION
        "The tmnxDiamGyEfhTable contains objects to configure Extended Failure
         Handling (EFH) for DIAMETER Gy sessions."
    ::= { tmnxDiameterObjects 14 }

tmnxDiamGyEfhEntry               OBJECT-TYPE
    SYNTAX      TmnxDiamGyEfhEntry
    MAX-ACCESS  not-accessible
    STATUS      current
    DESCRIPTION
        "Each conceptual row represents information about the EFH configuration
         for a DIAMETER application policy.

         Rows in this table are created and removed automatically by the system"
    AUGMENTS    { tmnxDiamApGyEntry }
    ::= { tmnxDiamGyEfhTable 1 }

TmnxDiamGyEfhEntry               ::= SEQUENCE
{
    tmnxDiamGyEfhAdminState          TmnxEnabledDisabledAdminState,
    tmnxDiamGyEfhNewSessionId        TruthValue,
    tmnxDiamGyEfhInterimCreditReport TruthValue,
    tmnxDiamGyEfhInterimCreditVolume Unsigned32,
    tmnxDiamGyEfhInterimCVolumeUnit  TmnxSubCreditVolumeUnit,
    tmnxDiamGyEfhInterimCredValTime  Unsigned32,
    tmnxDiamGyEfhInterimCMaxAttempts Unsigned32
}

tmnxDiamGyEfhAdminState          OBJECT-TYPE
    SYNTAX      TmnxEnabledDisabledAdminState
    MAX-ACCESS  read-create
    STATUS      current
    DESCRIPTION
        "The value of object tmnxDiamGyEfhAdminState specifies the
         administrative state of this EFH entry."
    DEFVAL      { disabled }
    ::= { tmnxDiamGyEfhEntry 1 }

tmnxDiamGyEfhNewSessionId        OBJECT-TYPE
    SYNTAX      TruthValue
    MAX-ACCESS  read-create
    STATUS      current
    DESCRIPTION
        "The value of object tmnxDiamGyEfhNewSessionId specifies whether a new
         session id is used for each CCR-i message for the same session."
    DEFVAL      { false }
    ::= { tmnxDiamGyEfhEntry 2 }

tmnxDiamGyEfhInterimCreditReport OBJECT-TYPE
    SYNTAX      TruthValue
    MAX-ACCESS  read-create
    STATUS      current
    DESCRIPTION
        "The value of object tmnxDiamGyEfhInterimCreditReport specifies if the
         consumed default credit is included in the Used-Service-Units reported
         to the Online Charging Server (OCS)."
    REFERENCE
        "RFC 4006 Diameter Credit-Control Application
         section 8.19. Used-Service-Unit AVP."
    DEFVAL      { false }
    ::= { tmnxDiamGyEfhEntry 3 }

tmnxDiamGyEfhInterimCreditVolume OBJECT-TYPE
    SYNTAX      Unsigned32
    MAX-ACCESS  read-create
    STATUS      current
    DESCRIPTION
        "The value of object tmnxDiamGyEfhInterimCreditVolume specifies the
         default volume credit.

         When setting the value of this object, the value of
         tmnxDiamGyEfhInterimCVolumeUnit must be set as well in the same SNMP
         SET PDU."
    DEFVAL      { 500 }
    ::= { tmnxDiamGyEfhEntry 4 }

tmnxDiamGyEfhInterimCVolumeUnit  OBJECT-TYPE
    SYNTAX      TmnxSubCreditVolumeUnit
    MAX-ACCESS  read-create
    STATUS      current
    DESCRIPTION
        "The value of object tmnxDiamGyEfhInterimCVolumeUnit specifies the unit
         in which the value of tmnxDiamGyEfhInterimCreditVolume is expressed.

         When setting the value of this object, the value of
         tmnxDiamGyEfhInterimCreditVolume must be set as well in the same SNMP
         SET PDU."
    DEFVAL      { megabytes }
    ::= { tmnxDiamGyEfhEntry 5 }

tmnxDiamGyEfhInterimCredValTime  OBJECT-TYPE
    SYNTAX      Unsigned32
    UNITS       "seconds"
    MAX-ACCESS  read-create
    STATUS      current
    DESCRIPTION
        "The value of object tmnxDiamGyEfhInterimCredValTime specifies the
         validity time of the default credit."
    REFERENCE
        "RFC 4006 Diameter Credit-Control Application
         section 8.33. Validity-Time AVP."
    DEFVAL      { 1800 }
    ::= { tmnxDiamGyEfhEntry 6 }

tmnxDiamGyEfhInterimCMaxAttempts OBJECT-TYPE
    SYNTAX      Unsigned32
    MAX-ACCESS  read-create
    STATUS      current
    DESCRIPTION
        "The value of object tmnxDiamGyEfhInterimCMaxAttempts specifies the
         number of attempts to report used credit to the OCS while in Extended
         Failure Handling mode.

         A value of zero(0) means an infinite number of retry attempts."
    DEFVAL      { 10 }
    ::= { tmnxDiamGyEfhEntry 7 }

tmnxDiamApGx3gppQosMapTable      OBJECT-TYPE
    SYNTAX      SEQUENCE OF TmnxDiamApGx3gppQosMapEntry
    MAX-ACCESS  not-accessible
    STATUS      current
    DESCRIPTION
        "The tmnxDiamApGx3gppQosMapTable contains objects to configure Gx 3GPP
         QoS Mappings."
    ::= { tmnxDiameterObjects 16 }

tmnxDiamApGx3gppQosMapEntry      OBJECT-TYPE
    SYNTAX      TmnxDiamApGx3gppQosMapEntry
    MAX-ACCESS  not-accessible
    STATUS      current
    DESCRIPTION
        "Each conceptual row represents Gx 3GPP QoS Mapping information."
    AUGMENTS    { tmnxDiamApGxEntry }
    ::= { tmnxDiamApGx3gppQosMapTable 1 }

TmnxDiamApGx3gppQosMapEntry      ::= SEQUENCE
{
    tmnxDiamApGx3gqmAADlMappingType  TmnxDiamApGx3gqmAADlMappingType,
    tmnxDiamApGx3gqmAADlArbiterName  TNamedItemOrEmpty,
    tmnxDiamApGx3gqmAADlSchedulrName TNamedItemOrEmpty,
    tmnxDiamApGx3gqmAADlPolicerId    TPolicyID,
    tmnxDiamApGx3gqmAADlQueueId      TEgressQueueId,
    tmnxDiamApGx3gqmAAUlMappingType  TmnxDiamApGx3gqmAAUlMappingType,
    tmnxDiamApGx3gqmAAUlArbiterName  TNamedItemOrEmpty,
    tmnxDiamApGx3gqmAAUlSchedulrName TNamedItemOrEmpty,
    tmnxDiamApGx3gqmAAUlPolicerId    TPolicyID,
    tmnxDiamApGx3gqmAAUlQueueId      TEgressQueueId
}

tmnxDiamApGx3gqmAADlMappingType  OBJECT-TYPE
    SYNTAX      TmnxDiamApGx3gqmAADlMappingType
    MAX-ACCESS  read-create
    STATUS      current
    DESCRIPTION
        "The QoS information in the CCA/RAR msgs is mapped to a qos-override
         object. The value of tmnxDiamApGx3gqmAADlMappingType specifies the
         kind of SR OS qos object the override applies to. For the downlink,
         this can be an aggregate rate, an arbiter, a policer, a queue or a
         scheduler. (This is used to determine the value for the APN-AMBR.)"
    DEFVAL      { noMapping }
    ::= { tmnxDiamApGx3gppQosMapEntry 1 }

tmnxDiamApGx3gqmAADlArbiterName  OBJECT-TYPE
    SYNTAX      TNamedItemOrEmpty
    MAX-ACCESS  read-create
    STATUS      current
    DESCRIPTION
        "The value of tmnxDiamApGx3gqmAADlArbiterName specifies the name of the
         arbiter used for the downlink QoS override mapping."
    DEFVAL      { "" }
    ::= { tmnxDiamApGx3gppQosMapEntry 2 }

tmnxDiamApGx3gqmAADlSchedulrName OBJECT-TYPE
    SYNTAX      TNamedItemOrEmpty
    MAX-ACCESS  read-create
    STATUS      current
    DESCRIPTION
        "The value of tmnxDiamApGx3gqmAADlSchedulrName specifies the name of
         the scheduler used for the downlink QoS override mapping."
    DEFVAL      { "" }
    ::= { tmnxDiamApGx3gppQosMapEntry 3 }

tmnxDiamApGx3gqmAADlPolicerId    OBJECT-TYPE
    SYNTAX      TPolicyID
    MAX-ACCESS  read-create
    STATUS      current
    DESCRIPTION
        "The value of tmnxDiamApGx3gqmAADlPolicerId specifies the id of the
         policer used for the downlink QoS override mapping."
    DEFVAL      { 0 }
    ::= { tmnxDiamApGx3gppQosMapEntry 4 }

tmnxDiamApGx3gqmAADlQueueId      OBJECT-TYPE
    SYNTAX      TEgressQueueId
    MAX-ACCESS  read-create
    STATUS      current
    DESCRIPTION
        "The value of tmnxDiamApGx3gqmAADlQueueId specifies the id of the queue
         used for the downlink QoS override mapping."
    DEFVAL      { 0 }
    ::= { tmnxDiamApGx3gppQosMapEntry 5 }

tmnxDiamApGx3gqmAAUlMappingType  OBJECT-TYPE
    SYNTAX      TmnxDiamApGx3gqmAAUlMappingType
    MAX-ACCESS  read-create
    STATUS      current
    DESCRIPTION
        "The QoS information in the CCA/RAR msgs is mapped to a qos-override
         object. The value of tmnxDiamApGx3gqmAAUlMappingType specifies the
         kind of SR OS qos object the override applies to. For the uplink, this
         can be an arbiter, a policer, a queue or a scheduler. (This is used to
         determine the value for the APN-AMBR.)"
    DEFVAL      { noMapping }
    ::= { tmnxDiamApGx3gppQosMapEntry 6 }

tmnxDiamApGx3gqmAAUlArbiterName  OBJECT-TYPE
    SYNTAX      TNamedItemOrEmpty
    MAX-ACCESS  read-create
    STATUS      current
    DESCRIPTION
        "The value of tmnxDiamApGx3gqmAAUlArbiterName specifies the name of the
         arbiter used for the uplink QoS override mapping."
    DEFVAL      { "" }
    ::= { tmnxDiamApGx3gppQosMapEntry 7 }

tmnxDiamApGx3gqmAAUlSchedulrName OBJECT-TYPE
    SYNTAX      TNamedItemOrEmpty
    MAX-ACCESS  read-create
    STATUS      current
    DESCRIPTION
        "The value of tmnxDiamApGx3gqmAAUlSchedulrName specifies the name of
         the scheduler used for the uplink QoS override mapping."
    DEFVAL      { "" }
    ::= { tmnxDiamApGx3gppQosMapEntry 8 }

tmnxDiamApGx3gqmAAUlPolicerId    OBJECT-TYPE
    SYNTAX      TPolicyID
    MAX-ACCESS  read-create
    STATUS      current
    DESCRIPTION
        "The value of tmnxDiamApGx3gqmAAUlPolicerId specifies the id of the
         policer used for the uplink QoS override mapping."
    DEFVAL      { 0 }
    ::= { tmnxDiamApGx3gppQosMapEntry 9 }

tmnxDiamApGx3gqmAAUlQueueId      OBJECT-TYPE
    SYNTAX      TEgressQueueId
    MAX-ACCESS  read-create
    STATUS      current
    DESCRIPTION
        "The value of tmnxDiamApGx3gqmAAUlQueueId specifies  the id
         of the queue used for the uplink QoS override mapping."
    DEFVAL      { 0 }
    ::= { tmnxDiamApGx3gppQosMapEntry 10 }

tmnxDiameterSessionObjects       OBJECT IDENTIFIER ::= { tmnxDiameter 4 }

tmnxDiamSeGxCcrtReplayTable      OBJECT-TYPE
    SYNTAX      SEQUENCE OF TmnxDiamSeGxCcrtReplayEntry
    MAX-ACCESS  not-accessible
    STATUS      current
    DESCRIPTION
        "The tmnxDiamSeGxCcrtReplayTable contains information about DIAMETER Gx
         sessions that are in Credit-Control-Request Session-Terminate-Request
         (CCR-T) replay mode."
    ::= { tmnxDiameterSessionObjects 1 }

tmnxDiamSeGxCcrtReplayEntry      OBJECT-TYPE
    SYNTAX      TmnxDiamSeGxCcrtReplayEntry
    MAX-ACCESS  not-accessible
    STATUS      current
    DESCRIPTION
        "Each conceptual row represents statistics information about a DIAMETER
         Gx session that is in CCR-T replay mode.

         Rows in this table are created and removed automatically by the
         system."
    INDEX       { tmnxDiamSeGxCcrtReplayIndex }
    ::= { tmnxDiamSeGxCcrtReplayTable 1 }

TmnxDiamSeGxCcrtReplayEntry      ::= SEQUENCE
{
    tmnxDiamSeGxCcrtReplayIndex      Unsigned32,
    tmnxDiamSeGxCcrtReplaySessionId  TmnxDiamSessionId,
    tmnxDiamSeGxCcrtReplayAppPolicy  TNamedItem,
    tmnxDiamSeGxCcrtReplayExpiryTime Unsigned32
}

tmnxDiamSeGxCcrtReplayIndex      OBJECT-TYPE
    SYNTAX      Unsigned32
    MAX-ACCESS  not-accessible
    STATUS      current
    DESCRIPTION
        "The value of tmnxDiamSeGxCcrtReplayIndex indicates the index of this
         entry."
    ::= { tmnxDiamSeGxCcrtReplayEntry 1 }

tmnxDiamSeGxCcrtReplaySessionId  OBJECT-TYPE
    SYNTAX      TmnxDiamSessionId
    MAX-ACCESS  read-only
    STATUS      current
    DESCRIPTION
        "The value of tmnxDiamSeGxCcrtReplaySessionId indicates the DIAMETER
         session id."
    ::= { tmnxDiamSeGxCcrtReplayEntry 2 }

tmnxDiamSeGxCcrtReplayAppPolicy  OBJECT-TYPE
    SYNTAX      TNamedItem
    MAX-ACCESS  read-only
    STATUS      current
    DESCRIPTION
        "The value of tmnxDiamSeGxCcrtReplayAppPolicy indicates the DIAMETER
         application policy name."
    ::= { tmnxDiamSeGxCcrtReplayEntry 3 }

tmnxDiamSeGxCcrtReplayExpiryTime OBJECT-TYPE
    SYNTAX      Unsigned32
    UNITS       "seconds"
    MAX-ACCESS  read-only
    STATUS      current
    DESCRIPTION
        "The value of tmnxDiamSeGxCcrtReplayExpiryTime indicates the time left
         before stopping to send CCR-T messages for this session."
    ::= { tmnxDiamSeGxCcrtReplayEntry 4 }

tmnxDiameterNotificationObjs     OBJECT IDENTIFIER ::= { tmnxDiameter 100 }

tmnxDiamAppPlcyName              OBJECT-TYPE
    SYNTAX      TNamedItem
    MAX-ACCESS  accessible-for-notify
    STATUS      current
    DESCRIPTION
        "The value of tmnxDiamAppPlcyName specifies the name of the DIAMETER
         policy."
    ::= { tmnxDiameterNotificationObjs 1 }

tmnxDiamAppPeerName              OBJECT-TYPE
    SYNTAX      TNamedItem
    MAX-ACCESS  accessible-for-notify
    STATUS      current
    DESCRIPTION
        "The value of tmnxDiamAppPeerName specifies the name of the peer within
         a DIAMETER policy."
    ::= { tmnxDiameterNotificationObjs 2 }

tmnxDiamAppTrapDescription       OBJECT-TYPE
    SYNTAX      TItemDescription
    MAX-ACCESS  accessible-for-notify
    STATUS      current
    DESCRIPTION
        "The value of tmnxDiamAppTrapDescription specifies the diameter
         application provided description of the failure for this trap."
    ::= { tmnxDiameterNotificationObjs 3 }

tmnxDiamAppSessionId             OBJECT-TYPE
    SYNTAX      TmnxDiamSessionId
    MAX-ACCESS  accessible-for-notify
    STATUS      current
    DESCRIPTION
        "The value of tmnxDiamAppSessionId specifies the diameter session id
         for this trap."
    ::= { tmnxDiameterNotificationObjs 4 }

tmnxDiamAppSubscrId              OBJECT-TYPE
    SYNTAX      DisplayString (SIZE (1..32))
    MAX-ACCESS  accessible-for-notify
    STATUS      current
    DESCRIPTION
        "The value of tmnxDiamAppSubscrId specifies the subscriber
         identification for this trap."
    ::= { tmnxDiameterNotificationObjs 5 }

tmnxDiamAppSapId                 OBJECT-TYPE
    SYNTAX      DisplayString (SIZE (1..32))
    MAX-ACCESS  accessible-for-notify
    STATUS      current
    DESCRIPTION
        "The value of tmnxDiamAppSapId specifies the SAP identification for
         this trap."
    ::= { tmnxDiameterNotificationObjs 6 }

tmnxDiamAppSLAProfName           OBJECT-TYPE
    SYNTAX      TNamedItem
    MAX-ACCESS  accessible-for-notify
    STATUS      current
    DESCRIPTION
        "The value of tmnxDiamAppSLAProfName specifies the SLA profile name for
         this trap."
    ::= { tmnxDiameterNotificationObjs 7 }

tmnxDiamNotifyEventId            OBJECT-TYPE
    SYNTAX      INTEGER {
        unknownApplicationPolicy   (1),
        unknownPeerPolicy          (2),
        noOperationalPeers         (3),
        txError                    (4),
        rxError                    (5),
        txTimeout                  (6),
        txTimeoutPendingQ          (7),
        txRetriesExceeded          (8),
        ccrtReplayLifetimeExceeded (9),
        ccrtReplayTooManySessions  (10)
    }
    MAX-ACCESS  accessible-for-notify
    STATUS      current
    DESCRIPTION
        "The value of tmnxDiamNotifyEventId corresponds to a type of event."
    ::= { tmnxDiameterNotificationObjs 8 }

tmnxDiameterConformance          OBJECT IDENTIFIER ::= { tmnxSRConfs 58 }

tmnxDiameterCompliances          OBJECT IDENTIFIER ::= { tmnxDiameterConformance 1 }

tmnxDiameterV8v0MIBCompliance    MODULE-COMPLIANCE
    STATUS      obsolete
    DESCRIPTION
        "The compliance statement for TIMETRA-DIAMETER-MIB on Nokia SROS and
         7710 series systems release R8.0."
    MODULE
        MANDATORY-GROUPS {
            tmnxDiameterBaseV8v0Group,
            tmnxDiameterDccaGroup,
            tmnxDiameterNotifyV8v0Group
        }
    ::= { tmnxDiameterCompliances 1 }

tmnxDiameterV10v0MIBCompliance   MODULE-COMPLIANCE
    STATUS      obsolete
    DESCRIPTION
        "The compliance statement for TIMETRA-DIAMETER-MIB on Nokia SROS and
         7710 series systems release R10.0."
    MODULE
        MANDATORY-GROUPS {
            tmnxDiameterBaseV8v0Group,
            tmnxDiameterDccaGroup,
            tmnxDiameterNotifyV10v0Group,
            tmnxDiameterDccaGxGroup,
            tmnxDiameterDccaV10v0Group
        }
    ::= { tmnxDiameterCompliances 2 }

tmnxDiameterV12v0Compliance      MODULE-COMPLIANCE
    STATUS      obsolete
    DESCRIPTION
        "The compliance statement for TIMETRA-DIAMETER-MIB release R12.0 Nokia
         SROS series systems."
    MODULE
        MANDATORY-GROUPS {
            tmnxDiameterBaseV8v0Group,
            tmnxDiameterNotifyV10v0Group,
            tmnxDiameterV12v0Group
        }
    ::= { tmnxDiameterCompliances 3 }

tmnxDiameterV13v0Compliance      MODULE-COMPLIANCE
    STATUS      obsolete
    DESCRIPTION
        "The compliance statement for TIMETRA-DIAMETER-MIB release R13.0 Nokia
         SROS series systems."
    MODULE
        MANDATORY-GROUPS {
            tmnxDiameterBaseV8v0Group,
            tmnxDiameterNotifyV13v0Group,
            tmnxDiameterV12v0Group,
            tmnxDiameterV13v0Group,
            tmnxDiameterNasreqGroup,
            tmnxDiameterProxyGroup
        }
    ::= { tmnxDiameterCompliances 4 }

tmnxDiameterV14v0Compliance      MODULE-COMPLIANCE
    STATUS      obsolete
    DESCRIPTION
        "The compliance statement for TIMETRA-DIAMETER-MIB release R14.0 Nokia
         SROS series systems."
    MODULE
        MANDATORY-GROUPS {
            tmnxDiameterBaseV14v0Group,
            tmnxDiameterNotifyV14v0Group,
            tmnxDiameterV12v0Group,
            tmnxDiameterV13v0Group,
            tmnxDiameterNasreqV14v0Group,
            tmnxDiameterProxyV14v0Group,
            tmnxDiameterV14v0Group,
            tmnxDiameterGyEfhGroup,
            tmnxDiameterPeerStatsGroup
        }
    ::= { tmnxDiameterCompliances 5 }

tmnxDiameterV15v0Compliance      MODULE-COMPLIANCE
    STATUS      current
    DESCRIPTION
        "The compliance statement for TIMETRA-DIAMETER-MIB release R15.0 Nokia
         SROS series systems."
    MODULE
        MANDATORY-GROUPS {
            tmnxDiameterBaseV14v0Group,
            tmnxDiameterNotifyV14v0Group,
            tmnxDiameterV12v0Group,
            tmnxDiameterV13v0Group,
            tmnxDiameterNasreqV14v0Group,
            tmnxDiameterProxyV14v0Group,
            tmnxDiameterV14v0Group,
            tmnxDiameterV15v0Group,
            tmnxDiameterGyEfhGroup,
            tmnxDiameterPeerStatsGroup
        }
    ::= { tmnxDiameterCompliances 6 }

tmnxDiameterGroups               OBJECT IDENTIFIER ::= { tmnxDiameterConformance 2 }

tmnxDiameterBaseV7v0Group        OBJECT-GROUP
    OBJECTS     {
        tmnxDiameterPlcyTableLastChngd,
        tmnxDiamPlcyRowStatus,
        tmnxDiamPlcyLastMgmtChange,
        tmnxDiamPlcyDescription,
        tmnxDiamPlcyOriginHost,
        tmnxDiamPlcyOriginRealm,
        tmnxDiamPlcyRouter,
        tmnxDiamPlcySourceAddrType,
        tmnxDiamPlcySourceAddr,
        tmnxDiamPlcyWatchdogTimer,
        tmnxDiamPlcyConnectionTimer,
        tmnxDiamPlcyTransactionTimer,
        tmnxDiamPlcyPeerTableLastChngd,
        tmnxDiamPlcyPeerRowStatus,
        tmnxDiamPlcyPeerLastMgmtChange,
        tmnxDiamPlcyPeerAdminState,
        tmnxDiamPlcyPeerAddrType,
        tmnxDiamPlcyPeerAddr,
        tmnxDiamPlcyPeerTransportProt,
        tmnxDiamPlcyPeerTransportPort,
        tmnxDiamPlcyPeerDestHost,
        tmnxDiamPlcyPeerDestRealm,
        tmnxDiamPlcyPeerWatchdogTimer,
        tmnxDiamPlcyPeerConnectionTimer,
        tmnxDiamPlcyPeerTransactTimer,
        tmnxDiamPlcyPeerPreference
    }
    STATUS      obsolete
    DESCRIPTION
        "The group of objects supporting DIAMETER on Nokia SROS series systems
         7.0 release."
    ::= { tmnxDiameterGroups 1 }

tmnxDiameterDccaGroup            OBJECT-GROUP
    OBJECTS     {
        tmnxDiamPlcyDccaTableLastChngd,
        tmnxDiamPlcyDccaLastMgmtChange,
        tmnxDiamPlcyDccaFailover,
        tmnxDiamPlcyDccaFailureHndlng,
        tmnxDiamPlcyDccaTxTimer,
        tmnxDiamPlcyDccaAvpServCntxtId,
        tmnxDiamPlcyDccaAvpCldStationId,
        tmnxDiamPlcyDccaAvpRadiusUsrNme,
        tmnxDiamPlcyDccaAvpSubIdOrg,
        tmnxDiamPlcyDccaAvpSubIdType
    }
    STATUS      obsolete
    DESCRIPTION
        "The group of objects supporting DIAMETER DCCA on Nokia SROS series
         systems."
    ::= { tmnxDiameterGroups 2 }

tmnxDiameterBaseV8v0Group        OBJECT-GROUP
    OBJECTS     {
        tmnxDiameterPlcyTableLastChngd,
        tmnxDiamPlcyRowStatus,
        tmnxDiamPlcyLastMgmtChange,
        tmnxDiamPlcyDescription,
        tmnxDiamPlcyOriginHost,
        tmnxDiamPlcyOriginRealm,
        tmnxDiamPlcyRouter,
        tmnxDiamPlcySourceAddrType,
        tmnxDiamPlcySourceAddr,
        tmnxDiamPlcyWatchdogTimer,
        tmnxDiamPlcyConnectionTimer,
        tmnxDiamPlcyTransactionTimer,
        tmnxDiamPlcyPeerTableLastChngd,
        tmnxDiamPlcyPeerRowStatus,
        tmnxDiamPlcyPeerLastMgmtChange,
        tmnxDiamPlcyPeerAdminState,
        tmnxDiamPlcyPeerAddrType,
        tmnxDiamPlcyPeerAddr,
        tmnxDiamPlcyPeerTransportProt,
        tmnxDiamPlcyPeerTransportPort,
        tmnxDiamPlcyPeerDestHost,
        tmnxDiamPlcyPeerDestRealm,
        tmnxDiamPlcyPeerWatchdogTimer,
        tmnxDiamPlcyPeerConnectionTimer,
        tmnxDiamPlcyPeerTransactTimer,
        tmnxDiamPlcyPeerPreference,
        tmnxDiamPeerPsmState,
        tmnxDiamPeerConnectionSuspended,
        tmnxDiamPeerCooldownSeqStage,
        tmnxDiamPeerOrder,
        tmnxDiamPeerPrimarySecondary,
        tmnxDiamPeerTcTimerTimeLeft,
        tmnxDiamPeerTtTimerTimeLeft,
        tmnxDiamPeerTwTimerTimeLeft,
        tmnxDiamPeerWatchdogAlgActive,
        tmnxDiamPeerWatchdogAnswPending,
        tmnxDiamPeerCooldownSeqPending,
        tmnxDiamPeerCooldownSeqActive,
        tmnxDiamPeerPeerRemovalPending,
        tmnxDiamPeerStatsLastClearTime,
        tmnxDiamPeerStCiTcpSendFailed,
        tmnxDiamPeerStCiDiamRxDropCnt,
        tmnxDiamPeerStCiDiamTxReqs,
        tmnxDiamPeerStCiDiamRxResps,
        tmnxDiamPeerStCiPendMsgsPMQ,
        tmnxDiamPeerStCiReqTimeoutsPMQ,
        tmnxDiamPeerStSiTcpSendFailed,
        tmnxDiamPeerStSiDiamRxDropCnt,
        tmnxDiamPeerStSiDiamRxReqs,
        tmnxDiamPeerStSiDiamTxResps,
        tmnxDiamPeerStErrHdlDiamTxErrCnt,
        tmnxDiamPeerStErrHdlDiamRxErrCnt,
        tmnxDiamPeerStCcrInitialTx,
        tmnxDiamPeerStCcaInitialRx,
        tmnxDiamPeerStCcrUpdateTx,
        tmnxDiamPeerStCcaUpdateRx,
        tmnxDiamPeerStCcrTerminateTx,
        tmnxDiamPeerStCcaTerminateRx,
        tmnxDiamPeerStCerTx,
        tmnxDiamPeerStCeaRx,
        tmnxDiamPeerStWdrTx,
        tmnxDiamPeerStWdaRx,
        tmnxDiamPeerStWdrRx,
        tmnxDiamPeerStWdaTx,
        tmnxDiamPeerStAsrRx,
        tmnxDiamPeerStAsaTx,
        tmnxDiamPeerStRarRx,
        tmnxDiamPeerStRaaTx,
        tmnxDiamPeerStDprTx,
        tmnxDiamPeerStDpaRx,
        tmnxDiamPeerStDprRx,
        tmnxDiamPeerStDpaTx
    }
    STATUS      obsolete
    DESCRIPTION
        "The group of objects supporting DIAMETER on Nokia SROS series systems
         8.0 release."
    ::= { tmnxDiameterGroups 3 }

tmnxDiameterNotifyV8v0Group      NOTIFICATION-GROUP
    NOTIFICATIONS {
        tmnxDiamPolicyPeerStateChange,
        tmnxDiamAppMessageDropped
    }
    STATUS      obsolete
    DESCRIPTION
        "The group of notifications supporting DIAMETER on Nokia SROS series
         systems 8.0 release."
    ::= { tmnxDiameterGroups 4 }

tmnxDiameterV8v0NotifyObjsGroup  OBJECT-GROUP
    OBJECTS     {
        tmnxDiamAppPlcyName,
        tmnxDiamAppPeerName,
        tmnxDiamAppTrapDescription
    }
    STATUS      obsolete
    DESCRIPTION
        "The group of objects supporting management of DIAMETER notification
         objects on Nokia SROS series systems 8.0 release."
    ::= { tmnxDiameterGroups 5 }

tmnxDiameterDccaGxGroup          OBJECT-GROUP
    OBJECTS     {
        tmnxDiamPlcyDccaAvpNasP,
        tmnxDiamPlcyDccaAvpNasPPfixType,
        tmnxDiamPlcyDccaAvpNasPPfixStr,
        tmnxDiamPlcyDccaAvpNasPSfixType,
        tmnxDiamPlcyDccaAvpNasPType,
        tmnxDiamPlcyDccaApplicationType,
        tmnxDiamPlcyDccaAvpImsiOrg,
        tmnxDiamPlcyDccaMaxPendingReq,
        tmnxDiamPlcyDccaTxRetryLimit
    }
    STATUS      obsolete
    DESCRIPTION
        "The group of objects supporting DIAMETER DCCA Gx Interface on Nokia
         SROS series systems."
    ::= { tmnxDiameterGroups 6 }

tmnxDiameterDccaV10v0Group       OBJECT-GROUP
    OBJECTS     {
        tmnxDiamPlcyVendorSupport,
        tmnxDiamPlcyDccaOutOfCreditRep
    }
    STATUS      obsolete
    DESCRIPTION
        "The group of objects supporting DIAMETER vendor type on Nokia SROS
         series systems."
    ::= { tmnxDiameterGroups 7 }

tmnxDiameterNotifyV10v0Group     NOTIFICATION-GROUP
    NOTIFICATIONS {
        tmnxDiamPolicyPeerStateChange,
        tmnxDiamAppMessageDropped,
        tmnxDiamAppSessionFailure
    }
    STATUS      obsolete
    DESCRIPTION
        "The group of notifications supporting DIAMETER on Nokia SROS series
         systems 10.0 release."
    ::= { tmnxDiameterGroups 8 }

tmnxDiameterV10v0NotifyObjsGroup OBJECT-GROUP
    OBJECTS     {
        tmnxDiamAppPlcyName,
        tmnxDiamAppPeerName,
        tmnxDiamAppTrapDescription,
        tmnxDiamAppSessionId,
        tmnxDiamAppSubscrId,
        tmnxDiamAppSapId,
        tmnxDiamAppSLAProfName
    }
    STATUS      obsolete
    DESCRIPTION
        "The group of objects supporting management of DIAMETER notification
         objects on Nokia SROS series systems 10.0 release."
    ::= { tmnxDiameterGroups 9 }

tmnxDiameterV12v0Group           OBJECT-GROUP
    OBJECTS     {
        tmnxDiamPlcyVendorSupport,
        tmnxDiamPlcyApplications,
        tmnxDiamAppPlcyTableLastCh,
        tmnxDiamAppPlcyRowStatus,
        tmnxDiamAppPlcyLastMgmtChange,
        tmnxDiamAppPlcyFailover,
        tmnxDiamAppPlcyFailureHndlng,
        tmnxDiamAppPlcyPeerPlcy,
        tmnxDiamAppPlcyApplication,
        tmnxDiamAppPlcyTxTimer,
        tmnxDiamAppPlcyDescription,
        tmnxDiamApGyTableLastCh,
        tmnxDiamApGyLastMgmtChange,
        tmnxDiamApGyAvpServCntxtId,
        tmnxDiamApGyAvpCldStationId,
        tmnxDiamApGyAvpRadiusUsrNme,
        tmnxDiamApGyAvpImsiOrg,
        tmnxDiamApGyOutOfCreditRep,
        tmnxDiamApGyVendorSupport,
        tmnxDiamApGySubIdOrg,
        tmnxDiamApGySubIdType,
        tmnxDiamApGxTableLastCh,
        tmnxDiamApGxLastMgmtChange,
        tmnxDiamApGxAvp,
        tmnxDiamApGxAvpClngStationIdType,
        tmnxDiamApGxAvpNasPortBitspec,
        tmnxDiamApGxAvpNasPortIdPfixType,
        tmnxDiamApGxAvpNasPortIdPfixStr,
        tmnxDiamApGxAvpNasPortIdSfixType,
        tmnxDiamApGxAvpNasPortTypeValue,
        tmnxDiamApGxAvpUeInfoType,
        tmnxDiamApGxSubIdOrg,
        tmnxDiamApGxSubIdType,
        tmnxDiamApGxMacFormat,
        tmnxDiamApGxReportIpAddrEvent,
        tmnxDiamPlcyPythonPolicy
    }
    STATUS      current
    DESCRIPTION
        "The group of objects supporting DIAMETER that were added in release
         12.0 of the Nokia SROS series systems."
    ::= { tmnxDiameterGroups 10 }

tmnxDiameterNasreqGroup          OBJECT-GROUP
    OBJECTS     {
        tmnxDiamPeerStAarTx,
        tmnxDiamPeerStAaaRx,
        tmnxDiamApNqTableLastCh,
        tmnxDiamApNqLastMgmtChange,
        tmnxDiamApNqAvp,
        tmnxDiamApNqAvpClngStationIdType,
        tmnxDiamApNqAvpNasPortBitspec,
        tmnxDiamApNqAvpNasPortIdPfixType,
        tmnxDiamApNqAvpNasPortIdPfixStr,
        tmnxDiamApNqAvpNasPortIdSfixType,
        tmnxDiamApNqAvpNasPortIdSfixStr,
        tmnxDiamApNqAvpNasPortTypeType,
        tmnxDiamApNqAvpNasPortTypeValue,
        tmnxDiamApNqPassword,
        tmnxDiamApNqUserNameFormat,
        tmnxDiamApNqUserNameOp,
        tmnxDiamApNqDomain,
        tmnxDiamApNqMacFormat
    }
    STATUS      obsolete
    DESCRIPTION
        "The group of objects supporting DIAMETER NASREQ for the Nokia SROS
         series systems."
    ::= { tmnxDiameterGroups 11 }

tmnxDiameterProxyGroup           OBJECT-GROUP
    OBJECTS     {
        tmnxDiamPlcyRole,
        tmnxDiamPpPrxLastMgmtChange,
        tmnxDiamPpPrxAdminState,
        tmnxDiamPpPrxRouter,
        tmnxDiamPpPrxAddrType,
        tmnxDiamPpPrxAddr,
        tmnxDiamPpPrxOperState,
        tmnxDiamPpPrxMcLocState,
        tmnxDiamPpPrxMcLocOriginStateId,
        tmnxDiamPpPrxMcLocMacAddress,
        tmnxDiamPpPrxMcLocCtrlMacAddress,
        tmnxDiamPpPrxMcRemState,
        tmnxDiamPpPrxMcRemOriginStateId,
        tmnxDiamPpPrxMcRemMacAddress,
        tmnxDiamPpPrxMcRemCtrlMacAddress,
        tmnxDiamPpPrxClientPsmState,
        tmnxDiamPrxClStLastClearedTime,
        tmnxDiamPrxClStCiTcpSendFailed,
        tmnxDiamPrxClStCiDiamRxDropCnt,
        tmnxDiamPrxClStCiDiamRxReqs,
        tmnxDiamPrxClStCiDiamTxResps,
        tmnxDiamPrxClStCiPendMsgsPmq,
        tmnxDiamPrxClStCiReqTimeoutsPmq,
        tmnxDiamPrxClStSiTcpSendFailed,
        tmnxDiamPrxClStSiDiamRxDropCnt,
        tmnxDiamPrxClStSiDiamTxReqs,
        tmnxDiamPrxClStSiDiamRxResps,
        tmnxDiamPrxClStCcrInitialRx,
        tmnxDiamPrxClStCcaInitialTx,
        tmnxDiamPrxClStCcrUpdateRx,
        tmnxDiamPrxClStCcaUpdateTx,
        tmnxDiamPrxClStCcrTerminateRx,
        tmnxDiamPrxClStCcaTerminateTx,
        tmnxDiamPrxClStCerRx,
        tmnxDiamPrxClStCeaTx,
        tmnxDiamPrxClStDwrRx,
        tmnxDiamPrxClStDwaTx,
        tmnxDiamPrxClStDwrTx,
        tmnxDiamPrxClStDwaRx,
        tmnxDiamPrxClStAsrTx,
        tmnxDiamPrxClStAsaRx,
        tmnxDiamPrxClStRarTx,
        tmnxDiamPrxClStRaaRx,
        tmnxDiamPrxClStDprTx,
        tmnxDiamPrxClStDpaRx,
        tmnxDiamPrxClStDprRx,
        tmnxDiamPrxClStDpaTx,
        tmnxDiamPrxClStAarRx,
        tmnxDiamPrxClStAaaTx,
        tmnxDiamPpPrxTableLastCh,
        tmnxDiamApGxAvpNasPortIdSfixStr
    }
    STATUS      obsolete
    DESCRIPTION
        "The group of objects supporting DIAMETER Proxy for the Nokia SROS
         series systems."
    ::= { tmnxDiameterGroups 12 }

tmnxDiameterNotifyV13v0Group     NOTIFICATION-GROUP
    NOTIFICATIONS {
        tmnxDiamPolicyPeerStateChange,
        tmnxDiamAppMessageDropped,
        tmnxDiamAppSessionFailure,
        tmnxDiamSessionEvent,
        tmnxDiamPpPrxMcLocStateChanged,
        tmnxDiamPrxMessageDropped
    }
    STATUS      obsolete
    DESCRIPTION
        "The group of notifications supporting DIAMETER on Nokia SROS series
         systems 13.0 release."
    ::= { tmnxDiameterGroups 13 }

tmnxDiameterV13v0NotifyObjsGroup OBJECT-GROUP
    OBJECTS     {
        tmnxDiamAppPlcyName,
        tmnxDiamAppPeerName,
        tmnxDiamAppTrapDescription,
        tmnxDiamAppSessionId,
        tmnxDiamAppSubscrId,
        tmnxDiamAppSapId,
        tmnxDiamAppSLAProfName,
        tmnxDiamNotifyEventId
    }
    STATUS      current
    DESCRIPTION
        "The group of objects supporting management of DIAMETER notification
         objects on Nokia SROS series systems 13.0 release."
    ::= { tmnxDiameterGroups 14 }

tmnxDiameterV13v0Group           OBJECT-GROUP
    OBJECTS     {
        tmnxDiamApGxCcrtReplayInterval,
        tmnxDiamSeGxCcrtReplaySessionId,
        tmnxDiamSeGxCcrtReplayAppPolicy,
        tmnxDiamSeGxCcrtReplayExpiryTime
    }
    STATUS      current
    DESCRIPTION
        "The group of objects supporting DIAMETER that were added in release
         13.0 of the Nokia SROS series systems."
    ::= { tmnxDiameterGroups 15 }

tmnxDiameterV14v0Group           OBJECT-GROUP
    OBJECTS     {
        tmnxDiamPlcyV6SourceAddrType,
        tmnxDiamPlcyV6SourceAddr,
        tmnxDiamApGyInc3GppGgsnAddr,
        tmnxDiamApGyInc3GppGgsnIPv6Addr
    }
    STATUS      current
    DESCRIPTION
        "The group of objects supporting DIAMETER that were added in release
         14.0 of the Nokia SROS series systems."
    ::= { tmnxDiameterGroups 16 }

tmnxDiameterPeerStatsGroup       OBJECT-GROUP
    OBJECTS     {
        tmnxDiamPeerStatsLastClearedTime,
        tmnxDiamPeerStatsTotalMessages,
        tmnxDiamPeerStatsFailedMessages,
        tmnxDiamPeerStatsBaseCe,
        tmnxDiamPeerStatsBaseDp,
        tmnxDiamPeerStatsBaseDw,
        tmnxDiamPeerStatsNqAa,
        tmnxDiamPeerStatsGyCcI,
        tmnxDiamPeerStatsGyCcU,
        tmnxDiamPeerStatsGyCcT,
        tmnxDiamPeerStatsGyRa,
        tmnxDiamPeerStatsGyAs,
        tmnxDiamPeerStatsGxCcI,
        tmnxDiamPeerStatsGxCcU,
        tmnxDiamPeerStatsGxCcT,
        tmnxDiamPeerStatsGxRa,
        tmnxDiamPeerStatsGxAs
    }
    STATUS      current
    DESCRIPTION
        "The group of objects supporting DIAMETER Peer statistics for the Nokia
         SROS series systems."
    ::= { tmnxDiameterGroups 17 }

tmnxDiameterBaseV14v0Group       OBJECT-GROUP
    OBJECTS     {
        tmnxDiameterPlcyTableLastChngd,
        tmnxDiamPlcyRowStatus,
        tmnxDiamPlcyLastMgmtChange,
        tmnxDiamPlcyDescription,
        tmnxDiamPlcyOriginHost,
        tmnxDiamPlcyOriginRealm,
        tmnxDiamPlcyRouter,
        tmnxDiamPlcySourceAddrType,
        tmnxDiamPlcySourceAddr,
        tmnxDiamPlcyWatchdogTimer,
        tmnxDiamPlcyConnectionTimer,
        tmnxDiamPlcyTransactionTimer,
        tmnxDiamPlcyPeerTableLastChngd,
        tmnxDiamPlcyPeerRowStatus,
        tmnxDiamPlcyPeerLastMgmtChange,
        tmnxDiamPlcyPeerAdminState,
        tmnxDiamPlcyPeerAddrType,
        tmnxDiamPlcyPeerAddr,
        tmnxDiamPlcyPeerTransportProt,
        tmnxDiamPlcyPeerTransportPort,
        tmnxDiamPlcyPeerDestHost,
        tmnxDiamPlcyPeerDestRealm,
        tmnxDiamPlcyPeerWatchdogTimer,
        tmnxDiamPlcyPeerConnectionTimer,
        tmnxDiamPlcyPeerTransactTimer,
        tmnxDiamPlcyPeerPreference,
        tmnxDiamPeerPsmState,
        tmnxDiamPeerConnectionSuspended,
        tmnxDiamPeerCooldownSeqStage,
        tmnxDiamPeerOrder,
        tmnxDiamPeerPrimarySecondary,
        tmnxDiamPeerTcTimerTimeLeft,
        tmnxDiamPeerTtTimerTimeLeft,
        tmnxDiamPeerTwTimerTimeLeft,
        tmnxDiamPeerWatchdogAlgActive,
        tmnxDiamPeerWatchdogAnswPending,
        tmnxDiamPeerCooldownSeqPending,
        tmnxDiamPeerCooldownSeqActive,
        tmnxDiamPeerPeerRemovalPending,
        tmnxDiamPeerPendingMsgsPMQ
    }
    STATUS      current
    DESCRIPTION
        "The group of objects supporting DIAMETER on Nokia SROS series systems."
    ::= { tmnxDiameterGroups 18 }

tmnxDiameterNasreqV14v0Group     OBJECT-GROUP
    OBJECTS     {
        tmnxDiamApNqTableLastCh,
        tmnxDiamApNqLastMgmtChange,
        tmnxDiamApNqAvp,
        tmnxDiamApNqAvpClngStationIdType,
        tmnxDiamApNqAvpNasPortBitspec,
        tmnxDiamApNqAvpNasPortIdPfixType,
        tmnxDiamApNqAvpNasPortIdPfixStr,
        tmnxDiamApNqAvpNasPortIdSfixType,
        tmnxDiamApNqAvpNasPortIdSfixStr,
        tmnxDiamApNqAvpNasPortTypeType,
        tmnxDiamApNqAvpNasPortTypeValue,
        tmnxDiamApNqPassword,
        tmnxDiamApNqUserNameFormat,
        tmnxDiamApNqUserNameOp,
        tmnxDiamApNqDomain,
        tmnxDiamApNqMacFormat
    }
    STATUS      current
    DESCRIPTION
        "The group of objects supporting DIAMETER NASREQ for the Nokia SROS
         series systems."
    ::= { tmnxDiameterGroups 19 }

tmnxDiameterProxyV14v0Group      OBJECT-GROUP
    OBJECTS     {
        tmnxDiamPlcyRole,
        tmnxDiamPpPrxLastMgmtChange,
        tmnxDiamPpPrxAdminState,
        tmnxDiamPpPrxRouter,
        tmnxDiamPpPrxAddrType,
        tmnxDiamPpPrxAddr,
        tmnxDiamPpPrxOperState,
        tmnxDiamPpPrxMcLocState,
        tmnxDiamPpPrxMcLocOriginStateId,
        tmnxDiamPpPrxMcLocMacAddress,
        tmnxDiamPpPrxMcLocCtrlMacAddress,
        tmnxDiamPpPrxMcRemState,
        tmnxDiamPpPrxMcRemOriginStateId,
        tmnxDiamPpPrxMcRemMacAddress,
        tmnxDiamPpPrxMcRemCtrlMacAddress,
        tmnxDiamPpPrxClientPsmState,
        tmnxDiamPpPrxClientTransactions,
        tmnxDiamPpPrxTableLastCh,
        tmnxDiamApGxAvpNasPortIdSfixStr
    }
    STATUS      current
    DESCRIPTION
        "The group of objects supporting management of DIAMETER Proxy on Nokia
         SROS series systems."
    ::= { tmnxDiameterGroups 20 }

tmnxDiameterNotifyV14v0Group     NOTIFICATION-GROUP
    NOTIFICATIONS {
        tmnxDiamPolicyPeerStateChange,
        tmnxDiamAppSessionFailure,
        tmnxDiamSessionEvent,
        tmnxDiamPpPrxMcLocStateChanged,
        tmnxDiamMessageDropped
    }
    STATUS      current
    DESCRIPTION
        "The group of notifications supporting DIAMETER on Nokia SROS series."
    ::= { tmnxDiameterGroups 21 }

tmnxDiameterGyEfhGroup           OBJECT-GROUP
    OBJECTS     {
        tmnxDiamGyEfhAdminState,
        tmnxDiamGyEfhNewSessionId,
        tmnxDiamGyEfhInterimCreditReport,
        tmnxDiamGyEfhInterimCreditVolume,
        tmnxDiamGyEfhInterimCVolumeUnit,
        tmnxDiamGyEfhInterimCredValTime,
        tmnxDiamGyEfhInterimCMaxAttempts
    }
    STATUS      current
    DESCRIPTION
        "The group of objects supporting DIAMETER Extended Failure Handling on
         Nokia SROS series."
    ::= { tmnxDiameterGroups 22 }

tmnxDiameterV15v0Group           OBJECT-GROUP
    OBJECTS     {
        tmnxDiamApGyMacFormat,
        tmnxDiamApGyMacFormat,
        tmnxDiamApGyIncAddressAvp,
        tmnxDiamApGyInc3GppChargingId,
        tmnxDiamApGyInc3GppGprsNQosProf,
        tmnxDiamApGyInc3GppNsapi,
        tmnxDiamApGyInc3GppSessionStopIn,
        tmnxDiamApGyInc3GppSelectionMode,
        tmnxDiamApGyInc3GppChargingChara,
        tmnxDiamApGyInc3GppRatType,
        tmnxDiamApGyIncGgsnAddress,
        tmnxDiamApGyIncPsInformation,
        tmnxDiamApGyIncChargingRBaseName,
        tmnxDiamApGyChargingRuleBaseName,
        tmnxDiamApGyIncPdpContextType,
        tmnxDiamApGyIncUserEqInfoType,
        tmnxDiamApGx3gqmAADlMappingType,
        tmnxDiamApGx3gqmAADlArbiterName,
        tmnxDiamApGx3gqmAADlSchedulrName,
        tmnxDiamApGx3gqmAADlPolicerId,
        tmnxDiamApGx3gqmAADlQueueId,
        tmnxDiamApGx3gqmAAUlMappingType,
        tmnxDiamApGx3gqmAAUlArbiterName,
        tmnxDiamApGx3gqmAAUlSchedulrName,
        tmnxDiamApGx3gqmAAUlPolicerId,
        tmnxDiamApGx3gqmAAUlQueueId
    }
    STATUS      current
    DESCRIPTION
        "The group of objects supporting DIAMETER that were added in release
         15.0 of the Nokia SROS series systems."
    ::= { tmnxDiameterGroups 25 }

tmnxDiamObsoleteGroup            OBJECT-GROUP
    OBJECTS     {
        tmnxDiamPlcyDccaTableLastChngd,
        tmnxDiamPlcyDccaLastMgmtChange,
        tmnxDiamPlcyDccaFailover,
        tmnxDiamPlcyDccaFailureHndlng,
        tmnxDiamPlcyDccaTxTimer,
        tmnxDiamPlcyDccaAvpServCntxtId,
        tmnxDiamPlcyDccaAvpCldStationId,
        tmnxDiamPlcyDccaAvpRadiusUsrNme,
        tmnxDiamPlcyDccaAvpSubIdOrg,
        tmnxDiamPlcyDccaAvpSubIdType,
        tmnxDiamPlcyDccaOutOfCreditRep,
        tmnxDiamPlcyDccaAvpNasP,
        tmnxDiamPlcyDccaAvpNasPPfixType,
        tmnxDiamPlcyDccaAvpNasPPfixStr,
        tmnxDiamPlcyDccaAvpNasPSfixType,
        tmnxDiamPlcyDccaAvpNasPType,
        tmnxDiamPlcyDccaApplicationType,
        tmnxDiamPlcyDccaAvpImsiOrg,
        tmnxDiamPlcyDccaMaxPendingReq,
        tmnxDiamPlcyDccaTxRetryLimit,
        tmnxDiamPeerStatsLastClearTime,
        tmnxDiamPeerStCiTcpSendFailed,
        tmnxDiamPeerStCiDiamRxDropCnt,
        tmnxDiamPeerStCiDiamTxReqs,
        tmnxDiamPeerStCiDiamRxResps,
        tmnxDiamPeerStCiPendMsgsPMQ,
        tmnxDiamPeerStCiReqTimeoutsPMQ,
        tmnxDiamPeerStSiTcpSendFailed,
        tmnxDiamPeerStSiDiamRxDropCnt,
        tmnxDiamPeerStSiDiamRxReqs,
        tmnxDiamPeerStSiDiamTxResps,
        tmnxDiamPeerStErrHdlDiamTxErrCnt,
        tmnxDiamPeerStErrHdlDiamRxErrCnt,
        tmnxDiamPeerStCcrInitialTx,
        tmnxDiamPeerStCcaInitialRx,
        tmnxDiamPeerStCcrUpdateTx,
        tmnxDiamPeerStCcaUpdateRx,
        tmnxDiamPeerStCcrTerminateTx,
        tmnxDiamPeerStCcaTerminateRx,
        tmnxDiamPeerStCerTx,
        tmnxDiamPeerStCeaRx,
        tmnxDiamPeerStWdrTx,
        tmnxDiamPeerStWdaRx,
        tmnxDiamPeerStWdrRx,
        tmnxDiamPeerStWdaTx,
        tmnxDiamPeerStAsrRx,
        tmnxDiamPeerStAsaTx,
        tmnxDiamPeerStRarRx,
        tmnxDiamPeerStRaaTx,
        tmnxDiamPeerStDprTx,
        tmnxDiamPeerStDpaRx,
        tmnxDiamPeerStDprRx,
        tmnxDiamPeerStDpaTx,
        tmnxDiamPeerStAarTx,
        tmnxDiamPeerStAaaRx,
        tmnxDiamPrxClStLastClearedTime,
        tmnxDiamPrxClStCiTcpSendFailed,
        tmnxDiamPrxClStCiDiamRxDropCnt,
        tmnxDiamPrxClStCiDiamRxReqs,
        tmnxDiamPrxClStCiDiamTxResps,
        tmnxDiamPrxClStCiPendMsgsPmq,
        tmnxDiamPrxClStCiReqTimeoutsPmq,
        tmnxDiamPrxClStSiTcpSendFailed,
        tmnxDiamPrxClStSiDiamRxDropCnt,
        tmnxDiamPrxClStSiDiamTxReqs,
        tmnxDiamPrxClStSiDiamRxResps,
        tmnxDiamPrxClStCcrInitialRx,
        tmnxDiamPrxClStCcaInitialTx,
        tmnxDiamPrxClStCcrUpdateRx,
        tmnxDiamPrxClStCcaUpdateTx,
        tmnxDiamPrxClStCcrTerminateRx,
        tmnxDiamPrxClStCcaTerminateTx,
        tmnxDiamPrxClStCerRx,
        tmnxDiamPrxClStCeaTx,
        tmnxDiamPrxClStDwrRx,
        tmnxDiamPrxClStDwaTx,
        tmnxDiamPrxClStDwrTx,
        tmnxDiamPrxClStDwaRx,
        tmnxDiamPrxClStAsrTx,
        tmnxDiamPrxClStAsaRx,
        tmnxDiamPrxClStRarTx,
        tmnxDiamPrxClStRaaRx,
        tmnxDiamPrxClStDprTx,
        tmnxDiamPrxClStDpaRx,
        tmnxDiamPrxClStDprRx,
        tmnxDiamPrxClStDpaTx,
        tmnxDiamPrxClStAarRx,
        tmnxDiamPrxClStAaaTx
    }
    STATUS      current
    DESCRIPTION
        "The group of objects that have been obsoleted."
    ::= { tmnxDiameterGroups 98 }

tmnxDiamObsoleteNotifyGroup      NOTIFICATION-GROUP
    NOTIFICATIONS {
        tmnxDiamAppMessageDropped,
        tmnxDiamPrxMessageDropped
    }
    STATUS      current
    DESCRIPTION
        "The group of notification objects that are obsoleted."
    ::= { tmnxDiameterGroups 99 }

tmnxDiameterNotifyPrefix         OBJECT IDENTIFIER ::= { tmnxSRNotifyPrefix 58 }

tmnxDiameterNotifications        OBJECT IDENTIFIER ::= { tmnxDiameterNotifyPrefix 0 }

tmnxDiamPolicyPeerStateChange    NOTIFICATION-TYPE
    OBJECTS     {
        tmnxDiamPeerPrimarySecondary,
        tmnxDiamPeerConnectionSuspended,
        tmnxDiamPeerCooldownSeqActive,
        tmnxDiamAppTrapDescription
    }
    STATUS      current
    DESCRIPTION
        "A tmnxDiamPolicyPeerStateChange notification is generated when the
         state of a DIAMETER policy peer changes."
    ::= { tmnxDiameterNotifications 1 }

tmnxDiamAppMessageDropped        NOTIFICATION-TYPE
    OBJECTS     {
        tmnxDiamAppPlcyName,
        tmnxDiamAppPeerName,
        tmnxDiamAppTrapDescription
    }
    STATUS      obsolete
    DESCRIPTION
        "The tmnxDiamAppMessageDropped notification indicates that the DIAMETER
         protocol has dropped a message due to some reason.

         This notification is obsoleted in release 14.0. It is replaced by
         tmnxDiamMessageDropped."
    ::= { tmnxDiameterNotifications 2 }

tmnxDiamAppSessionFailure        NOTIFICATION-TYPE
    OBJECTS     {
        tmnxDiamAppSessionId,
        tmnxDiamAppSubscrId,
        tmnxDiamAppSapId,
        tmnxDiamAppSLAProfName,
        tmnxDiamAppTrapDescription
    }
    STATUS      current
    DESCRIPTION
        "The tmnxDiamAppSessionFailure notification indicates that the DIAMETER
         protocol has a session failure."
    ::= { tmnxDiameterNotifications 3 }

tmnxDiamSessionEvent             NOTIFICATION-TYPE
    OBJECTS     {
        tmnxDiamAppSessionId,
        tmnxDiamAppPlcyApplication,
        tmnxDiamNotifyEventId,
        tmnxDiamAppTrapDescription
    }
    STATUS      current
    DESCRIPTION
        "The tmnxDiamSessionEvent notification is issued when something unusual
         happens while handling a Diameter session.

         [CAUSE] A Diameter session has experienced a problem. The session ID
         is indicated with the tmnxDiamAppSessionId. The associated Diameter
         application policy is indicated with the tmnxDiamAppPlcyApplication.
         What happened is indicated with the tmnxDiamNotifyEventId and the
         tmnxDiamAppTrapDescription.

         [EFFECT] The effect depends on the cause. For example: if a Diameter
         message could not be transmitted, session set-up may fail.

         [RECOVERY] The recovery depends on the cause."
    ::= { tmnxDiameterNotifications 4 }

tmnxDiamPpPrxMcLocStateChanged   NOTIFICATION-TYPE
    OBJECTS     {
        tmnxDiamPpPrxMcLocState
    }
    STATUS      current
    DESCRIPTION
        "The tmnxDiamPpPrxMcLocStateChanged notification is sent when the value
         of the object tmnxWlanGwGrpOperState changes.

         [CAUSE] The MCS (Multi Chassis redundancy Synchronization) state of a
         proxy function has changed. [EFFECT] The effect depends on the actual
         state transition. The states 'active' and 'standby' are normal states.
         In other states, Diameter communication may be interrupted, and hosts
         may be refused access to network services. [RECOVERY] The need for
         recovery action depends on the state transition. In the states
         'active' and 'standby', no recovery action may be necessary."
    ::= { tmnxDiameterNotifications 5 }

tmnxDiamPrxMessageDropped        NOTIFICATION-TYPE
    OBJECTS     {
        tmnxDiamPrxClStCiDiamRxDropCnt,
        tmnxDiamPrxClStSiDiamRxDropCnt,
        tmnxDiamAppTrapDescription
    }
    STATUS      obsolete
    DESCRIPTION
        "The tmnxDiamPrxMessageDropped notification indicates that a Diameter
         proxy has dropped a message.

         This notification is obsoleted in release 14.0. It is replaced by
         tmnxDiamMessageDropped."
    ::= { tmnxDiameterNotifications 6 }

tmnxDiamMessageDropped           NOTIFICATION-TYPE
    OBJECTS     {
        tmnxDiamPeerStatsFailedMessages,
        tmnxDiamAppTrapDescription
    }
    STATUS      current
    DESCRIPTION
        "The tmnxDiamMessageDropped notification indicates that the DIAMETER
         protocol has dropped a message."
    ::= { tmnxDiameterNotifications 7 }

END
