TIMETRA-OTU-MIB DEFINITIONS ::= BEGIN

IMPORTS
    ifIndex
                                                         FROM IF-MIB
    MODULE-COMPLIANCE, NOTIFICATION-GROUP,
    OBJECT-GROUP
                                                         FROM SNMPv2-CONF
    Counter32, Counter64, MODULE-IDENTITY,
    NOTIFICATION-TYPE, OBJECT-TYPE,
    Unsigned32
                                                         FROM SNMPv2-SMI
    RowStatus, TEXTUAL-CONVENTION,
    TimeStamp, TruthValue
                                                         FROM SNMPv2-TC
    timetraSRMIBModules, tmnxSRConfs,
    tmnxSRNotifyPrefix, tmnxSRObjs
                                                         FROM TIMETRA-GLOBAL-MIB
    TmnxActionType
                                                         FROM TIMETRA-TC-MIB
    ;

tmnxOtuMIBModule                 MODULE-IDENTITY
    LAST-UPDATED "201501010000Z"
    ORGANIZATION "Nokia"
    CONTACT-INFO
        "Nokia 7x50 Support
         Web: http://www.nokia.com"
    DESCRIPTION
        "This document is the SNMP MIB module to manage and provision the
         Optical Transport Unit (OTU) components of the Nokia SROS device.

         Copyright 2008-2017 Nokia.  All rights reserved.
         Reproduction of this document is authorized on the condition that
         the foregoing copyright notice is included.

         This SNMP MIB module (Specification) embodies Nokia's
         proprietary intellectual property.  Nokia retains
         all title and ownership in the Specification, including any
         revisions.

         Nokia grants all interested parties a non-exclusive license to use and
         distribute an unmodified copy of this Specification in connection with
         management of Nokia products, and without fee, provided this copyright
         notice and license appear on all copies.

         This Specification is supplied 'as is', and Nokia makes no warranty,
         either express or implied, as to the use, operation, condition, or
         performance of the Specification."

    REVISION    "201501010000Z"
    DESCRIPTION
        "Rev 13.0                1 Jan 2015 00:00
         13.0 release of the TIMETRA-OTU-MIB."

    REVISION    "200902280000Z"
    DESCRIPTION
        "Rev 7.0                28 Feb 2009 00:00
         7.0 release of the TIMETRA-OTU-MIB."

    REVISION    "200810230000Z"
    DESCRIPTION
        "Rev 1.0                01 Jul 2008 00:00
         1.0 release of the TIMETRA-OTU-MIB."

    ::= { timetraSRMIBModules 62 }

TmnxOtuFecMode                   ::= TEXTUAL-CONVENTION
    STATUS      current
    DESCRIPTION
        "The TmnxOtuFecMode specifies what type of Forward Error Correction
         (FEC) has been enabled on the port. The valid types are as follows:

                - disabled       - OTU encap enabled with no FEC.
                - g709fec        - OTU encap enabled with G.709 FEC.
                - enhanced       - OTU encap enabled with enhanced FEC."
    SYNTAX      INTEGER {
        disabled (0),
        g709fec  (1),
        enhanced (2)
    }

TmnxOtu2LanDataRate              ::= TEXTUAL-CONVENTION
    STATUS      current
    DESCRIPTION
        "The TmnxOtu2LanDataRate specifies the allowable data rates for a given
         OTU2 10GE-LAN enabled interface. The valid data rates are as follows:

                - notApplicable  - not an OTU 10GE enabled interface.
                - dr11049        - 11.049 Gb/s synchronous OTU encapsulated
                                   10GE-LAN signal. (i.e. No fixed stuffing
                                   bytes in the OTU2 frame).
                - dr11096        - 11.0957 Gb/s synchronous OTU encapsulated
                                   10GE-LAN signal. (i.e. Fixed stuffing bytes
                                   in the OTU2 frame)."
    SYNTAX      INTEGER {
        notApplicable (0),
        dr11049       (1),
        dr11096       (2)
    }

TmnxOtuSFSDMethod                ::= TEXTUAL-CONVENTION
    STATUS      current
    DESCRIPTION
        "The TmnxOtuSFSDMethod specifies the method to determine the Signal
         Failure (SF) and Signal Degradation (SD) of the interface. The valid
         methods are as follows:

                - fec            - FEC correctable bit errors are used to
                                   declare the presence of the Signal Fail and
                                   Signal Degrade condition.
                - bip8           - the SM-BIP8 errors are used to declare the
                                   presence of the Signal Fail and Signal
                                   Degrade condition."
    SYNTAX      INTEGER {
        fec  (1),
        bip8 (2)
    }

TmnxOtuTtiMode                   ::= TEXTUAL-CONVENTION
    STATUS      current
    DESCRIPTION
        "The TmnxOtuTtiMode specifies the type of data transmitted in the Trail
         Trace Identifier (TTI) Section of the OTU frame. The valid modes are
         as follows:

                - auto           - Specifies that the TTI Section is
                                   auto-generated by the system.
                - string         - Specifies that the TTI Section is a
                                   sequence of printable-ascii.
                - bytes          - Specifies that the TTI Section is a
                                   sequence of bytes."
    SYNTAX      INTEGER {
        auto   (0),
        string (1),
        bytes  (2)
    }

TmnxOtuTtiString                 ::= TEXTUAL-CONVENTION
    STATUS      current
    DESCRIPTION
        "The TmnxOtuTtiString specifies the data transmitted in the Trail Trace
         Identifier (TTI) Section of the OTU frame. The TTI Section may consist
         of octet values from the range 0..255 (0x00..0xFF)."
    SYNTAX      OCTET STRING (SIZE (0..255))

TmnxOtuAlarms                    ::= TEXTUAL-CONVENTION
    STATUS      current
    DESCRIPTION
        "The TmnxOtuAlarms specifies the alarms which are enabled or
         outstanding against an OTU enabled interface. The valid alarms are as
         follows:

                - loc            - Loss of Clock.
                - los            - Loss of Signal.
                - lof            - Loss of OTU Framing.
                - lom            - Loss of Multi-frame.
                - otuAis         - OTU Alarm Indication Signal.
                - otuBerSf       - OTU Bit Error Rate Signal Fail.
                - otuBerSd       - OTU Bit Error Rate Signal Degradation.
                - otuBdi         - OTU Backward Defect Indication.
                - otuTim         - OTU Trace ID Mismatch.
                - otuIae         - OTU Incoming Alignment Error.
                - otuBiae        - OTU Backward Incoming Alignment Error.
                - fecSf          - FEC Signal Failure.
                - fecSd          - FEC Signal Degradation.
                - fecFail        - FEC Rx/Tx mode mismatch (enhanced/g709fec)
                                   or High uncorrectable bit rate (>10E-2).
                - fecUncorr      - One or more uncorrectable FEC errors.
                - oduAis         - Optical Data Unit (ODU) Alarm Indication
                                   Signal.
                - oduOci         - ODU Open Connection Indication.
                - oduLck         - ODU Locked.
                - oduBdi         - PM Backward Defect Indication.
                - oduTim         - PM Trace ID Mismatch.
                - opuTim         - OPU PSI Trace Mismatch.
                - opuPlm         - OPU PSI Payload Type Mismatch."
    SYNTAX      BITS {
        loc       (0),
        los       (1),
        lof       (2),
        lom       (3),
        otuAis    (4),
        otuBerSf  (5),
        otuBerSd  (6),
        otuBdi    (7),
        otuTim    (8),
        otuIae    (9),
        otuBiae   (10),
        fecSf     (11),
        fecSd     (12),
        fecFail   (13),
        fecUncorr (14),
        oduAis    (15),
        oduOci    (16),
        oduLck    (17),
        oduBdi    (18),
        oduTim    (19),
        opuTim    (20),
        opuPlm    (21)
    }

TmnxOtuPsiPayloadType            ::= TEXTUAL-CONVENTION
    STATUS      current
    DESCRIPTION
        "The TmnxOtuPsiPayloadType specifies the payload type identifier as
         defined in table 15-8 of section 15.9.2.1.1 of ITU-T Rec. G.709 and
         the codes are as follows:

                - auto           - Automatic based on operating mode.
                - exp            - Experimental mapping.
                - asyncCbr       - Asynchronous CBR mapping.
                - syncCbr        - Bit synchronous CBR mapping.
                - atm            - ATM mapping.
                - gfp            - GFP mapping.
                - vcat           - Virtual Concatenated signal.
                - gmp            - Generic Mapping Procedure.
                - bitStrOctet    - Bit stream with octet timing mapping.
                - bitStrNoOctet  - Bit stream without octet timing mapping.
                - oduMux         - ODU multiplex structure.
                - rsvd80         - Reserved Proprietary 0x80
                - rsvd81         - Reserved Proprietary 0x81
                - rsvd82         - Reserved Proprietary 0x82
                - rsvd83         - Reserved Proprietary 0x83
                - rsvd84         - Reserved Proprietary 0x84
                - rsvd85         - Reserved Proprietary 0x85
                - rsvd86         - Reserved Proprietary 0x86
                - rsvd87         - Reserved Proprietary 0x87
                - rsvd88         - Reserved Proprietary 0x88
                - rsvd89         - Reserved Proprietary 0x89
                - rsvd8A         - Reserved Proprietary 0x8A
                - rsvd8B         - Reserved Proprietary 0x8B
                - rsvd8C         - Reserved Proprietary 0x8C
                - rsvd8D         - Reserved Proprietary 0x8D
                - rsvd8E         - Reserved Proprietary 0x8E
                - rsvd8F         - Reserved Proprietary 0x8F
                - nullTest       - NULL test signal mapping.
                - prbsTest       - PRBS test signal mapping."
    SYNTAX      INTEGER {
        auto          (0),
        exp           (1),
        asyncCbr      (2),
        syncCbr       (3),
        atm           (4),
        gfp           (5),
        vcat          (6),
        gmp           (7),
        bitStrOctet   (16),
        bitStrNoOctet (17),
        oduMux        (32),
        rsvd80        (128),
        rsvd81        (129),
        rsvd82        (130),
        rsvd83        (131),
        rsvd84        (132),
        rsvd85        (133),
        rsvd86        (134),
        rsvd87        (135),
        rsvd88        (136),
        rsvd89        (137),
        rsvd8A        (138),
        rsvd8B        (139),
        rsvd8C        (140),
        rsvd8D        (141),
        rsvd8E        (142),
        rsvd8F        (143),
        nullTest      (253),
        prbsTest      (254)
    }

TmnxOtuTimReaction               ::= TEXTUAL-CONVENTION
    STATUS      current
    DESCRIPTION
        "The TmnxOtuTimReaction specifies the type of reaction that should be
         taken in the event of Trace Identifier (TTI) Mismatch or Payload Type
         Mismatch. The valid modes are as follows:

                - none           - Specifies that the Received Payload data
                                   should be passed through when a Trace
                                   Identifier Mismatch is detected.
                - squelch-rx     - Specifies that the Received Payload data
                                   should be blocked with a maintenance signal
                                   when a Trace Identifier Mismatch is
                                   detected."
    SYNTAX      INTEGER {
        none      (0),
        squelchRx (1)
    }

TmnxOtuIfOtu4SignalType          ::= TEXTUAL-CONVENTION
    STATUS      current
    DESCRIPTION
        "TmnxOtuIfOtu4SignalType is an enumerated integer that specifies the
         signal type that can be provisioned on the OTU encapsulated physical
         interface.

         Values:
            'notApplicable' - The provisioned port is not a DWDM line port.
            'otu4'          - The DWDM line port can transport one 100GbE
                              client signal.
            'otu4x2'        - The DWDM line port can transport up to two
                              100GbE client signals."
    SYNTAX      INTEGER {
        notApplicable (1),
        otu4          (2),
        otu4x2        (3)
    }

tmnxOtuObjs                      OBJECT IDENTIFIER ::= { tmnxSRObjs 62 }

tmnxOtuConfigurationTimeStamps   OBJECT IDENTIFIER ::= { tmnxOtuObjs 0 }

tmnxOtuIfTableLastChanged        OBJECT-TYPE
    SYNTAX      TimeStamp
    MAX-ACCESS  read-only
    STATUS      current
    DESCRIPTION
        "The tmnxOtuIfTableLastChanged indicates the time, since system
         startup, when a row in the tmnxOtuIfTable last changed."
    ::= { tmnxOtuConfigurationTimeStamps 1 }

tmnxOtuConfigurations            OBJECT IDENTIFIER ::= { tmnxOtuObjs 1 }

tmnxOtuIfTable                   OBJECT-TYPE
    SYNTAX      SEQUENCE OF TmnxOtuIfEntry
    MAX-ACCESS  not-accessible
    STATUS      current
    DESCRIPTION
        "The tmnxOtuIfTable consists of the interfaces using OTU encapsulation."
    ::= { tmnxOtuConfigurations 1 }

tmnxOtuIfEntry                   OBJECT-TYPE
    SYNTAX      TmnxOtuIfEntry
    MAX-ACCESS  not-accessible
    STATUS      current
    DESCRIPTION
        "The tmnxOtuIfEntry contains information pertaining to an individual
         OTU encapsulated physical interface.

         Rows in this table are created and destroyed using the
         tmnxOtuIfRowStatus object."
    INDEX       { ifIndex }
    ::= { tmnxOtuIfTable 1 }

TmnxOtuIfEntry                   ::= SEQUENCE
{
    tmnxOtuIfRowStatus               RowStatus,
    tmnxOtuIfTimeStamp               TimeStamp,
    tmnxOtuIfFecMode                 TmnxOtuFecMode,
    tmnxOtuIfSfSdMethod              TmnxOtuSFSDMethod,
    tmnxOtuIfBerSfThreshold          Unsigned32,
    tmnxOtuIfBerSdThreshold          Unsigned32,
    tmnxOtuIfOtuOperDataRate         Unsigned32,
    tmnxOtuIfOtu2LanDataRate         TmnxOtu2LanDataRate,
    tmnxOtuIfCfgAlarms               TmnxOtuAlarms,
    tmnxOtuIfAlarmState              TmnxOtuAlarms,
    tmnxOtuIfHoldTimeUp              Unsigned32,
    tmnxOtuIfHoldTimeDown            Unsigned32,
    tmnxOtuIfSmTtiTxMode             TmnxOtuTtiMode,
    tmnxOtuIfSmTtiTx                 TmnxOtuTtiString,
    tmnxOtuIfSmTtiRx                 TmnxOtuTtiString,
    tmnxOtuIfSmTtiExpMode            TmnxOtuTtiMode,
    tmnxOtuIfSmTtiExpCopyRx          TmnxActionType,
    tmnxOtuIfSmTtiExp                TmnxOtuTtiString,
    tmnxOtuIfPmTtiTxMode             TmnxOtuTtiMode,
    tmnxOtuIfPmTtiTx                 TmnxOtuTtiString,
    tmnxOtuIfPmTtiRx                 TmnxOtuTtiString,
    tmnxOtuIfPmTtiExpMode            TmnxOtuTtiMode,
    tmnxOtuIfPmTtiExpCopyRx          TmnxActionType,
    tmnxOtuIfPmTtiExp                TmnxOtuTtiString,
    tmnxOtuIfPsiTtiTxMode            TmnxOtuTtiMode,
    tmnxOtuIfPsiTtiTx                TmnxOtuTtiString,
    tmnxOtuIfPsiTtiRx                TmnxOtuTtiString,
    tmnxOtuIfPsiTtiExpMode           TmnxOtuTtiMode,
    tmnxOtuIfPsiTtiExpCopyRx         TmnxActionType,
    tmnxOtuIfPsiTtiExp               TmnxOtuTtiString,
    tmnxOtuIfPsiPayloadTypeTx        TmnxOtuPsiPayloadType,
    tmnxOtuIfPsiPayloadTypeRx        TmnxOtuPsiPayloadType,
    tmnxOtuIfPsiPayloadTypeExp       TmnxOtuPsiPayloadType,
    tmnxOtuIfGfpMappingEnable        TruthValue,
    tmnxOtuIfAsyncMappingEnable      TruthValue,
    tmnxOtuIfSmTimReaction           TmnxOtuTimReaction,
    tmnxOtuIfPmTimReaction           TmnxOtuTimReaction,
    tmnxOtuIfPsiTimReaction          TmnxOtuTimReaction,
    tmnxOtuIfPsiPlmReaction          TmnxOtuTimReaction
}

tmnxOtuIfRowStatus               OBJECT-TYPE
    SYNTAX      RowStatus
    MAX-ACCESS  read-create
    STATUS      current
    DESCRIPTION
        "The tmnxOtuIfRowStatus controls the creation and deletion of row
         entries in the tmnxOtuIfTable.

         Creating a row in the tmnxOtuIfTable using 'createAndGo (4)' enables
         OTU encapsulation for the interface. Deleting the row using 'destroy
         (6)' will disable the OTU encapsulation.

         If a physical port does not support the OTU encapsulation, an attempt
         to set the tmnxOtuIfRowStatus to a value of 'createAndGo (4)' will
         fail with an inconsistent value result."
    ::= { tmnxOtuIfEntry 1 }

tmnxOtuIfTimeStamp               OBJECT-TYPE
    SYNTAX      TimeStamp
    MAX-ACCESS  read-only
    STATUS      current
    DESCRIPTION
        "The tmnxOtuIfTimeStamp indicates the time, since system startup, of
         the last change to this row."
    ::= { tmnxOtuIfEntry 2 }

tmnxOtuIfFecMode                 OBJECT-TYPE
    SYNTAX      TmnxOtuFecMode
    MAX-ACCESS  read-create
    STATUS      current
    DESCRIPTION
        "The tmnxOtuIfFecMode specifies the OTU encapsulation used by this
         interface."
    DEFVAL      { enhanced }
    ::= { tmnxOtuIfEntry 3 }

tmnxOtuIfSfSdMethod              OBJECT-TYPE
    SYNTAX      TmnxOtuSFSDMethod
    MAX-ACCESS  read-create
    STATUS      current
    DESCRIPTION
        "The tmnxOtuIfSfSdMethod specifies the method on which to detect Signal
         Failure and Signal Degradation."
    DEFVAL      { fec }
    ::= { tmnxOtuIfEntry 4 }

tmnxOtuIfBerSfThreshold          OBJECT-TYPE
    SYNTAX      Unsigned32 (3..6)
    UNITS       "error bits in 1/10e-n bits received"
    MAX-ACCESS  read-create
    STATUS      current
    DESCRIPTION
        "The value of tmnxOtuIfBerSfThreshold specifies the bit error rate
         (BER) threshold used to determine when to raise and clear
         otuBerSf/fecSf alarms.

         Bit error computed must reach/exceed the threshold value over a
         predefined period of time for the alarms to be raised. The
         tmnxOtuIfSfSdMethod defines how the bit error is computed and what
         values of tmnxOtuIfBerSfThreshold are allowed. The following table
         defines this dependency:

         tmnxOtuIfSfSdMethod   Bit error calculation
         -------------------   ----------------------------------------------
         fec (1)               Each corrected bit counts as one bit error.
         bip8 (2)              Each BIP8 coding violation counts as one bit
                               error."
    DEFVAL      { 5 }
    ::= { tmnxOtuIfEntry 5 }

tmnxOtuIfBerSdThreshold          OBJECT-TYPE
    SYNTAX      Unsigned32 (5..9)
    UNITS       "error bits in 1/10^n bits received"
    MAX-ACCESS  read-create
    STATUS      current
    DESCRIPTION
        "The value of tmnxOtuIfBerSdThreshold specifies the bit error rate
         (BER) threshold used to determine when to raise and clear
         otuBerSd/fecSd alarms.

         Bit error computed must reach/exceed the threshold value over a
         predefined period of time for the alarms to be raised. The
         tmnxOtuIfSfSdMethod defines how the bit error is computed and what
         values of tmnxOtuIfBerSdThreshold are allowed. The following table
         defines this dependency:

         tmnxOtuIfSfSdMethod   Bit error calculation
         -------------------   ----------------------------------------------
         fec (1)               Each corrected bit counts as one bit error.
         bip8 (2)              Each BIP8 coding violation counts as one bit
                               error."
    DEFVAL      { 7 }
    ::= { tmnxOtuIfEntry 6 }

tmnxOtuIfOtuOperDataRate         OBJECT-TYPE
    SYNTAX      Unsigned32
    UNITS       "Mb/s"
    MAX-ACCESS  read-only
    STATUS      current
    DESCRIPTION
        "The tmnxOtuIfOtuOperDataRate indicates the rate at which the OTU data
         is transmitted on the line."
    ::= { tmnxOtuIfEntry 7 }

tmnxOtuIfOtu2LanDataRate         OBJECT-TYPE
    SYNTAX      TmnxOtu2LanDataRate
    UNITS       "Gb/s"
    MAX-ACCESS  read-create
    STATUS      current
    DESCRIPTION
        "The value of tmnxOtuIfOtu2LanDataRate specifies the rate at which data
         is transmitted on the line. An interface that does not support OTU2
         encapsulation will default, and be restricted to, the value of
         'notApplicable (0)'."
    DEFVAL      { dr11049 }
    ::= { tmnxOtuIfEntry 8 }

tmnxOtuIfCfgAlarms               OBJECT-TYPE
    SYNTAX      TmnxOtuAlarms
    MAX-ACCESS  read-create
    STATUS      current
    DESCRIPTION
        "The value of tmnxOtuIfCfgAlarms specifies the alarms that are to be
         monitored by the OTU interface. If an alarm bit is set, then the
         corresponding alarm will raise/clear an alarm when its state changes.
         An unset bit specifies that the alarm corresponding with the bit will
         not alarm on its state transitions."
    DEFVAL      { {loc, los, lof, lom, otuBdi, otuBerSf, fecSf} }
    ::= { tmnxOtuIfEntry 9 }

tmnxOtuIfAlarmState              OBJECT-TYPE
    SYNTAX      TmnxOtuAlarms
    MAX-ACCESS  read-only
    STATUS      current
    DESCRIPTION
        "The value of tmnxOtuIfAlarmState indicates which monitored alarms are
         raised against the OTU interface."
    ::= { tmnxOtuIfEntry 10 }

tmnxOtuIfHoldTimeUp              OBJECT-TYPE
    SYNTAX      Unsigned32 (0..100)
    UNITS       "100s of milliseconds"
    MAX-ACCESS  read-create
    STATUS      obsolete
    DESCRIPTION
        "The value of tmnxOtuIfHoldTimeUp is used to configure the hold-timer
         for link up event dampening. This guards against reporting excessive
         interface transitions. This is implemented by not advertising
         subsequent transitions of the interface to upper layer protocols until
         the configured timer has expired.

         A value of zero (0) indicates that an up transition is reported
         immediately."
    DEFVAL      { 5 }
    ::= { tmnxOtuIfEntry 11 }

tmnxOtuIfHoldTimeDown            OBJECT-TYPE
    SYNTAX      Unsigned32 (0..100)
    UNITS       "100s of milliseconds"
    MAX-ACCESS  read-create
    STATUS      obsolete
    DESCRIPTION
        "The value of tmnxOtuIfHoldTimeDown is used to configure the hold-timer
         for link down event dampening. This guards against reporting excessive
         interface transitions. This is implemented by not advertising
         subsequent transitions of the interface to upper layer protocols until
         the configured timer has expired.

         A value of zero (0) indicates that an up transition is reported
         immediately."
    DEFVAL      { 0 }
    ::= { tmnxOtuIfEntry 12 }

tmnxOtuIfSmTtiTxMode             OBJECT-TYPE
    SYNTAX      TmnxOtuTtiMode
    MAX-ACCESS  read-create
    STATUS      current
    DESCRIPTION
        "The value of tmnxOtuIfSmTtiTxMode specifies the type of Trail Trace
         Identifier (TTI) for the Section Monitoring (SM) in the OTU overhead.

         Specifying a tmnxOtuIfSmTtiTxMode value of 'auto (0)' along with
         tmnxOtuIfSmTtiTx set with a single octet of '0xFF' will revert the
         SM-TTI to the default:
         '<system-name>/<iom-slot>/<mda-slot>/<port-number>/C<dwdm-channel>'"
    ::= { tmnxOtuIfEntry 13 }

tmnxOtuIfSmTtiTx                 OBJECT-TYPE
    SYNTAX      TmnxOtuTtiString (SIZE (0..64))
    MAX-ACCESS  read-create
    STATUS      current
    DESCRIPTION
        "The value of tmnxOtuIfSmTtiTx specifies the Trail Trace Identifier
         (TTI) for the Section Monitoring (SM) in the OTU overhead. This
         identifier can be a string or a non-printable sequence of bytes.

         Specifying a one octet string with the value '0xFF' along with a
         tmnxOtuIfSmTtiTxMode set to the value of 'auto (0)' will reset the TTI
         to the system generated value."
    ::= { tmnxOtuIfEntry 14 }

tmnxOtuIfSmTtiRx                 OBJECT-TYPE
    SYNTAX      TmnxOtuTtiString (SIZE (0..64))
    MAX-ACCESS  read-only
    STATUS      current
    DESCRIPTION
        "The value of tmnxOtuIfSmTtiRx indicates the Trail Trace Identifier
         (TTI) for the Section Monitoring (SM) in the received OTU overhead."
    ::= { tmnxOtuIfEntry 15 }

tmnxOtuIfSmTtiExpMode            OBJECT-TYPE
    SYNTAX      TmnxOtuTtiMode
    MAX-ACCESS  read-create
    STATUS      current
    DESCRIPTION
        "The value of tmnxOtuIfSmTtiExpMode specifies the type of expected
         Trail Trace Identifier (TTI) for the Section Monitoring (SM) in the
         OTU overhead.

         Specifying a tmnxOtuIfSmTtiExpMode value of 'auto (0)' along with
         tmnxOtuIfSmTtiExp set with a single octet of '0xFF' will revert the
         SM-TTI to the default which is 'all zeros' in tmnxOtuIfSmTtiExp."
    ::= { tmnxOtuIfEntry 16 }

tmnxOtuIfSmTtiExpCopyRx          OBJECT-TYPE
    SYNTAX      TmnxActionType
    MAX-ACCESS  read-create
    STATUS      current
    DESCRIPTION
        "tmnxOtuIfSmTtiExpCopyRx is used to copy the contents of
         tmnxOtuIfSmTtiRx into tmnxOtuIfSmTtiExp."
    ::= { tmnxOtuIfEntry 17 }

tmnxOtuIfSmTtiExp                OBJECT-TYPE
    SYNTAX      TmnxOtuTtiString (SIZE (0..64))
    MAX-ACCESS  read-create
    STATUS      current
    DESCRIPTION
        "The value of tmnxOtuIfSmTtiExp specifies the Trail Trace Identifier
         (TTI) for the Section Monitoring (SM) that is expected to be received
         in the OTU overhead.

         A mismatch of the received and the expected SM TTI will cause an
         'otuTim' alarm to be raised"
    ::= { tmnxOtuIfEntry 18 }

tmnxOtuIfPmTtiTxMode             OBJECT-TYPE
    SYNTAX      TmnxOtuTtiMode
    MAX-ACCESS  read-create
    STATUS      current
    DESCRIPTION
        "The value of tmnxOtuIfPmTtiTxMode specifies the type of Trail Trace
         Identifier (TTI) for the Path Monitoring (PM) in the OTU overhead.

         Specifying a tmnxOtuIfPmTtiTxMode value of 'auto (0)' along with
         tmnxOtuIfPmTtiTx set with a single octet of '0xFF' will revert the
         PM-TTI to the default:
         '<system-name>/<iom-slot>/<mda-slot>/<port-number>/C<dwdm-channel>'"
    ::= { tmnxOtuIfEntry 19 }

tmnxOtuIfPmTtiTx                 OBJECT-TYPE
    SYNTAX      TmnxOtuTtiString (SIZE (0..64))
    MAX-ACCESS  read-create
    STATUS      current
    DESCRIPTION
        "The value of tmnxOtuIfPmTtiTx specifies the Trail Trace Identifier
         (TTI) for the Path Monitoring (PM) in the OTU overhead. This
         identifier can be a string or a non-printable sequence of bytes.

         Specifying a one octet string with the value '0xFF' along with a
         tmnxOtuIfPmTtiTxMode set to the value of 'auto (0)' will reset the TTI
         to the system generated value."
    ::= { tmnxOtuIfEntry 20 }

tmnxOtuIfPmTtiRx                 OBJECT-TYPE
    SYNTAX      TmnxOtuTtiString (SIZE (0..64))
    MAX-ACCESS  read-only
    STATUS      current
    DESCRIPTION
        "The value of tmnxOtuIfPmTtiRx indicates the Trail Trace Identifier
         (TTI) for the Path Monitoring (PM) in the received OTU overhead."
    ::= { tmnxOtuIfEntry 21 }

tmnxOtuIfPmTtiExpMode            OBJECT-TYPE
    SYNTAX      TmnxOtuTtiMode
    MAX-ACCESS  read-create
    STATUS      current
    DESCRIPTION
        "The value of tmnxOtuIfPmTtiExpMode specifies the type of expected
         Trail Trace Identifier (TTI) for the Path Monitoring (PM) in the OTU
         overhead.

         Specifying a tmnxOtuIfPmTtiExpMode value of 'auto (0)' along with
         tmnxOtuIfPmTtiExp set with a single octet of '0xFF' will revert the
         PM-TTI to the default which is 'all zeros' in tmnxOtuIfPmTtiExp."
    ::= { tmnxOtuIfEntry 22 }

tmnxOtuIfPmTtiExpCopyRx          OBJECT-TYPE
    SYNTAX      TmnxActionType
    MAX-ACCESS  read-create
    STATUS      current
    DESCRIPTION
        "tmnxOtuIfPmTtiExpCopyRx is used to copy the contents of
         tmnxOtuIfPmTtiRx into tmnxOtuIfPmTtiExp."
    ::= { tmnxOtuIfEntry 23 }

tmnxOtuIfPmTtiExp                OBJECT-TYPE
    SYNTAX      TmnxOtuTtiString (SIZE (0..64))
    MAX-ACCESS  read-create
    STATUS      current
    DESCRIPTION
        "The value of tmnxOtuIfPmTtiExp indicates the Trail Trace Identifier
         (TTI) for the Path Monitoring (PM) that is expected to be received in
         the OTU overhead.

         A mismatch of the received and the expected PM TTI will cause an
         'oduTim' alarm to be raised"
    ::= { tmnxOtuIfEntry 24 }

tmnxOtuIfPsiTtiTxMode            OBJECT-TYPE
    SYNTAX      TmnxOtuTtiMode
    MAX-ACCESS  read-create
    STATUS      current
    DESCRIPTION
        "The value of tmnxOtuIfPsiTtiTxMode specifies the type of Trail Trace
         Identifier (TTI) for the Payload Structure Identifier (PSI) in the OTU
         overhead.

         Specifying a tmnxOtuIfPsiTtiTxMode value of 'auto (0)' along with
         tmnxOtuIfPsiTtiTx set with a single octet of '0xFF' will revert the
         PSI-TTI to the default:
         '<system-name>/<iom-slot>/<mda-slot>/<port-number>/C<dwdm-channel>'"
    ::= { tmnxOtuIfEntry 25 }

tmnxOtuIfPsiTtiTx                OBJECT-TYPE
    SYNTAX      TmnxOtuTtiString
    MAX-ACCESS  read-create
    STATUS      current
    DESCRIPTION
        "The value of tmnxOtuIfPsiTtiTx specifies the Trail Trace Identifier
         (TTI) for the Payload Structure Identifier (PSI) in the OTU overhead.
         This identifier can be a string or a non-printable sequence of bytes.

         Specifying a one octet string with the value '0xFF' along with a
         tmnxOtuIfPsiTtiTxMode set to the value of 'auto (0)' will reset the
         PSI Trace to the system generated value."
    ::= { tmnxOtuIfEntry 26 }

tmnxOtuIfPsiTtiRx                OBJECT-TYPE
    SYNTAX      TmnxOtuTtiString
    MAX-ACCESS  read-only
    STATUS      current
    DESCRIPTION
        "The value of tmnxOtuIfPsiTtiRx indicates the Trail Trace Identifier
         (TTI) for the Payload Structure Identifier (PSI) in the received OTU
         overhead."
    ::= { tmnxOtuIfEntry 27 }

tmnxOtuIfPsiTtiExpMode           OBJECT-TYPE
    SYNTAX      TmnxOtuTtiMode
    MAX-ACCESS  read-create
    STATUS      current
    DESCRIPTION
        "The value of tmnxOtuIfPsiTtiExpMode specifies the type of expected
         Trail Trace Identifier (TTI) Payload Structure Identifier (PSI) in the
         OTU overhead.

         Specifying a tmnxOtuIfPsiTtiExpMode value of 'auto (0)' along with
         tmnxOtuIfPsiTtiExp set with a single octet of '0xFF' will revert the
         PSI-TTI to the default which is 'all zeros' in tmnxOtuIfPsiTtiExp."
    ::= { tmnxOtuIfEntry 28 }

tmnxOtuIfPsiTtiExpCopyRx         OBJECT-TYPE
    SYNTAX      TmnxActionType
    MAX-ACCESS  read-create
    STATUS      current
    DESCRIPTION
        "tmnxOtuIfPsiTtiExpCopyRx is used to copy the contents of
         tmnxOtuIfPsiTtiRx into tmnxOtuIfPsiTtiExp."
    ::= { tmnxOtuIfEntry 29 }

tmnxOtuIfPsiTtiExp               OBJECT-TYPE
    SYNTAX      TmnxOtuTtiString (SIZE (0..255))
    MAX-ACCESS  read-create
    STATUS      current
    DESCRIPTION
        "The value of tmnxOtuIfPsiTtiExp indicates the Trail Trace Identifier
         (TTI) for the Payload Structure Identifier (PSI) that is expected to
         be received in the OTU overhead.

         A mismatch of the received and the expected PSI Trace will cause an
         'opuTim' alarm to be raised"
    ::= { tmnxOtuIfEntry 30 }

tmnxOtuIfPsiPayloadTypeTx        OBJECT-TYPE
    SYNTAX      TmnxOtuPsiPayloadType
    MAX-ACCESS  read-create
    STATUS      current
    DESCRIPTION
        "The value of tmnxOtuIfPsiPayloadTypeTx specifies the Payload Type in
         the transmitted OPU PSI overhead.

         Specifying a value 'auto (0)' will provision the standard defined
         payload type for the current OTU mode of operation."
    ::= { tmnxOtuIfEntry 31 }

tmnxOtuIfPsiPayloadTypeRx        OBJECT-TYPE
    SYNTAX      TmnxOtuPsiPayloadType
    MAX-ACCESS  read-only
    STATUS      current
    DESCRIPTION
        "The value of tmnxOtuIfPsiPayloadTypeRx indicates the Payload Type in
         the received OPU PSI overhead."
    ::= { tmnxOtuIfEntry 32 }

tmnxOtuIfPsiPayloadTypeExp       OBJECT-TYPE
    SYNTAX      TmnxOtuPsiPayloadType
    MAX-ACCESS  read-create
    STATUS      current
    DESCRIPTION
        "The value of tmnxOtuIfPsiPayloadTypeExp indicates the Payload Type
         that is expected to be received in the OPU PSI overhead.

         Specifying a value 'auto (0)' will provision the standard defined
         payload type for the current OTU mode of operation.

         A mismatch of the received and the expected Payload type will cause an
         'opuPlm' alarm to be raised"
    ::= { tmnxOtuIfEntry 33 }

tmnxOtuIfGfpMappingEnable        OBJECT-TYPE
    SYNTAX      TruthValue
    MAX-ACCESS  not-accessible
    STATUS      current
    DESCRIPTION
        "The value of tmnxOtuIfGfpMappingEnable specifies whether or not the
         GFP mapping mode of transporting 10GbE is enabled."
    DEFVAL      { false }
    ::= { tmnxOtuIfEntry 34 }

tmnxOtuIfAsyncMappingEnable      OBJECT-TYPE
    SYNTAX      TruthValue
    MAX-ACCESS  read-create
    STATUS      current
    DESCRIPTION
        "The value of tmnxOtuIfAsyncMappingEnable specifies whether or not the
         Asynchronous mapping mode of transporting the OTU client is enabled.

         When this value is set to false, the OTU client is client is mapped
         Synchronously."
    DEFVAL      { false }
    ::= { tmnxOtuIfEntry 35 }

tmnxOtuIfSmTimReaction           OBJECT-TYPE
    SYNTAX      TmnxOtuTimReaction
    MAX-ACCESS  read-create
    STATUS      current
    DESCRIPTION
        "The value of tmnxOtuIfSmTimReaction specifies the reaction that should
         be taken in the event of a Section Monitor Trace Identifier Mismatch.

         Specifying a value 'none (0)' indicates that no reaction should occur
         and therefore the ingress data will be passed through in the event of
         a Section Monitor Trace Identifier mismatch.

         Specifying a value 'squelch-rx (1)' indicates that the incoming data
         will be squelched and therefore the ingress data will be blocked with
         a maintenance signal in the event of a Section Monitor Trace
         Identifier mismatch."
    DEFVAL      { none }
    ::= { tmnxOtuIfEntry 36 }

tmnxOtuIfPmTimReaction           OBJECT-TYPE
    SYNTAX      TmnxOtuTimReaction
    MAX-ACCESS  read-create
    STATUS      current
    DESCRIPTION
        "The value of tmnxOtuIfPmTimReaction specifies the reaction that should
         be taken in the event of a Path Monitor Trace Identifier Mismatch.

         Specifying a value 'none (0)' indicates that no reaction should occur
         and therefore the ingress data will be passed through in the event of
         a Path Monitor Trace Identifier mismatch.

         Specifying a value 'squelch-rx (1)' indicates that the incoming data
         will be squelched and therefore the ingress data will be blocked with
         a maintenance signal in the event of a Path Monitor Trace Identifier
         mismatch."
    DEFVAL      { none }
    ::= { tmnxOtuIfEntry 37 }

tmnxOtuIfPsiTimReaction          OBJECT-TYPE
    SYNTAX      TmnxOtuTimReaction
    MAX-ACCESS  read-create
    STATUS      current
    DESCRIPTION
        "The value of tmnxOtuIfPsiTimReaction specifies the reaction that
         should be taken in the event of a Payload Structure Identifier Trace
         Mismatch.

         Specifying a value 'none (0)' indicates that no reaction should occur
         and therefore the ingress data will be passed through in the event of
         a Payload Structure Identifier Trace mismatch.

         Specifying a value 'squelch-rx (1)' indicates that the incoming data
         will be squelched and therefore the ingress data will be blocked with
         a maintenance signal in the event of a Payload Structure Identifier
         Trace mismatch."
    DEFVAL      { none }
    ::= { tmnxOtuIfEntry 38 }

tmnxOtuIfPsiPlmReaction          OBJECT-TYPE
    SYNTAX      TmnxOtuTimReaction
    MAX-ACCESS  read-create
    STATUS      current
    DESCRIPTION
        "The value of tmnxOtuIfPsiPlmReaction specifies the reaction that
         should be taken in the event of a Payload Type mismatch.

         Specifying a value 'none (0)' indicates that no reaction should occur
         and therefore the ingress data will be passed through in the event of
         a Payload Type mismatch.

         Specifying a value 'squelch-rx (1)' indicates that the incoming data
         will be squelched and therefore the ingress data will be blocked with
         a maintenance signal in the event of a Payload Type mismatch."
    DEFVAL      { none }
    ::= { tmnxOtuIfEntry 39 }

tmnxOtuIfFineGrBerTable          OBJECT-TYPE
    SYNTAX      SEQUENCE OF TmnxOtuIfFineGrBerEntry
    MAX-ACCESS  not-accessible
    STATUS      current
    DESCRIPTION
        "The tmnxOtuIfFineGrBerTable has a row for each interface with OTU
         encapsulation and contains configuration parameters related to fine
         granularity pre-FEC BER SD and SF thresholds."
    ::= { tmnxOtuConfigurations 2 }

tmnxOtuIfFineGrBerEntry          OBJECT-TYPE
    SYNTAX      TmnxOtuIfFineGrBerEntry
    MAX-ACCESS  not-accessible
    STATUS      current
    DESCRIPTION
        "The tmnxOtuIfFineGrBerEntry contains fine granularity pre-FEC BER SD
         and SF threshold information for an individual OTU encapsulated
         physical interface.

         For the coefficient MIB attributes, 10 represents 1.0 and 99
         represents 9.9. The combination of the SF/SD threshold coefficient and
         exponent form a number: coefficient x 10^-exponent; therefore, by
         example, a tmnxOtuIfFineGrBerSfThresh value of 4 and a
         tmnxOtuIfFineGrBerSfThrCoef value of 32 forms 3.2 x 10^-4 or 3.2E-04
         in scientific notation.

         For a set request, the combination of the coefficient and exponent for
         an SD raise threshold must be a lower value than for the SF raise
         threshold; otherwise, the set request will fail with error code
         inconsistentValue.

         For a set request, the combination of the coefficient and exponent for
         a clear threshold must be a lower value than for the raise threshold;
         otherwise, the set request will fail with error code
         inconsistentValue.

         The row exists only if the associated tmnxOtuIfEntry is active."
    AUGMENTS    { tmnxOtuIfEntry }
    ::= { tmnxOtuIfFineGrBerTable 1 }

TmnxOtuIfFineGrBerEntry          ::= SEQUENCE
{
    tmnxOtuIfFineGrBerSupported      TruthValue,
    tmnxOtuIfFineGrBerSfThresh       Unsigned32,
    tmnxOtuIfFineGrBerSdThresh       Unsigned32,
    tmnxOtuIfFineGrBerSfThrCoef      Unsigned32,
    tmnxOtuIfFineGrBerSdThrCoef      Unsigned32,
    tmnxOtuIfFineGrBerSfThreshClr    Unsigned32,
    tmnxOtuIfFineGrBerSdThreshClr    Unsigned32,
    tmnxOtuIfFineGrBerSfThrClrCoef   Unsigned32,
    tmnxOtuIfFineGrBerSdThrClrCoef   Unsigned32
}

tmnxOtuIfFineGrBerSupported      OBJECT-TYPE
    SYNTAX      TruthValue
    MAX-ACCESS  read-only
    STATUS      current
    DESCRIPTION
        "The value of tmnxOtuIfFineGrBerSupported indicates whether or not fine
         granularity BER thresholds are supported on this OTU encapsulated
         physical interface."
    ::= { tmnxOtuIfFineGrBerEntry 1 }

tmnxOtuIfFineGrBerSfThresh       OBJECT-TYPE
    SYNTAX      Unsigned32 (3..8)
    UNITS       "error bits in 1/10e-n bits received"
    MAX-ACCESS  read-write
    STATUS      current
    DESCRIPTION
        "The value of tmnxOtuIfFineGrBerSfThresh specifies the BER threshold
         used to determine when to raise fecSf alarms (notification
         tmnxOtuIfAlarmNotification).

         Bit error rate computed must reach/exceed the threshold value over a
         predefined period of time (window size) for the alarms to be raised:

         BER        | Window
         Threshold  | Length (ms)
         --------------------------
         3          | 8
         4          | 8
         5          | 8
         6          | 13
         7          | 100
         8          | 333
         9          | 1660"
    DEFVAL      { 5 }
    ::= { tmnxOtuIfFineGrBerEntry 2 }

tmnxOtuIfFineGrBerSdThresh       OBJECT-TYPE
    SYNTAX      Unsigned32 (3..9)
    UNITS       "error bits in 1/10e-n bits received"
    MAX-ACCESS  read-write
    STATUS      current
    DESCRIPTION
        "The value of tmnxOtuIfFineGrBerSdThresh specifies the BER threshold
         used to determine when to raise fecSd alarms (notification
         tmnxOtuIfAlarmNotification).

         Bit error rate computed must reach/exceed the threshold value over a
         predefined period of time (window size) for the alarms to be raised:

         BER        | Window
         Threshold  | Length (ms)
         --------------------------
         3          | 8
         4          | 8
         5          | 8
         6          | 13
         7          | 100
         8          | 333
         9          | 1660"
    DEFVAL      { 7 }
    ::= { tmnxOtuIfFineGrBerEntry 3 }

tmnxOtuIfFineGrBerSfThrCoef      OBJECT-TYPE
    SYNTAX      Unsigned32 (10..99)
    UNITS       "tenths"
    MAX-ACCESS  read-write
    STATUS      current
    DESCRIPTION
        "The value of tmnxOtuIfFineGrBerSfThrCoef specifies the factor used to
         fine tune the SF BER threshold (tmnxOtuIfFineGrBerSfThresh) for SF
         alarm raising."
    DEFVAL      { 10 }
    ::= { tmnxOtuIfFineGrBerEntry 4 }

tmnxOtuIfFineGrBerSdThrCoef      OBJECT-TYPE
    SYNTAX      Unsigned32 (10..99)
    UNITS       "tenths"
    MAX-ACCESS  read-write
    STATUS      current
    DESCRIPTION
        "The value of tmnxOtuIfFineGrBerSdThrCoef specifies the factor used to
         fine tune the SD BER threshold (tmnxOtuIfFineGrBerSdThresh) for SD
         alarm raising."
    DEFVAL      { 10 }
    ::= { tmnxOtuIfFineGrBerEntry 5 }

tmnxOtuIfFineGrBerSfThreshClr    OBJECT-TYPE
    SYNTAX      Unsigned32 (3..9)
    UNITS       "error bits in 1/10e-n bits received"
    MAX-ACCESS  read-write
    STATUS      current
    DESCRIPTION
        "The value of tmnxOtuIfFineGrBerSfThreshClr specifies the BER threshold
         used to determine when to clear fecSf alarms (notification
         tmnxOtuIfAlarmNotification)."
    DEFVAL      { 6 }
    ::= { tmnxOtuIfFineGrBerEntry 6 }

tmnxOtuIfFineGrBerSdThreshClr    OBJECT-TYPE
    SYNTAX      Unsigned32 (3..10)
    UNITS       "error bits in 1/10e-n bits received"
    MAX-ACCESS  read-write
    STATUS      current
    DESCRIPTION
        "The value of tmnxOtuIfFineGrBerSdThreshClr specifies the BER threshold
         used to determine when to clear fecSd alarms (notification
         tmnxOtuIfAlarmNotification)."
    DEFVAL      { 8 }
    ::= { tmnxOtuIfFineGrBerEntry 7 }

tmnxOtuIfFineGrBerSfThrClrCoef   OBJECT-TYPE
    SYNTAX      Unsigned32 (10..99)
    UNITS       "tenths"
    MAX-ACCESS  read-write
    STATUS      current
    DESCRIPTION
        "The value of tmnxOtuIfFineGrBerSfThrClrCoef specifies the factor used
         to fine tune the SF BER threshold (tmnxOtuIfFineGrBerSfThreshClr) for
         SF alarm clearing."
    DEFVAL      { 10 }
    ::= { tmnxOtuIfFineGrBerEntry 8 }

tmnxOtuIfFineGrBerSdThrClrCoef   OBJECT-TYPE
    SYNTAX      Unsigned32 (10..99)
    UNITS       "tenths"
    MAX-ACCESS  read-write
    STATUS      current
    DESCRIPTION
        "The value of tmnxOtuIfFineGrBerSdThrClrCoef specifies the factor used
         to fine tune the SD BER threshold (tmnxOtuIfFineGrBerSdThreshClr) for
         SD alarm clearing."
    DEFVAL      { 10 }
    ::= { tmnxOtuIfFineGrBerEntry 9 }

tmnxOtuStatistics                OBJECT IDENTIFIER ::= { tmnxOtuObjs 2 }

tmnxOtuIfRawStatsTable           OBJECT-TYPE
    SYNTAX      SEQUENCE OF TmnxOtuIfRawStatsEntry
    MAX-ACCESS  not-accessible
    STATUS      current
    DESCRIPTION
        "The tmnxOtuIfRawStatsTable consists of the raw statistics associated
         with the OTU interfaces contained in the tmnxOtuIfTable."
    ::= { tmnxOtuStatistics 1 }

tmnxOtuIfRawStatsEntry           OBJECT-TYPE
    SYNTAX      TmnxOtuIfRawStatsEntry
    MAX-ACCESS  not-accessible
    STATUS      current
    DESCRIPTION
        "The tmnxOtuIfRawStatsEntry stores the statistics for an individual OTU
         interface. tmnxOtuIfRawStatsEntry rows are created and destroyed by
         the system when rows are added or removed in the tmnxOtuIfTable."
    INDEX       { ifIndex }
    ::= { tmnxOtuIfRawStatsTable 1 }

TmnxOtuIfRawStatsEntry           ::= SEQUENCE
{
    tmnxOtuIfRawStatsFECCorrZeros    Counter32,
    tmnxOtuIfRawStatsOFFECCorrZeros  Counter32,
    tmnxOtuIfRawStatsHCFECCorrZeros  Counter64,
    tmnxOtuIfRawStatsFECCorrOnes     Counter32,
    tmnxOtuIfRawStatsOFFECCorrOnes   Counter32,
    tmnxOtuIfRawStatsHCFECCorrOnes   Counter64,
    tmnxOtuIfRawStatsFECUncorrSR     Counter32,
    tmnxOtuIfRawStatsOFFECUncorrSR   Counter32,
    tmnxOtuIfRawStatsHCFECUncorrSR   Counter64,
    tmnxOtuIfRawStatsFECSES          Counter32,
    tmnxOtuIfRawStatsSMBIP8          Counter32,
    tmnxOtuIfRawStatsOFSMBIP8        Counter32,
    tmnxOtuIfRawStatsHCSMBIP8        Counter64,
    tmnxOtuIfRawStatsSMBEI           Counter32,
    tmnxOtuIfRawStatsOFSMBEI         Counter32,
    tmnxOtuIfRawStatsHCSMBEI         Counter64,
    tmnxOtuIfRawStatsSMSES           Counter32,
    tmnxOtuIfRawStatsPMBIP8          Counter32,
    tmnxOtuIfRawStatsOFPMBIP8        Counter32,
    tmnxOtuIfRawStatsHCPMBIP8        Counter64,
    tmnxOtuIfRawStatsPMBEI           Counter32,
    tmnxOtuIfRawStatsOFPMBEI         Counter32,
    tmnxOtuIfRawStatsHCPMBEI         Counter64,
    tmnxOtuIfRawStatsPMSES           Counter32,
    tmnxOtuIfRawStatsFECES           Counter32,
    tmnxOtuIfRawStatsFECUAS          Counter32,
    tmnxOtuIfRawStatsSMES            Counter32,
    tmnxOtuIfRawStatsSMUAS           Counter32,
    tmnxOtuIfRawStatsPMES            Counter32,
    tmnxOtuIfRawStatsPMUAS           Counter32,
    tmnxOtuIfRawStatsNPJ             Counter32,
    tmnxOtuIfRawStatsPPJ             Counter32,
    tmnxOtuIfRawStatsElapsedSec      Counter32
}

tmnxOtuIfRawStatsFECCorrZeros    OBJECT-TYPE
    SYNTAX      Counter32
    UNITS       "bits"
    MAX-ACCESS  read-only
    STATUS      current
    DESCRIPTION
        "The value of tmnxOtuIfRawStatsFECCorrZeros indicates the number of
         Forward Error Correction (FEC) corrected zeros."
    ::= { tmnxOtuIfRawStatsEntry 1 }

tmnxOtuIfRawStatsOFFECCorrZeros  OBJECT-TYPE
    SYNTAX      Counter32
    UNITS       "count"
    MAX-ACCESS  read-only
    STATUS      current
    DESCRIPTION
        "The value of tmnxOtuIfRawStatsOFFECCorrZeros indicates the number of
         times the tmnxOtuIfRawStatsFECCorrZeros overflowed."
    ::= { tmnxOtuIfRawStatsEntry 2 }

tmnxOtuIfRawStatsHCFECCorrZeros  OBJECT-TYPE
    SYNTAX      Counter64
    UNITS       "bits"
    MAX-ACCESS  read-only
    STATUS      current
    DESCRIPTION
        "The value of tmnxOtuIfRawStatsHCFECCorrZeros indicates the High
         Capacity number of Forward Error Correction (FEC) corrected zeros."
    ::= { tmnxOtuIfRawStatsEntry 3 }

tmnxOtuIfRawStatsFECCorrOnes     OBJECT-TYPE
    SYNTAX      Counter32
    UNITS       "bits"
    MAX-ACCESS  read-only
    STATUS      current
    DESCRIPTION
        "The value of tmnxOtuIfRawStatsFECCorrOnes indicates the number of
         Forward Error Correction (FEC) corrected ones."
    ::= { tmnxOtuIfRawStatsEntry 4 }

tmnxOtuIfRawStatsOFFECCorrOnes   OBJECT-TYPE
    SYNTAX      Counter32
    UNITS       "count"
    MAX-ACCESS  read-only
    STATUS      current
    DESCRIPTION
        "The value of tmnxOtuIfRawStatsOFFECCorrOnes indicates the number of
         times the tmnxOtuIfRawStatsFECCorrOnes overflowed."
    ::= { tmnxOtuIfRawStatsEntry 5 }

tmnxOtuIfRawStatsHCFECCorrOnes   OBJECT-TYPE
    SYNTAX      Counter64
    UNITS       "bits"
    MAX-ACCESS  read-only
    STATUS      current
    DESCRIPTION
        "The value of tmnxOtuIfRawStatsHCFECCorrOnes indicates the High
         Capacity number of Forward Error Correction (FEC) corrected ones."
    ::= { tmnxOtuIfRawStatsEntry 6 }

tmnxOtuIfRawStatsFECUncorrSR     OBJECT-TYPE
    SYNTAX      Counter32
    UNITS       "Sub-Rows"
    MAX-ACCESS  read-only
    STATUS      current
    DESCRIPTION
        "The value of tmnxOtuIfRawStatsFECUncorrSR indicates the number of
         Forward Error Correction (FEC) Uncorrectable Sub-Rows."
    ::= { tmnxOtuIfRawStatsEntry 7 }

tmnxOtuIfRawStatsOFFECUncorrSR   OBJECT-TYPE
    SYNTAX      Counter32
    UNITS       "count"
    MAX-ACCESS  read-only
    STATUS      current
    DESCRIPTION
        "The value of tmnxOtuIfRawStatsOFFECUncorrSR indicates the number of
         times the tmnxOtuIfRawStatsFECUncorrSR overflowed."
    ::= { tmnxOtuIfRawStatsEntry 8 }

tmnxOtuIfRawStatsHCFECUncorrSR   OBJECT-TYPE
    SYNTAX      Counter64
    UNITS       "Sub-Rows"
    MAX-ACCESS  read-only
    STATUS      current
    DESCRIPTION
        "The value of tmnxOtuIfRawStatsHCFECUncorrSR indicates the High
         Capacity number of Forward Error Correction (FEC) Uncorrectable
         Sub-Rows."
    ::= { tmnxOtuIfRawStatsEntry 9 }

tmnxOtuIfRawStatsFECSES          OBJECT-TYPE
    SYNTAX      Counter32
    UNITS       "seconds"
    MAX-ACCESS  read-only
    STATUS      current
    DESCRIPTION
        "The value of tmnxOtuIfRawStatsFECSES indicates the number of Forward
         Error Correction (FEC) Severely Errors Seconds (SES)."
    ::= { tmnxOtuIfRawStatsEntry 10 }

tmnxOtuIfRawStatsSMBIP8          OBJECT-TYPE
    SYNTAX      Counter32
    UNITS       "bits"
    MAX-ACCESS  read-only
    STATUS      current
    DESCRIPTION
        "The value of tmnxOtuIfRawStatsSMBIP8 indicates the number of Section
         Monitoring (SM) BIP8 errors."
    ::= { tmnxOtuIfRawStatsEntry 11 }

tmnxOtuIfRawStatsOFSMBIP8        OBJECT-TYPE
    SYNTAX      Counter32
    UNITS       "count"
    MAX-ACCESS  read-only
    STATUS      current
    DESCRIPTION
        "The value of tmnxOtuIfRawStatsOFSMBIP8 indicates the number of times
         the tmnxOtuIfRawStatsSMBIP8 overflowed."
    ::= { tmnxOtuIfRawStatsEntry 12 }

tmnxOtuIfRawStatsHCSMBIP8        OBJECT-TYPE
    SYNTAX      Counter64
    UNITS       "bits"
    MAX-ACCESS  read-only
    STATUS      current
    DESCRIPTION
        "The value of tmnxOtuIfRawStatsHCSMBIP8 indicates the High Capacity
         number of Section Monitoring (SM) BIP8 errors."
    ::= { tmnxOtuIfRawStatsEntry 13 }

tmnxOtuIfRawStatsSMBEI           OBJECT-TYPE
    SYNTAX      Counter32
    UNITS       "bits"
    MAX-ACCESS  read-only
    STATUS      current
    DESCRIPTION
        "The value of tmnxOtuIfRawStatsSMBEI indicates the number of Section
         Monitoring (SM) Backward Error Indication (BEI) errors."
    ::= { tmnxOtuIfRawStatsEntry 14 }

tmnxOtuIfRawStatsOFSMBEI         OBJECT-TYPE
    SYNTAX      Counter32
    UNITS       "count"
    MAX-ACCESS  read-only
    STATUS      current
    DESCRIPTION
        "The value of tmnxOtuIfRawStatsOFSMBEI indicates the number of times
         the tmnxOtuIfRawStatsSMBEI overflowed."
    ::= { tmnxOtuIfRawStatsEntry 15 }

tmnxOtuIfRawStatsHCSMBEI         OBJECT-TYPE
    SYNTAX      Counter64
    UNITS       "bits"
    MAX-ACCESS  read-only
    STATUS      current
    DESCRIPTION
        "The value of tmnxOtuIfRawStatsHCSMBEI indicates the High Capacity
         number of Section Monitoring (SM) Backward Error Indication (BEI)
         errors."
    ::= { tmnxOtuIfRawStatsEntry 16 }

tmnxOtuIfRawStatsSMSES           OBJECT-TYPE
    SYNTAX      Counter32
    UNITS       "seconds"
    MAX-ACCESS  read-only
    STATUS      current
    DESCRIPTION
        "The value of tmnxOtuIfRawStatsSMSES indicates the number of Section
         Monitoring (SM) Severely Errored Seconds (SES)."
    ::= { tmnxOtuIfRawStatsEntry 17 }

tmnxOtuIfRawStatsPMBIP8          OBJECT-TYPE
    SYNTAX      Counter32
    UNITS       "bits"
    MAX-ACCESS  read-only
    STATUS      current
    DESCRIPTION
        "The value of tmnxOtuIfRawStatsPMBIP8 indicates the number of Path
         Monitoring (PM) BIP8 errors."
    ::= { tmnxOtuIfRawStatsEntry 18 }

tmnxOtuIfRawStatsOFPMBIP8        OBJECT-TYPE
    SYNTAX      Counter32
    UNITS       "count"
    MAX-ACCESS  read-only
    STATUS      current
    DESCRIPTION
        "The value of tmnxOtuIfRawStatsOFPMBIP8 indicates the number of times
         the tmnxOtuIfRawStatsPMBIP8 overflowed."
    ::= { tmnxOtuIfRawStatsEntry 19 }

tmnxOtuIfRawStatsHCPMBIP8        OBJECT-TYPE
    SYNTAX      Counter64
    UNITS       "bits"
    MAX-ACCESS  read-only
    STATUS      current
    DESCRIPTION
        "The value of tmnxOtuIfRawStatsHCPMBIP8 indicates the High Capacity
         number of Path Monitoring (PM) BIP8 errors."
    ::= { tmnxOtuIfRawStatsEntry 20 }

tmnxOtuIfRawStatsPMBEI           OBJECT-TYPE
    SYNTAX      Counter32
    UNITS       "bits"
    MAX-ACCESS  read-only
    STATUS      current
    DESCRIPTION
        "The value of tmnxOtuIfRawStatsPMBEI indicates the number of Path
         Monitoring (PM) Backward Error Indication (BEI) errors."
    ::= { tmnxOtuIfRawStatsEntry 21 }

tmnxOtuIfRawStatsOFPMBEI         OBJECT-TYPE
    SYNTAX      Counter32
    UNITS       "count"
    MAX-ACCESS  read-only
    STATUS      current
    DESCRIPTION
        "The value of tmnxOtuIfRawStatsOFPMBEI indicates the number of times
         tmnxOtuIfRawStatsPMBEI overflowed."
    ::= { tmnxOtuIfRawStatsEntry 22 }

tmnxOtuIfRawStatsHCPMBEI         OBJECT-TYPE
    SYNTAX      Counter64
    UNITS       "bits"
    MAX-ACCESS  read-only
    STATUS      current
    DESCRIPTION
        "The value of tmnxOtuIfRawStatsHCPMBEI indicates the High Capacity
         number of Path Monitoring (PM) Backward Error Indication (BEI) errors."
    ::= { tmnxOtuIfRawStatsEntry 23 }

tmnxOtuIfRawStatsPMSES           OBJECT-TYPE
    SYNTAX      Counter32
    UNITS       "seconds"
    MAX-ACCESS  read-only
    STATUS      current
    DESCRIPTION
        "The value of tmnxOtuIfRawStatsPMSES indicates the number of Path
         Monitoring (PM) Severely Errored Seconds (SES)."
    ::= { tmnxOtuIfRawStatsEntry 24 }

tmnxOtuIfRawStatsFECES           OBJECT-TYPE
    SYNTAX      Counter32
    UNITS       "seconds"
    MAX-ACCESS  read-only
    STATUS      current
    DESCRIPTION
        "The value of tmnxOtuIfRawStatsFECES indicates the number of Forward
         Error Correction (FEC) Errors Seconds (ES)."
    ::= { tmnxOtuIfRawStatsEntry 25 }

tmnxOtuIfRawStatsFECUAS          OBJECT-TYPE
    SYNTAX      Counter32
    UNITS       "seconds"
    MAX-ACCESS  read-only
    STATUS      current
    DESCRIPTION
        "The value of tmnxOtuIfRawStatsFECUAS indicates the number of Forward
         Error Correction (FEC) Unavailable Seconds (UAS)."
    ::= { tmnxOtuIfRawStatsEntry 26 }

tmnxOtuIfRawStatsSMES            OBJECT-TYPE
    SYNTAX      Counter32
    UNITS       "seconds"
    MAX-ACCESS  read-only
    STATUS      current
    DESCRIPTION
        "The value of tmnxOtuIfRawStatsSMES indicates the number of Section
         Monitoring (SM) Errored Seconds (ES)."
    ::= { tmnxOtuIfRawStatsEntry 27 }

tmnxOtuIfRawStatsSMUAS           OBJECT-TYPE
    SYNTAX      Counter32
    UNITS       "seconds"
    MAX-ACCESS  read-only
    STATUS      current
    DESCRIPTION
        "The value of tmnxOtuIfRawStatsSMUAS indicates the number of Section
         Monitoring (SM) Unavailable Seconds (UAS)."
    ::= { tmnxOtuIfRawStatsEntry 28 }

tmnxOtuIfRawStatsPMES            OBJECT-TYPE
    SYNTAX      Counter32
    UNITS       "seconds"
    MAX-ACCESS  read-only
    STATUS      current
    DESCRIPTION
        "The value of tmnxOtuIfRawStatsPMES indicates the number of Path
         Monitoring (PM) Errored Seconds (ES)."
    ::= { tmnxOtuIfRawStatsEntry 29 }

tmnxOtuIfRawStatsPMUAS           OBJECT-TYPE
    SYNTAX      Counter32
    UNITS       "seconds"
    MAX-ACCESS  read-only
    STATUS      current
    DESCRIPTION
        "The value of tmnxOtuIfRawStatsPMUAS indicates the number of Path
         Monitoring (PM) Unavailable Seconds (UAS)."
    ::= { tmnxOtuIfRawStatsEntry 30 }

tmnxOtuIfRawStatsNPJ             OBJECT-TYPE
    SYNTAX      Counter32
    UNITS       "count"
    MAX-ACCESS  read-only
    STATUS      current
    DESCRIPTION
        "The value of tmnxOtuIfRawStatsNPJ indicates the number of Negative
         Pointer justifications that occurred during the asynchronous demapping
         of the received payload inside the OTU frame."
    ::= { tmnxOtuIfRawStatsEntry 31 }

tmnxOtuIfRawStatsPPJ             OBJECT-TYPE
    SYNTAX      Counter32
    UNITS       "count"
    MAX-ACCESS  read-only
    STATUS      current
    DESCRIPTION
        "The value of tmnxOtuIfRawStatsPPJ indicates the number of Positive
         Pointer justifications that occurred during the asynchronous demapping
         of the received payload inside the OTU frame."
    ::= { tmnxOtuIfRawStatsEntry 32 }

tmnxOtuIfRawStatsElapsedSec      OBJECT-TYPE
    SYNTAX      Counter32
    UNITS       "seconds"
    MAX-ACCESS  read-only
    STATUS      current
    DESCRIPTION
        "The value of tmnxOtuIfRawStatsElapsedSec indicates the number of
         Elapsed seconds since the last OTU raw statistics clearing."
    ::= { tmnxOtuIfRawStatsEntry 33 }

tmnxOtuIfIntervalStatsTable      OBJECT-TYPE
    SYNTAX      SEQUENCE OF TmnxOtuIfIntervalStatsEntry
    MAX-ACCESS  not-accessible
    STATUS      current
    DESCRIPTION
        "The tmnxOtuIfIntervalStatsTable consists of the statistic elements
         associated with the OTU interfaces contained in the tmnxOtuIfTable."
    ::= { tmnxOtuStatistics 2 }

tmnxOtuIfIntervalStatsEntry      OBJECT-TYPE
    SYNTAX      TmnxOtuIfIntervalStatsEntry
    MAX-ACCESS  not-accessible
    STATUS      current
    DESCRIPTION
        "The tmnxOtuIfIntervalStatsEntry stores the statistics for an
         individual OTU interface per row. tmnxOtuIfIntervalStatsEntry objects
         are created and destroyed by the system when rows are added or removed
         in the tmnxOtuIfTable."
    INDEX       {
        ifIndex,
        tmnxOtuIfIntvlStatsIndex
    }
    ::= { tmnxOtuIfIntervalStatsTable 1 }

TmnxOtuIfIntervalStatsEntry      ::= SEQUENCE
{
    tmnxOtuIfIntvlStatsIndex         Unsigned32,
    tmnxOtuIfIntvlStatsIsValid       TruthValue,
    tmnxOtuIfIntvlStatsFECCorrZeros  Counter32,
    tmnxOtuIfIntvlStatsFECCorrOnes   Counter32,
    tmnxOtuIfIntvlStatsFECUncorrSR   Counter32,
    tmnxOtuIfIntvlStatsFECSES        Counter32,
    tmnxOtuIfIntvlStatsSMBIP8        Counter32,
    tmnxOtuIfIntvlStatsSMBEI         Counter32,
    tmnxOtuIfIntvlStatsSMSES         Counter32,
    tmnxOtuIfIntvlStatsPMBIP8        Counter32,
    tmnxOtuIfIntvlStatsPMBEI         Counter32,
    tmnxOtuIfIntvlStatsPMSES         Counter32,
    tmnxOtuIfIntvlStatsFECES         Counter32,
    tmnxOtuIfIntvlStatsFECUAS        Counter32,
    tmnxOtuIfIntvlStatsSMES          Counter32,
    tmnxOtuIfIntvlStatsSMUAS         Counter32,
    tmnxOtuIfIntvlStatsPMES          Counter32,
    tmnxOtuIfIntvlStatsPMUAS         Counter32,
    tmnxOtuIfIntvlStatsNPJ           Counter32,
    tmnxOtuIfIntvlStatsPPJ           Counter32,
    tmnxOtuIfIntvlStatsElapsedSec    Counter32
}

tmnxOtuIfIntvlStatsIndex         OBJECT-TYPE
    SYNTAX      Unsigned32 (0 | 1..96)
    MAX-ACCESS  not-accessible
    STATUS      current
    DESCRIPTION
        "The tmnxOtuIfIntvlStatsIndex specifies the 15 minute statistic
         snap-shot for the OTU interface. The interval index value of 0
         specifies the current raw 15 minute statistic window. The value of one
         indicates the most recently completed 15 minute interval statistics
         snap-shot. The interval identified by N is the interval immediately
         preceding the one identified by N-1."
    ::= { tmnxOtuIfIntervalStatsEntry 1 }

tmnxOtuIfIntvlStatsIsValid       OBJECT-TYPE
    SYNTAX      TruthValue
    MAX-ACCESS  read-only
    STATUS      current
    DESCRIPTION
        "The value of tmnxOtuIfIntvlStatsIsValid indicates whether or not the
         current statistics interval is valid.

         The raw interval (tmnxOtuIfIntvlStatsIndex set to 0) is always false."
    ::= { tmnxOtuIfIntervalStatsEntry 2 }

tmnxOtuIfIntvlStatsFECCorrZeros  OBJECT-TYPE
    SYNTAX      Counter32
    UNITS       "bits"
    MAX-ACCESS  read-only
    STATUS      current
    DESCRIPTION
        "The value of tmnxOtuIfIntvlStatsFECCorrZeros indicates the number of
         Forward Error Correction (FEC) corrected zeros."
    ::= { tmnxOtuIfIntervalStatsEntry 3 }

tmnxOtuIfIntvlStatsFECCorrOnes   OBJECT-TYPE
    SYNTAX      Counter32
    UNITS       "bits"
    MAX-ACCESS  read-only
    STATUS      current
    DESCRIPTION
        "The value of tmnxOtuIfIntvlStatsFECCorrOnes indicates the number of
         Forward Error Correction (FEC) corrected ones."
    ::= { tmnxOtuIfIntervalStatsEntry 4 }

tmnxOtuIfIntvlStatsFECUncorrSR   OBJECT-TYPE
    SYNTAX      Counter32
    UNITS       "Sub-Rows"
    MAX-ACCESS  read-only
    STATUS      current
    DESCRIPTION
        "The value of tmnxOtuIfIntvlStatsFECUncorrSR indicates the number of
         Forward Error Correction (FEC) Uncorrectable Sub-Rows."
    ::= { tmnxOtuIfIntervalStatsEntry 5 }

tmnxOtuIfIntvlStatsFECSES        OBJECT-TYPE
    SYNTAX      Counter32
    UNITS       "seconds"
    MAX-ACCESS  read-only
    STATUS      current
    DESCRIPTION
        "The value of tmnxOtuIfIntvlStatsFECSES indicates the number of Forward
         Error Correction (FEC) Severely Errors Seconds (SES)."
    ::= { tmnxOtuIfIntervalStatsEntry 6 }

tmnxOtuIfIntvlStatsSMBIP8        OBJECT-TYPE
    SYNTAX      Counter32
    UNITS       "bits"
    MAX-ACCESS  read-only
    STATUS      current
    DESCRIPTION
        "The value of tmnxOtuIfIntvlStatsSMBIP8 indicates the number of Section
         Monitoring (SM) BIP8 errors."
    ::= { tmnxOtuIfIntervalStatsEntry 7 }

tmnxOtuIfIntvlStatsSMBEI         OBJECT-TYPE
    SYNTAX      Counter32
    UNITS       "bits"
    MAX-ACCESS  read-only
    STATUS      current
    DESCRIPTION
        "The value of tmnxOtuIfIntvlStatsSMBEI indicates the number of Section
         Monitoring (SM) Backward Error Indication (BEI) errors."
    ::= { tmnxOtuIfIntervalStatsEntry 8 }

tmnxOtuIfIntvlStatsSMSES         OBJECT-TYPE
    SYNTAX      Counter32
    UNITS       "seconds"
    MAX-ACCESS  read-only
    STATUS      current
    DESCRIPTION
        "The value of tmnxOtuIfIntvlStatsSMSES indicates the number of Section
         Monitoring (SM) Severely Errored Seconds (SES)."
    ::= { tmnxOtuIfIntervalStatsEntry 9 }

tmnxOtuIfIntvlStatsPMBIP8        OBJECT-TYPE
    SYNTAX      Counter32
    UNITS       "bits"
    MAX-ACCESS  read-only
    STATUS      current
    DESCRIPTION
        "The value of tmnxOtuIfIntvlStatsPMBIP8 indicates the number of Path
         Monitoring (PM) BIP8 errors."
    ::= { tmnxOtuIfIntervalStatsEntry 10 }

tmnxOtuIfIntvlStatsPMBEI         OBJECT-TYPE
    SYNTAX      Counter32
    UNITS       "bits"
    MAX-ACCESS  read-only
    STATUS      current
    DESCRIPTION
        "The value of tmnxOtuIfIntvlStatsPMBEI indicates the number of Path
         Monitoring (PM) Backward Error Indication (BEI) errors."
    ::= { tmnxOtuIfIntervalStatsEntry 11 }

tmnxOtuIfIntvlStatsPMSES         OBJECT-TYPE
    SYNTAX      Counter32
    UNITS       "seconds"
    MAX-ACCESS  read-only
    STATUS      current
    DESCRIPTION
        "The value of tmnxOtuIfIntvlStatsPMSES indicates the number of Path
         Monitoring (PM) Severely Errored Seconds (SES)."
    ::= { tmnxOtuIfIntervalStatsEntry 12 }

tmnxOtuIfIntvlStatsFECES         OBJECT-TYPE
    SYNTAX      Counter32
    UNITS       "seconds"
    MAX-ACCESS  read-only
    STATUS      current
    DESCRIPTION
        "The value of tmnxOtuIfIntvlStatsFECES indicates the number of Forward
         Error Correction (FEC) Errors Seconds (ES)."
    ::= { tmnxOtuIfIntervalStatsEntry 13 }

tmnxOtuIfIntvlStatsFECUAS        OBJECT-TYPE
    SYNTAX      Counter32
    UNITS       "seconds"
    MAX-ACCESS  read-only
    STATUS      current
    DESCRIPTION
        "The value of tmnxOtuIfIntvlStatsFECUAS indicates the number of Forward
         Error Correction (FEC) Unavailable Seconds (UAS)."
    ::= { tmnxOtuIfIntervalStatsEntry 14 }

tmnxOtuIfIntvlStatsSMES          OBJECT-TYPE
    SYNTAX      Counter32
    UNITS       "seconds"
    MAX-ACCESS  read-only
    STATUS      current
    DESCRIPTION
        "The value of tmnxOtuIfIntvlStatsSMES indicates the number of Section
         Monitoring (SM) Errored Seconds (ES)."
    ::= { tmnxOtuIfIntervalStatsEntry 15 }

tmnxOtuIfIntvlStatsSMUAS         OBJECT-TYPE
    SYNTAX      Counter32
    UNITS       "seconds"
    MAX-ACCESS  read-only
    STATUS      current
    DESCRIPTION
        "The value of tmnxOtuIfIntvlStatsSMUAS indicates the number of Section
         Monitoring (SM) Unavailable Seconds (UAS)."
    ::= { tmnxOtuIfIntervalStatsEntry 16 }

tmnxOtuIfIntvlStatsPMES          OBJECT-TYPE
    SYNTAX      Counter32
    UNITS       "seconds"
    MAX-ACCESS  read-only
    STATUS      current
    DESCRIPTION
        "The value of tmnxOtuIfIntvlStatsPMES indicates the number of Path
         Monitoring (PM) Errored Seconds (ES)."
    ::= { tmnxOtuIfIntervalStatsEntry 17 }

tmnxOtuIfIntvlStatsPMUAS         OBJECT-TYPE
    SYNTAX      Counter32
    UNITS       "seconds"
    MAX-ACCESS  read-only
    STATUS      current
    DESCRIPTION
        "The value of tmnxOtuIfIntvlStatsPMUAS indicates the number of Path
         Monitoring (PM) Unavailable Seconds (UAS)."
    ::= { tmnxOtuIfIntervalStatsEntry 18 }

tmnxOtuIfIntvlStatsNPJ           OBJECT-TYPE
    SYNTAX      Counter32
    UNITS       "count"
    MAX-ACCESS  read-only
    STATUS      current
    DESCRIPTION
        "The value of tmnxOtuIfIntvlStatsNPJ indicates the number of Negative
         Pointer justifications that occurred during the asynchronous demapping
         of the received payload inside the OTU frame."
    ::= { tmnxOtuIfIntervalStatsEntry 19 }

tmnxOtuIfIntvlStatsPPJ           OBJECT-TYPE
    SYNTAX      Counter32
    UNITS       "count"
    MAX-ACCESS  read-only
    STATUS      current
    DESCRIPTION
        "The value of tmnxOtuIfIntvlStatsPPJ indicates the number of Positive
         Pointer justifications that occurred during the asynchronous demapping
         of the received payload inside the OTU frame."
    ::= { tmnxOtuIfIntervalStatsEntry 20 }

tmnxOtuIfIntvlStatsElapsedSec    OBJECT-TYPE
    SYNTAX      Counter32
    UNITS       "seconds"
    MAX-ACCESS  read-only
    STATUS      current
    DESCRIPTION
        "The value of tmnxOtuIfIntvlStatsElapsedSec indicates the number of
         Elapsed seconds in the current statistics interval."
    ::= { tmnxOtuIfIntervalStatsEntry 21 }

tmnxOtuConformance               OBJECT IDENTIFIER ::= { tmnxSRConfs 62 }

tmnxOtuCompliances               OBJECT IDENTIFIER ::= { tmnxOtuConformance 1 }

tmnxOtuCompliance                MODULE-COMPLIANCE
    STATUS      obsolete
    DESCRIPTION
        "The compliance statement for revision 1.0 of TIMETRA-OTU-MIB."
    MODULE
        MANDATORY-GROUPS {
            tmnxOtuIfBaseConfigGroup,
            tmnxOtuIfBaseConfigGroupV8v0,
            tmnxOtuIfSMGroup,
            tmnxOtuIfSMGroupV8v0,
            tmnxOtuIfPMGroupV8v0,
            tmnxOtuIfPSIGroupV8v0,
            tmnxOtuStatsGroup,
            tmnxOtuStatsGroupV8v0,
            tmnxOtuNotificationGroup
        }
    ::= { tmnxOtuCompliances 1 }

tmnxOtuComplianceV8v0            MODULE-COMPLIANCE
    STATUS      obsolete
    DESCRIPTION
        "The compliance statement for revision 8.0 of TIMETRA-OTU-MIB."
    MODULE
        MANDATORY-GROUPS {
            tmnxOtuIfBaseConfigGroupV8v0,
            tmnxOtuIfSMGroup,
            tmnxOtuIfSMGroupV8v0,
            tmnxOtuIfPMGroupV8v0,
            tmnxOtuIfPSIGroupV8v0,
            tmnxOtuStatsGroup,
            tmnxOtuStatsGroupV8v0,
            tmnxOtuNotificationGroup,
            tmnxOtuObsoleteV8v0Group
        }
    ::= { tmnxOtuCompliances 2 }

tmnxOtuComplianceV11v0           MODULE-COMPLIANCE
    STATUS      current
    DESCRIPTION
        "The compliance statement for management of OTU interface features in
         the TIMETRA-OTU-MIB for release 11.0."
    MODULE
        MANDATORY-GROUPS {
            tmnxOtuIfBaseConfigGroupV8v0,
            tmnxOtuIfSMGroup,
            tmnxOtuIfSMGroupV8v0,
            tmnxOtuIfPMGroupV8v0,
            tmnxOtuIfPSIGroupV8v0,
            tmnxOtuStatsGroup,
            tmnxOtuStatsGroupV8v0,
            tmnxOtuNotificationGroup,
            tmnxOtuObsoleteV8v0Group,
            tmnxOtuIfFineGrBerGroupV11v0
        }
    ::= { tmnxOtuCompliances 3 }

tmnxOtuGroups                    OBJECT IDENTIFIER ::= { tmnxOtuConformance 2 }

tmnxOtuIfBaseConfigGroup         OBJECT-GROUP
    OBJECTS     {
        tmnxOtuIfTableLastChanged,
        tmnxOtuIfRowStatus,
        tmnxOtuIfTimeStamp,
        tmnxOtuIfFecMode,
        tmnxOtuIfSfSdMethod,
        tmnxOtuIfBerSfThreshold,
        tmnxOtuIfBerSdThreshold,
        tmnxOtuIfOtu2LanDataRate,
        tmnxOtuIfCfgAlarms,
        tmnxOtuIfAlarmState,
        tmnxOtuIfHoldTimeUp,
        tmnxOtuIfHoldTimeDown,
        tmnxOtuIfOtuOperDataRate
    }
    STATUS      obsolete
    DESCRIPTION
        "The group of objects for management of OTU interfaces for the 7x50."
    ::= { tmnxOtuGroups 1 }

tmnxOtuIfSMGroup                 OBJECT-GROUP
    OBJECTS     {
        tmnxOtuIfSmTtiTxMode,
        tmnxOtuIfSmTtiTx,
        tmnxOtuIfSmTtiRx
    }
    STATUS      current
    DESCRIPTION
        "The group of objects for management of Section Monitoring of OTU
         interfaces for the 7x50."
    ::= { tmnxOtuGroups 2 }

tmnxOtuStatsGroup                OBJECT-GROUP
    OBJECTS     {
        tmnxOtuIfRawStatsFECCorrZeros,
        tmnxOtuIfRawStatsOFFECCorrZeros,
        tmnxOtuIfRawStatsHCFECCorrZeros,
        tmnxOtuIfRawStatsFECCorrOnes,
        tmnxOtuIfRawStatsOFFECCorrOnes,
        tmnxOtuIfRawStatsHCFECCorrOnes,
        tmnxOtuIfRawStatsFECUncorrSR,
        tmnxOtuIfRawStatsOFFECUncorrSR,
        tmnxOtuIfRawStatsHCFECUncorrSR,
        tmnxOtuIfRawStatsFECSES,
        tmnxOtuIfRawStatsSMBIP8,
        tmnxOtuIfRawStatsOFSMBIP8,
        tmnxOtuIfRawStatsHCSMBIP8,
        tmnxOtuIfRawStatsSMBEI,
        tmnxOtuIfRawStatsOFSMBEI,
        tmnxOtuIfRawStatsHCSMBEI,
        tmnxOtuIfRawStatsSMSES,
        tmnxOtuIfRawStatsPMBIP8,
        tmnxOtuIfRawStatsOFPMBIP8,
        tmnxOtuIfRawStatsHCPMBIP8,
        tmnxOtuIfRawStatsPMBEI,
        tmnxOtuIfRawStatsOFPMBEI,
        tmnxOtuIfRawStatsHCPMBEI,
        tmnxOtuIfRawStatsPMSES,
        tmnxOtuIfIntvlStatsIsValid,
        tmnxOtuIfIntvlStatsFECCorrZeros,
        tmnxOtuIfIntvlStatsFECCorrOnes,
        tmnxOtuIfIntvlStatsFECUncorrSR,
        tmnxOtuIfIntvlStatsFECSES,
        tmnxOtuIfIntvlStatsSMBIP8,
        tmnxOtuIfIntvlStatsSMBEI,
        tmnxOtuIfIntvlStatsSMSES,
        tmnxOtuIfIntvlStatsPMBIP8,
        tmnxOtuIfIntvlStatsPMBEI,
        tmnxOtuIfIntvlStatsPMSES
    }
    STATUS      current
    DESCRIPTION
        "The group of objects for monitoring statistics of OTU interfaces for
         the 7x50."
    ::= { tmnxOtuGroups 3 }

tmnxOtuNotificationGroup         NOTIFICATION-GROUP
    NOTIFICATIONS {
        tmnxOtuIfAlarmNotification
    }
    STATUS      current
    DESCRIPTION
        "The group of notifications supporting management of OTU interfaces for
         the 7x50."
    ::= { tmnxOtuGroups 4 }

tmnxOtuGroupsV7v0                OBJECT IDENTIFIER ::= { tmnxOtuGroups 5 }

tmnxOtuGroupsV8v0                OBJECT IDENTIFIER ::= { tmnxOtuGroups 6 }

tmnxOtuIfBaseConfigGroupV8v0     OBJECT-GROUP
    OBJECTS     {
        tmnxOtuIfTableLastChanged,
        tmnxOtuIfRowStatus,
        tmnxOtuIfTimeStamp,
        tmnxOtuIfFecMode,
        tmnxOtuIfSfSdMethod,
        tmnxOtuIfBerSfThreshold,
        tmnxOtuIfBerSdThreshold,
        tmnxOtuIfOtu2LanDataRate,
        tmnxOtuIfCfgAlarms,
        tmnxOtuIfAlarmState,
        tmnxOtuIfOtuOperDataRate,
        tmnxOtuIfAsyncMappingEnable
    }
    STATUS      current
    DESCRIPTION
        "The group of additional objects for management of OTU interfaces for
         the 7x50 in Release 8.0."
    ::= { tmnxOtuGroupsV8v0 1 }

tmnxOtuIfSMGroupV8v0             OBJECT-GROUP
    OBJECTS     {
        tmnxOtuIfSmTtiTxMode,
        tmnxOtuIfSmTtiTx,
        tmnxOtuIfSmTtiRx,
        tmnxOtuIfSmTtiExpMode,
        tmnxOtuIfSmTtiExpCopyRx,
        tmnxOtuIfSmTtiExp,
        tmnxOtuIfSmTimReaction
    }
    STATUS      current
    DESCRIPTION
        "The group of additional objects for management of Section Monitoring
         of OTU interfaces for the 7x50 in Release 8.0."
    ::= { tmnxOtuGroupsV8v0 2 }

tmnxOtuStatsGroupV8v0            OBJECT-GROUP
    OBJECTS     {
        tmnxOtuIfRawStatsFECES,
        tmnxOtuIfRawStatsFECUAS,
        tmnxOtuIfRawStatsSMES,
        tmnxOtuIfRawStatsSMUAS,
        tmnxOtuIfRawStatsPMES,
        tmnxOtuIfRawStatsPMUAS,
        tmnxOtuIfRawStatsNPJ,
        tmnxOtuIfRawStatsPPJ,
        tmnxOtuIfRawStatsElapsedSec,
        tmnxOtuIfIntvlStatsFECES,
        tmnxOtuIfIntvlStatsFECUAS,
        tmnxOtuIfIntvlStatsSMES,
        tmnxOtuIfIntvlStatsSMUAS,
        tmnxOtuIfIntvlStatsPMES,
        tmnxOtuIfIntvlStatsPMUAS,
        tmnxOtuIfIntvlStatsPPJ,
        tmnxOtuIfIntvlStatsNPJ,
        tmnxOtuIfIntvlStatsElapsedSec
    }
    STATUS      current
    DESCRIPTION
        "The group of additional objects for monitoring statistics of OTU
         interfaces for the 7x50 in Release 8.0."
    ::= { tmnxOtuGroupsV8v0 3 }

tmnxOtuIfPMGroupV8v0             OBJECT-GROUP
    OBJECTS     {
        tmnxOtuIfPmTtiTxMode,
        tmnxOtuIfPmTtiTx,
        tmnxOtuIfPmTtiRx,
        tmnxOtuIfPmTtiExpMode,
        tmnxOtuIfPmTtiExpCopyRx,
        tmnxOtuIfPmTtiExp,
        tmnxOtuIfPmTimReaction
    }
    STATUS      current
    DESCRIPTION
        "The group of objects for management of Path Monitoring of OTU
         interfaces for the 7x50 in Release 8.0."
    ::= { tmnxOtuGroupsV8v0 4 }

tmnxOtuIfPSIGroupV8v0            OBJECT-GROUP
    OBJECTS     {
        tmnxOtuIfPsiTtiTxMode,
        tmnxOtuIfPsiTtiTx,
        tmnxOtuIfPsiTtiRx,
        tmnxOtuIfPsiTtiExpMode,
        tmnxOtuIfPsiTtiExpCopyRx,
        tmnxOtuIfPsiTtiExp,
        tmnxOtuIfPsiPayloadTypeTx,
        tmnxOtuIfPsiPayloadTypeRx,
        tmnxOtuIfPsiPayloadTypeExp,
        tmnxOtuIfPsiTimReaction,
        tmnxOtuIfPsiPlmReaction
    }
    STATUS      current
    DESCRIPTION
        "The group of objects for management of Payload Structure Identifier of
         OTU interfaces for the 7x50 in Release 8.0."
    ::= { tmnxOtuGroupsV8v0 5 }

tmnxOtuObsoleteV8v0Group         OBJECT-GROUP
    OBJECTS     {
        tmnxOtuIfHoldTimeUp,
        tmnxOtuIfHoldTimeDown
    }
    STATUS      current
    DESCRIPTION
        "The group of objects that were made obsolete for the 7x50 in Release
         8.0."
    ::= { tmnxOtuGroupsV8v0 6 }

tmnxOtuGroupsV11v0               OBJECT IDENTIFIER ::= { tmnxOtuGroups 7 }

tmnxOtuIfFineGrBerGroupV11v0     OBJECT-GROUP
    OBJECTS     {
        tmnxOtuIfFineGrBerSupported,
        tmnxOtuIfFineGrBerSfThresh,
        tmnxOtuIfFineGrBerSdThresh,
        tmnxOtuIfFineGrBerSfThrCoef,
        tmnxOtuIfFineGrBerSdThrCoef,
        tmnxOtuIfFineGrBerSfThreshClr,
        tmnxOtuIfFineGrBerSdThreshClr,
        tmnxOtuIfFineGrBerSfThrClrCoef,
        tmnxOtuIfFineGrBerSdThrClrCoef
    }
    STATUS      current
    DESCRIPTION
        "The group of objects introduced in Release 11.0 for OTU interface fine
         granularity pre-FEC BER SD and SF threshold information on Nokia SROS
         systems."
    ::= { tmnxOtuGroupsV11v0 1 }

tmnxOtuGroupsV13v0               OBJECT IDENTIFIER ::= { tmnxOtuGroups 8 }

tmnxOtuNotifyPrefix              OBJECT IDENTIFIER ::= { tmnxSRNotifyPrefix 62 }

tmnxOtuNotifications             OBJECT IDENTIFIER ::= { tmnxOtuNotifyPrefix 0 }

tmnxOtuIfAlarmNotification       NOTIFICATION-TYPE
    OBJECTS     {
        tmnxOtuIfAlarmState
    }
    STATUS      current
    DESCRIPTION
        "The tmnxOtuIfAlarmNotification notification indicates that an OTU
         interface has experienced either a raising or clearing of an alarm in
         the Forward Error Correction (FEC), Section Monitoring (SM), Path
         Monitoring (PM) or Payload Monitoring (PSI) fields of the OTU frame."
    ::= { tmnxOtuNotifications 1 }

END
