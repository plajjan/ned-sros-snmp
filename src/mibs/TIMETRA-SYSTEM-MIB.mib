TIMETRA-SYSTEM-MIB DEFINITIONS ::= BEGIN

IMPORTS

    MODULE-IDENTITY, OBJECT-TYPE,
    NOTIFICATION-TYPE,
    Integer32, IpAddress, Unsigned32,
    Counter64,
    Counter32, Gauge32                      FROM SNMPv2-SMI
    
    CounterBasedGauge64                     FROM HCNUM-TC

    MODULE-COMPLIANCE, OBJECT-GROUP,
    NOTIFICATION-GROUP                      FROM SNMPv2-CONF

    TEXTUAL-CONVENTION, DateAndTime,
    DisplayString, MacAddress, RowStatus,
    TruthValue, RowPointer, TimeStamp       FROM SNMPv2-TC

    snmpCommunityEntry                      FROM SNMP-COMMUNITY-MIB

    timetraSRMIBModules, tmnxSRObjs,
    tmnxSRConfs, tmnxSRNotifyPrefix         FROM TIMETRA-GLOBAL-MIB

    TNamedItem, TNamedItemOrEmpty,
    TmnxAdminState, TmnxOperState,
    TmnxActionType, TTcpUdpPort,
    IpAddressPrefixLength,
    TmnxDisplayStringURL, TLDisplayString,
    TmnxLongDisplayString,
    TmnxVRtrID, TmnxVRtrIDOrZero,
    TmnxServId, TmnxUuid,
    TItemDescription, TmnxEnabledDisabled, 
    TLNamedItem, TItemDescription           FROM TIMETRA-TC-MIB

    InetAddressPrefixLength,
    InetAddressIPv6, InetPortNumber,
    InetAddressType, InetAddress            FROM INET-ADDRESS-MIB

    tmnxChassisBaseMacAddress,
    tmnxChassisIndex, TmnxSlotNum,
    tmnxChassisNotifyHwIndex,
    tmnxHwID, tmnxHwClass,
    tmnxCpmCardSlotNum, tmnxCpmCardNum      FROM TIMETRA-CHASSIS-MIB
    
    tmnxLogExecRollbackOpIndex, tmnxLogExecRollbackOpType,
    tmnxEhsHandlerDescription, tmnxEhsHEntryScriptPlcyOwner,
    tmnxEhsHEntryScriptPlcyName, tmnxEhsHEntryMinDelay,
    tmnxEhsHEntryMinDelayInterval           FROM TIMETRA-LOG-MIB
                                            
    smLaunchEntry, smRunEntry,             
    smLaunchOwner, smLaunchName, 
    smRunIndex, smLaunchScriptOwner,
    smLaunchScriptName, smLaunchError       FROM DISMAN-SCRIPT-MIB


    TmnxScriptAuthType                      FROM TIMETRA-TC-MIB
    ;

timetraSysMIBModule   MODULE-IDENTITY
        LAST-UPDATED "201701010000Z"
        ORGANIZATION "Nokia"
        CONTACT-INFO
            "Nokia SROS Support
             Web: http://www.nokia.com"
        DESCRIPTION
        "This document is the System SNMP MIB module for the Nokia
        SROS device.  The System MIB module defines SNMP objects to
        manage and provision system features.

        Copyright 2003-2017 Nokia. All rights reserved.
        Reproduction of this document is authorized on the condition
        that the foregoing copyright notice is included.

        This SNMP MIB module (Specification) embodies Nokia's
        proprietary intellectual property.  Nokia retains
        all title and ownership in the Specification, including any
        revisions.

        Nokia grants all interested parties a non-exclusive
        license to use and distribute an unmodified copy of this
        Specification in connection with management of Nokia
        products, and without fee, provided this copyright notice and
        license appear on all copies.

        This Specification is supplied `as is', and Nokia
        makes no warranty, either express or implied, as to the use,
        operation, condition, or performance of the Specification."

--
--  Revision History
--
        REVISION         "201701010000Z"
        DESCRIPTION      "Rev 15.0               1 Jan 2017 00:00
                         15.0 release of the TIMETRA-SYSTEM-MIB."

        REVISION         "201601010000Z"
        DESCRIPTION      "Rev 14.0               1 Jan 2016 00:00
                         14.0 release of the TIMETRA-SYSTEM-MIB."

        REVISION        "201406010000Z"
        DESCRIPTION     "Rev 13.0               01 Jun 2014 00:00
                         13.0 release of the TIMETRA-SYSTEM-MIB."
                         
        REVISION        "201401010000Z"
        DESCRIPTION     "Rev 12.0               01 Jan 2014 00:00
                         12.0 release of the TIMETRA-SYSTEM-MIB."

        REVISION        "201102010000Z"
        DESCRIPTION     "Rev 9.0                01 Feb 2011 00:00
                         9.0 release of the TIMETRA-SYSTEM-MIB."

        REVISION        "201001010000Z"
        DESCRIPTION     "Rev 8.0                01 Jan 2010 00:00
                         8.0 release of the TIMETRA-SYSTEM-MIB."

        REVISION        "200902280000Z"
        DESCRIPTION     "Rev 7.0                28 Feb 2009 00:00
                         7.0 release of the TIMETRA-SYSTEM-MIB."

        REVISION        "200801010000Z"
        DESCRIPTION     "Rev 6.0                01 Jan 2008 00:00
                         6.0 release of the TIMETRA-SYSTEM-MIB."

        REVISION        "200701010000Z"
        DESCRIPTION     "Rev 5.0                01 Jan 2007 00:00
                         5.0 release of the TIMETRA-SYSTEM-MIB."

        REVISION        "200603150000Z"
        DESCRIPTION     "Rev 4.0                15 Mar 2006 00:00
                         4.0 release of the TIMETRA-SYSTEM-MIB."

        REVISION        "200508310000Z"
        DESCRIPTION     "Rev 3.0                31 Aug 2005 00:00
                         3.0 release of the TIMETRA-SYSTEM-MIB."

        REVISION        "200501240000Z"
        DESCRIPTION     "Rev 2.1                24 Jan 2005 00:00
                         2.1 release of the TIMETRA-SYSTEM-MIB."

        REVISION        "200401150000Z"
        DESCRIPTION     "Rev 2.0                15 Jan 2004 00:00
                         2.0 release of the TIMETRA-SYSTEM-MIB."

        REVISION        "200308150000Z"
        DESCRIPTION     "Rev 1.2                15 Aug 2003 00:00
                         1.2 release of the TIMETRA-SYSTEM-MIB."

        REVISION        "200301200000Z"
        DESCRIPTION     "Rev 1.0                20 Jan 2003 00:00
                        1.0 Release of the TIMETRA-SYSTEM-MIB."

        REVISION        "200008140000Z"
        DESCRIPTION     "Rev 0.1                14 Aug 2000 00:00
                        First version of the TIMETRA-SYSTEM-MIB."

    ::= { timetraSRMIBModules 1 }

--
--  sub-tree for Nokia 7x50 SR System MIB managed objects
--
    tmnxSysObjs         OBJECT IDENTIFIER ::= { tmnxSRObjs 1 }
    tmnxSysConformance  OBJECT IDENTIFIER ::= { tmnxSRConfs 1 }
    tmnxDCSysObjs       OBJECT IDENTIFIER ::= { tmnxSysObjs 24 }

--
--  Sub-tree for Nokia SROS System MIB notification (trap) events
--
tmnxSysMIBNotifyPrefix  OBJECT IDENTIFIER ::= { tmnxSRNotifyPrefix 1 }
tmnxSysNotifications    OBJECT IDENTIFIER ::= { tmnxSysMIBNotifyPrefix 0 }
tmnxSysMGNotifications    OBJECT IDENTIFIER ::= { tmnxSysMIBNotifyPrefix 1 }
--%%%%%%%%%%%%%%%%%%%%%%%%%%%%%%%%%%%%%%%%%%%%%%%%%%%%%%%%%%%%%%%%%%%%%
--
--      Nokia SROS series System MIB textual conventions
--
TmnxSsiSyncMode ::= TEXTUAL-CONVENTION
    STATUS      current
    DESCRIPTION
        "The value of TmnxSsiSyncMode specifies the type of
         synchronization operation to perform between the primary
         and secondary CPMs after a change has been made to the
         configuration files or the boot environment
         information contained in the boot options file (bof)."
    SYNTAX      INTEGER {
                    none (1),
                    config (2),
                    bootEnv (3)
                }

TmnxSsiSyncRollbackMode ::= TEXTUAL-CONVENTION
    STATUS      current
    DESCRIPTION
        "The value of TmnxSsiSyncRollbackMode specifies the type of
         synchronization operation to perform between the primary
         and secondary CPMs after a change has been made to the
         rollback files."
    SYNTAX      INTEGER {
                    none (1),
                    rollbackSingle (2),
                    rollbackAll (3)
                }

TmnxSysLicenseApplication ::= TEXTUAL-CONVENTION
    STATUS      current
    DESCRIPTION
        "The textual convention TmnxSysLicenseApplication represents
         an application in a virtual machine implementation that
         is subject to licensing.
         
         NAT - Network Address Translation
         WLAN-GW - Wireless Local Area Network Gateway
         LNS - L2TP Network Server
         Subscriber Management
         AA  - Application Assurance
        "
    SYNTAX      INTEGER {
                    none    (0),
                    nat     (1),
                    wlanGw  (2),
                    lns     (3),
                    subMgmt (4),
                    aa      (5),
                    ipsec   (6)
                }

TmnxSysLicenseAppStatsType ::= TEXTUAL-CONVENTION
    STATUS      current
    DESCRIPTION
        "The textual convention TmnxSysLicenseAppStatsType represents
         the type of statistics collected about an application
         in a virtual machine implementation subject to licensing."
    SYNTAX      INTEGER {
                        none                             (0),
--                  NAT (Network Address Translation)    
                        lsnSubscribers                   (1),
                        lsnBandwidth                     (2),
--                  Wireless LAN Gateway
                        wlanGwUserEquipment              (1000),
                        wlanGwGtpBearers                 (1001),
--                  LNS (L2TP Network Server)
                        lnsTunnels                       (2000),
                        lnsSessions                      (2001),
--                  Subscriber management
                        subscriberHosts                  (3000),
--                  AA (Application Assurance)    
                        aaSubscribers                    (4000),
                        aaBandwidth                      (4001),
--                  IPsec
                        ipsecTunnels                     (5000),
                        ipsecTnlBandwidth                (5001),
                        ipTunnels                        (5002),
                        ipTnlBandwidth                   (5003)
                }

TmnxSysMonSampleTime             ::= TEXTUAL-CONVENTION
    STATUS      current
    DESCRIPTION
        "The value of TmnxSysMonSampleTime specifies the monitoring sample time
         (in terms of seconds) for a system object."
    SYNTAX      Unsigned32 (1|60|300)

TmnxSysMonUtilization            ::= TEXTUAL-CONVENTION
    STATUS      current
    DESCRIPTION
        "The value of TmnxSysMonUtilization specifies the utilization/idle
         percentage (in terms 100ths of a percent) for a given sample-time."
    SYNTAX      Gauge32 (0..10000)

--%%%%%%%%%%%%%%%%%%%%%%%%%%%%%%%%%%%%%%%%%%%%%%%%%%%%%%%%%%%%%%%%%%%%%
--
--      tmnxSys Objects
--      The tmnxSys objects provide general information about the
--      Nokia SROS system.

--
--      General System Information
--

sysGenInfo      OBJECT IDENTIFIER ::= { tmnxSysObjs 1 }

sgiCpuUsage     OBJECT-TYPE
    SYNTAX      Unsigned32 (0..100)
    UNITS       "percent"
    MAX-ACCESS  read-only
    STATUS      current
    DESCRIPTION
        "The value of sgiCpuUsage indicates the current CPU utilization
         for the system."
    ::= { sysGenInfo 1 }

sgiMemoryUsed   OBJECT-TYPE
    SYNTAX      Unsigned32
    UNITS       "bytes"
    MAX-ACCESS  read-only
    STATUS      current
    DESCRIPTION
        "The value of sgiMemoryUsed indicates the total pre-allocated
        pool memory currently in use on the system.
        
        If the value is greater than the maximum value reportable by this
        object then this object reports its maximum value (4,294,967,295) 
        and sgiKbMemoryUsed must be used to determine the total 
        pre-allocated pool memory."
    ::= { sysGenInfo 2 }

sgiMemoryAvailable   OBJECT-TYPE
    SYNTAX      Unsigned32
    UNITS       "bytes"
    MAX-ACCESS  read-only
    STATUS      current
    DESCRIPTION
        "The value of sgiMemoryAvailable indicates the amount of free
        memory in the overall system that is not allocated to memory
        pools, but is available in case a memory pool needs to grow."
    ::= { sysGenInfo 3 }

sgiMemoryPoolAllocated   OBJECT-TYPE
    SYNTAX      Unsigned32
    UNITS       "bytes"
    MAX-ACCESS  read-only
    STATUS      current
    DESCRIPTION
        "The value of sgiMemoryPoolAllocated indicates the total memory
        currently allocated in memory-pools on the system.

        This memory may or may not be currently in use, but is pre-allocated
        should the software need to use it.

        If the value is greater than the maximum value reportable by this 
        object then this object reports its maximum value (4,294,967,295) 
        and sgiKbMemoryPoolAllocated must be used to determine the total 
        memory allocated in memory-pools."
    ::= { sysGenInfo 4 }

sgiSwMajorVersion   OBJECT-TYPE
    SYNTAX      Unsigned32
    MAX-ACCESS  read-only
    STATUS      current
    DESCRIPTION
        "The value of sgiSwMajorVersion indicates the major version number
         of the software running on the active CPM card."
    ::= { sysGenInfo 5 }

sgiSwMinorVersion   OBJECT-TYPE
    SYNTAX      Unsigned32
    MAX-ACCESS  read-only
    STATUS      current
    DESCRIPTION
        "The value of sgiSwMinorVersion indicates the minor version number
         of the software running on the active CPM card."
    ::= { sysGenInfo 6 }

sgiSwVersionModifier   OBJECT-TYPE
    SYNTAX      OCTET STRING (SIZE (0..255))
    MAX-ACCESS  read-only
    STATUS      current
    DESCRIPTION
        "The value of sgiSwVersionModifier indicates additional information
         about the version of software running on the active CPM card."
    ::= { sysGenInfo 7 }

sgiSnmpInGetBulks   OBJECT-TYPE
    SYNTAX      Counter32
    MAX-ACCESS  read-only
    STATUS      current
    DESCRIPTION
        "The value of sgiSnmpInGetBulks indicates the total number of
         SNMP Get-Next PDUs which have been accepted and processed by
         the SNMP protocol entity."
    ::= { sysGenInfo 8 }

sgiKbMemoryUsed   OBJECT-TYPE
    SYNTAX      Unsigned32
    UNITS       "kilobytes"
    MAX-ACCESS  read-only
    STATUS      current
    DESCRIPTION
        "The value of sgiKbMemoryUsed indicates the total pre-allocated
        pool memory, in kilobytes, currently in use on the system."
    ::= { sysGenInfo 9 }

sgiKbMemoryAvailable   OBJECT-TYPE
    SYNTAX      Unsigned32
    UNITS       "kilobytes"
    MAX-ACCESS  read-only
    STATUS      current
    DESCRIPTION
        "The value of sgiKbMemoryAvailable indicates the amount of free
        memory, in kilobytes, in the overall system that is not allocated to
        memory pools, but is available in case a memory pool needs to grow."
    ::= { sysGenInfo 10 }

sgiKbMemoryPoolAllocated   OBJECT-TYPE
    SYNTAX      Unsigned32
    UNITS       "kilobytes"
    MAX-ACCESS  read-only
    STATUS      current
    DESCRIPTION
        "The value of sgiKbMemoryPoolAllocated indicates the total memory, in
        kilobytes, currently allocated in memory-pools on the system.

        This memory may or may not be currently in use, but is pre-allocated
        should the software need to use it."
    ::= { sysGenInfo 11 }

sgiSnmpFailedSets OBJECT-TYPE
    SYNTAX      Counter32
    MAX-ACCESS  read-only
    STATUS      current
    DESCRIPTION
        "The value of sgiSnmpFailedSets indicates the total number of SNMP set
         requests which have failed which failed due to another management
         interface (such as NETCONF) exclusively reserving the system
         resources."
    ::= { sysGenInfo 14 }

tmnxSysCpuMonTable               OBJECT-TYPE
    SYNTAX      SEQUENCE OF TmnxSysCpuMonEntry
    MAX-ACCESS  not-accessible
    STATUS      current
    DESCRIPTION
        "tmnxSysCpuMonTable consists of the system level CPU monitoring
         statistics."
    ::= { sysGenInfo 12 }

tmnxSysCpuMonEntry               OBJECT-TYPE
    SYNTAX      TmnxSysCpuMonEntry
    MAX-ACCESS  not-accessible
    STATUS      current
    DESCRIPTION
        "tmnxSysCpuMonEntry contains the system level CPU monitoring statistics
         over a specified sample-time."
    INDEX       { tmnxSysCpuMonSampleTime }
    ::= { tmnxSysCpuMonTable 1 }

TmnxSysCpuMonEntry               ::= SEQUENCE {
    tmnxSysCpuMonSampleTime          TmnxSysMonSampleTime,
    tmnxSysCpuMonCpuIdle             TmnxSysMonUtilization,
    tmnxSysCpuMonBusyCoreUtil        TmnxSysMonUtilization,
    tmnxSysCpuMonBusyGroupName       OCTET STRING,
    tmnxSysCpuMonBusyGroupUtil       TmnxSysMonUtilization
}

tmnxSysCpuMonSampleTime          OBJECT-TYPE
    SYNTAX      TmnxSysMonSampleTime
    MAX-ACCESS  not-accessible
    STATUS      current
    DESCRIPTION
        "The value of tmnxSysCpuMonSampleTime specifies the sample-time used to
         calculate the utilization results for the row."
    ::= { tmnxSysCpuMonEntry 1 }

tmnxSysCpuMonCpuIdle             OBJECT-TYPE
    SYNTAX      TmnxSysMonUtilization
    MAX-ACCESS  read-only
    STATUS      current
    DESCRIPTION
        "The value of tmnxSysCpuMonCpuIdle indicates the overall percentage of
         CPU idleness over the specified sample-time."
    ::= { tmnxSysCpuMonEntry 2 }

tmnxSysCpuMonBusyCoreUtil        OBJECT-TYPE
    SYNTAX      TmnxSysMonUtilization
    MAX-ACCESS  read-only
    STATUS      current
    DESCRIPTION
        "The value of tmnxSysCpuMonBusyCoreUtil indicates the utilization
         percentage of the busiest processor core over the specified
         sample-time. On single core CPUs, this is the overall system
         utilization percentage over the specified sample-time."
    ::= { tmnxSysCpuMonEntry 3 }

tmnxSysCpuMonBusyGroupName       OBJECT-TYPE
    SYNTAX      OCTET STRING (SIZE (0..64))
    MAX-ACCESS  read-only
    STATUS      current
    DESCRIPTION
        "The value of tmnxSysCpuMonBusyGroupName indicates the name of the group
         that is running at the highest capacity utilization.

         Capacity utilization is the CPU utilization relative to the maximum CPU
         resources available to that group.  A group is a set of related
         applications, services, tasks or protocol handlers that consumes some
         part of the system CPU resources.

         The capacity utilization of the busiest group is indicated by
         tmnxSysCpuMonBusyGroupUtil."
    ::= { tmnxSysCpuMonEntry 4 }

tmnxSysCpuMonBusyGroupUtil       OBJECT-TYPE
    SYNTAX      TmnxSysMonUtilization
    MAX-ACCESS  read-only
    STATUS      current
    DESCRIPTION
        "The value of tmnxSysCpuMonBusyGroupUtil indicates the capacity
         utilization of the group that is running at the highest capacity
         utilization.

         Capacity utilization is the CPU utilization relative to the maximum CPU
         resources available to that group.  A group is a set of related
         applications, services, tasks or protocol handlers that consumes some
         part of the system CPU resources.

         The name of the busiest group is indicated by
         tmnxSysCpuMonBusyGroupName."
    ::= { tmnxSysCpuMonEntry 5 }

--
--      System Grouping Identifiers
--
sgiGroupingIDs     OBJECT IDENTIFIER ::= { sysGenInfo 13 }

sgiSystemGroupID   OBJECT-TYPE
    SYNTAX      Unsigned32
    MAX-ACCESS  read-write
    STATUS      current
    DESCRIPTION
        "The value of sgiSystemGroupID specifies a group this
         system belongs to.  It is used by NMS applications to identify
         a set of systems for which the NMS wants to perform common
         tasks such as correlating alarms."
    DEFVAL { 0 }
    ::= { sgiGroupingIDs 1 }

sgiSystemSubGroupID   OBJECT-TYPE
    SYNTAX      Unsigned32
    MAX-ACCESS  read-write
    STATUS      current
    DESCRIPTION
        "The value of sgiSystemSubGroupID specifies a sub-group within
         the sgiSystemGroupID group that this system belongs to.  
         It is used by NMS applications to identify a subset of systems 
         in the sgiSystemGroupID for which the NMS wants to perform common
         tasks such as correlating alarms."
    DEFVAL { 0 }
    ::= { sgiGroupingIDs 2 }

--
--      General system time information
--

sysTimeInfo     OBJECT IDENTIFIER ::= { tmnxSysObjs 2 }

stiDateAndTime  OBJECT-TYPE
    SYNTAX      DateAndTime (SIZE (11))
    MAX-ACCESS  read-write
    STATUS      current
    DESCRIPTION
        "The current date and time (in UTC) maintained in this managed
         system."
    ::= { sysTimeInfo 1 }

stiActiveZone   OBJECT-TYPE
    SYNTAX      DisplayString (SIZE (0..5))
    MAX-ACCESS  read-write
    STATUS      current
    DESCRIPTION
        "The time zone that is active in this managed system."
    DEFVAL { "UTC" }
    ::= { sysTimeInfo 2 }

stiHoursOffset  OBJECT-TYPE
    SYNTAX      Integer32 (-11..12)
    UNITS       "hours"
    MAX-ACCESS  read-write
    STATUS      current
    DESCRIPTION
        "The number of hours by which the time zone represented
        by stiActiveZone offsets from UTC (Coordinated Universal
        Time)."
    DEFVAL { 0 }
    ::= { sysTimeInfo 3 }

stiMinutesOffset  OBJECT-TYPE
    SYNTAX      Integer32 (0..59)
    UNITS       "minutes"
    MAX-ACCESS  read-write
    STATUS      current
    DESCRIPTION
        "The number of minutes (in addition to the hours offset
        defined by stiHoursOffset) by which the time zone
        represented by stiActiveZone offsets from UTC (Coordinated
        Universal Time). This value is used when the time zone does
        not have an offset that is an integral number of hours.

        If the hour offset is defined as '12', the minute offset
        cannot be anything other than zero."
    DEFVAL { 0 }
    ::= { sysTimeInfo 4 }

stiZoneType OBJECT-TYPE
    SYNTAX      INTEGER {
                    system (1),
                    user (2)
                }
    MAX-ACCESS  read-only
    STATUS      current
    DESCRIPTION
        "stiZoneType will be 'system' if the zone defined by
        stiActiveZone is a system-defined zone. It will be
        'user' if the zone has been defined by the user."
    ::= { sysTimeInfo 5 }

stiSummerZoneTable OBJECT-TYPE
    SYNTAX      SEQUENCE OF StiSummerZoneEntry
    MAX-ACCESS  not-accessible
    STATUS      current
    DESCRIPTION
        "The stiSummerZoneTable has an entry for each summer time
        zone information."
    ::= { sysTimeInfo 6 }


stiSummerZoneEntry OBJECT-TYPE
    SYNTAX      StiSummerZoneEntry
    MAX-ACCESS  not-accessible
    STATUS      current
    DESCRIPTION
        "Each row entry contains information about a summer time
        zone. This information can be used to either override the
        default summer (or daylight savings) time information for
        a system-defined time zone or define the summer time
        information for a user-defined time zone."
    INDEX {IMPLIED stiSummerZoneName}
    ::= { stiSummerZoneTable 1 }

StiSummerZoneEntry ::=
    SEQUENCE {
        stiSummerZoneName              OCTET STRING,
        stiSummerZoneRowStatus         RowStatus,
        stiSummerZoneStartDate         DateAndTime,
        stiSummerZoneEndDate           DateAndTime,
        stiSummerZoneOffset            Unsigned32,
        stiSummerZoneStartDay          INTEGER,
        stiSummerZoneStartWeek         INTEGER,
        stiSummerZoneStartMonth        INTEGER,
        stiSummerZoneStartHour         Unsigned32,
        stiSummerZoneStartMinute       Unsigned32,
        stiSummerZoneEndDay            INTEGER,
        stiSummerZoneEndWeek           INTEGER,
        stiSummerZoneEndMonth          INTEGER,
        stiSummerZoneEndHour           Unsigned32,
        stiSummerZoneEndMinute         Unsigned32
    }

stiSummerZoneName OBJECT-TYPE
    SYNTAX      OCTET STRING (SIZE (1..5))
    MAX-ACCESS  not-accessible
    STATUS      current
    DESCRIPTION
        "The name for a summer time zone. This name must be unique
        amongst the table entries. The summer time zone name should
        comprise only of uppercase letters A-Z and digits 0-9."
    ::= { stiSummerZoneEntry 1 }

stiSummerZoneRowStatus OBJECT-TYPE
    SYNTAX      RowStatus
    MAX-ACCESS  read-create
    STATUS      current
    DESCRIPTION
        "The row status used to create and delete rows in this table."
    ::= { stiSummerZoneEntry 2 }

stiSummerZoneStartDate OBJECT-TYPE
    SYNTAX      DateAndTime (SIZE (8))
    MAX-ACCESS  read-create
    STATUS      obsolete
    DESCRIPTION
        "The starting date and time when the summer time will
        take effect.

        This object was made obsolete in the 4.0 release."
    ::= { stiSummerZoneEntry 3 }

stiSummerZoneEndDate OBJECT-TYPE
    SYNTAX      DateAndTime (SIZE (8))
    MAX-ACCESS  read-create
    STATUS      obsolete
    DESCRIPTION
        "The date and time when summer time will end.

        This object was made obsolete in the 4.0 release."
    ::= { stiSummerZoneEntry 4 }

stiSummerZoneOffset OBJECT-TYPE
    SYNTAX      Unsigned32 (0..60)
    UNITS       "minutes"
    MAX-ACCESS  read-create
    STATUS      current
    DESCRIPTION
        "The number of minutes that will be added to the time
        when summer time takes effect. The same number of minutes
        will be subtracted from the time when the summer time ends."
    DEFVAL { 60 }
    ::= { stiSummerZoneEntry 5 }

stiSummerZoneStartDay OBJECT-TYPE
    SYNTAX      INTEGER {
                    sunday(0),
                    monday(1),
                    tuesday(2),
                    wednesday(3),
                    thursday(4),
                    friday(5),
                    saturday(6)
                }
    MAX-ACCESS  read-create
    STATUS      current
    DESCRIPTION
        "The starting day of the week when the summer time will
        take effect."
    DEFVAL { sunday }
    ::= { stiSummerZoneEntry 6 }

stiSummerZoneStartWeek OBJECT-TYPE
    SYNTAX      INTEGER {
                    first(0),
                    second(1),
                    third(2),
                    fourth(3),
                    last(4)
                }
    MAX-ACCESS  read-create
    STATUS      current
    DESCRIPTION
        "The starting week of the month when the summer time will
        take effect."
    DEFVAL { first }
    ::= { stiSummerZoneEntry 7 }

stiSummerZoneStartMonth OBJECT-TYPE
    SYNTAX      INTEGER {
                    january(0),
                    february(1),
                    march(2),
                    april(3),
                    may(4),
                    june(5),
                    july(6),
                    august(7),
                    september(8),
                    october(9),
                    november(10),
                    december(11)
                }
    MAX-ACCESS  read-create
    STATUS      current
    DESCRIPTION
        "The starting month of the year when the summer time will
        take effect."
    DEFVAL { january }
    ::= { stiSummerZoneEntry 8 }

stiSummerZoneStartHour  OBJECT-TYPE
    SYNTAX      Unsigned32 (0..23)
    UNITS       "hours"
    MAX-ACCESS  read-create
    STATUS      current
    DESCRIPTION
        "The hour at which the summer time will take effect."
    DEFVAL { 0 }
    ::= { stiSummerZoneEntry 9 }

stiSummerZoneStartMinute  OBJECT-TYPE
    SYNTAX      Unsigned32 (0..59)
    UNITS       "minutes"
    MAX-ACCESS  read-create
    STATUS      current
    DESCRIPTION
        "The number of minutes after the hours defined by
        stiSummerZoneStartHour when the summer time will
        take effect."
    DEFVAL { 0 }
    ::= { stiSummerZoneEntry 10 }

stiSummerZoneEndDay OBJECT-TYPE
    SYNTAX      INTEGER {
                    sunday(0),
                    monday(1),
                    tuesday(2),
                    wednesday(3),
                    thursday(4),
                    friday(5),
                    saturday(6)
                }
    MAX-ACCESS  read-create
    STATUS      current
    DESCRIPTION
        "The day of the week when the summer time setting will
        end."
    DEFVAL { sunday }
    ::= { stiSummerZoneEntry 11 }

stiSummerZoneEndWeek OBJECT-TYPE
    SYNTAX      INTEGER {
                    first(0),
                    second(1),
                    third(2),
                    fourth(3),
                    last(4)
                }
    MAX-ACCESS  read-create
    STATUS      current
    DESCRIPTION
        "The week of the month when the summer time setting will
        end."
    DEFVAL { first }
    ::= { stiSummerZoneEntry 12 }

stiSummerZoneEndMonth OBJECT-TYPE
    SYNTAX      INTEGER {
                    january(0),
                    february(1),
                    march(2),
                    april(3),
                    may(4),
                    june(5),
                    july(6),
                    august(7),
                    september(8),
                    october(9),
                    november(10),
                    december(11)
                }
    MAX-ACCESS  read-create
    STATUS      current
    DESCRIPTION
        "The month of the year when the summer time setting will
        end."
    DEFVAL { january }
    ::= { stiSummerZoneEntry 13 }

stiSummerZoneEndHour  OBJECT-TYPE
    SYNTAX      Unsigned32 (0..23)
    UNITS       "hours"
    MAX-ACCESS  read-create
    STATUS      current
    DESCRIPTION
        "The hour at which the summer time will stop taking effect."
    DEFVAL { 0 }
    ::= { stiSummerZoneEntry 14 }

stiSummerZoneEndMinute  OBJECT-TYPE
    SYNTAX      Unsigned32 (0..59)
    UNITS       "minutes"
    MAX-ACCESS  read-create
    STATUS      current
    DESCRIPTION
        "The number of minutes after the hours defined by
        stiSummerZoneEndHour when the summer time will
        stop taking effect."
    DEFVAL { 0 }
    ::= { stiSummerZoneEntry 15 }

stiPreferLocalTime OBJECT-TYPE
    SYNTAX      TruthValue
    MAX-ACCESS  read-write
    STATUS      current
    DESCRIPTION
        "The value of stiPreferLocalTime specifies the preference for the use
        of local or UTC time in the system for objects such as log file names,
        created/completed times reported in log files, rollback times displayed
        in show routines etc. Note that the time format for timestamps on
        log events themselves is controlled on a per log basis and not via
        prefer-local-time.

        A value of false(2) means use UTC time; true(1) means use the local
        system time, configured through 'configure system time' command"
    DEFVAL { false }
    ::= { sysTimeInfo 7}

--
--      SNTP (Simple Network Time Protocol) Information
--

sysSntpInfo     OBJECT IDENTIFIER ::= { tmnxSysObjs 3 }

sntpState OBJECT-TYPE
    SYNTAX      INTEGER {
                    unicast(1),
                    broadcast(2)
                }
    MAX-ACCESS  read-write
    STATUS      current
    DESCRIPTION
        "The mode for Simple Network Time Protocol (SNTP).
        'Unicast' indicates that broadcast client is
        disabled. A value of 'broadcast' indicates that SNTP
        is listening to SNTP/NTP broadcast messages on
        interfaces with broadcast client enabled."
    DEFVAL { unicast }
    ::= { sysSntpInfo 1 }

sntpServerTable OBJECT-TYPE
    SYNTAX      SEQUENCE OF SntpServerEntry
    MAX-ACCESS  not-accessible
    STATUS      current
    DESCRIPTION
        "The sntpServerEntry has an entry for each SNTP server
        for SNTP unicast client mode. SNTP can only receive the
        time from one of these SNTP servers.
        The table can have up to a maximum of 3 entries."
::= { sysSntpInfo 2 }


sntpServerEntry OBJECT-TYPE
    SYNTAX      SntpServerEntry
    MAX-ACCESS  not-accessible
    STATUS      current
    DESCRIPTION
        "Each row entry contains information about an SNTP server."
    INDEX {sntpServerAddress}
    ::= { sntpServerTable 1 }

SntpServerEntry ::=
    SEQUENCE {
        sntpServerAddress           IpAddress,
        sntpServerRowStatus         RowStatus,
        sntpServerVersion           Integer32,
        sntpServerPreference        INTEGER,
        sntpServerInterval          Unsigned32
    }

sntpServerAddress OBJECT-TYPE
    SYNTAX      IpAddress
    MAX-ACCESS  not-accessible
    STATUS      current
    DESCRIPTION
        "The IP address of the SNTP server."
    ::= { sntpServerEntry 1 }

sntpServerRowStatus OBJECT-TYPE
    SYNTAX      RowStatus
    MAX-ACCESS  read-create
    STATUS      current
    DESCRIPTION
        "The row status used to create and delete rows in this table."
    ::= { sntpServerEntry 2 }

sntpServerVersion OBJECT-TYPE
    SYNTAX      Integer32 (1..3)
    MAX-ACCESS  read-create
    STATUS      current
    DESCRIPTION
        "The SNTP Version supported by this server."
    DEFVAL { 3 }
    ::= { sntpServerEntry 3 }

sntpServerPreference OBJECT-TYPE
    SYNTAX      INTEGER {
                    normal (1),
                    preferred(2)
                }
    MAX-ACCESS  read-create
    STATUS      current
    DESCRIPTION
        "The preference value for this SNTP server.
        When more then one time-server is configured it may be
        desirable that one server have preference over others.
        The value of sntpServerPreference for that server will be
        set to preferred(2). Only one server in the table can be
        a preferred server"
    DEFVAL { normal }
    ::= { sntpServerEntry 4 }

sntpServerInterval OBJECT-TYPE
    SYNTAX      Unsigned32 (64..1024)
    UNITS       "seconds"
    MAX-ACCESS  read-create
    STATUS      current
    DESCRIPTION
        "The frequency at which this server is queried."
    DEFVAL { 64 }
    ::= { sntpServerEntry 5 }

sntpAdminState OBJECT-TYPE
    SYNTAX      INTEGER {
                    noop (1),
                    inService (2),
                    outOfService (3)
                }
    MAX-ACCESS  read-write
    STATUS      current
    DESCRIPTION
        "The desired administrative state for SNTP."
    DEFVAL { outOfService }
    ::= { sysSntpInfo 3 }

sntpOperStatus OBJECT-TYPE
      SYNTAX      TmnxOperState
      MAX-ACCESS  read-only
      STATUS      current
      DESCRIPTION
          "The value of sntpOperStatus indicates the current operational status
           of SNTP."
      ::= { sysSntpInfo 4 }

--
--      System Synchronization information
--
sysSyncInfo     OBJECT IDENTIFIER ::= { tmnxSysObjs 4 }

ssiSaveConfig   OBJECT-TYPE
    SYNTAX      TmnxActionType
    MAX-ACCESS  read-write
    STATUS      current
    DESCRIPTION
        "Setting this action variable to 'doAction' causes the current
         running configuration information to be saved to the location
         specified by ssiSaveConfigDest.  If no location is specified
         by ssiSaveConfigDest, the primary configuration file pointed to
         in the boot options file (bof) will be backed up and a new
         primary configuration file will be created with the current
         running configuration information.

         If ssiSaveConfigDetail has a value of 'true', default configuration
         values will be included in the saved configuration information.

         A corresponding persistent SNMP index file is created regardless of
         the setting of the persistence switch in the bof."
    DEFVAL { notApplicable }
    ::= { sysSyncInfo 15 }

ssiSyncMode     OBJECT-TYPE
    SYNTAX      TmnxSsiSyncMode
    MAX-ACCESS  read-write
    STATUS      current
    DESCRIPTION
        "The value of ssiSyncMode specifies the type of synchronization
         operation to perform between the primary and secondary CPMs
         after a change has been made to the configuration files 
         or the boot environment information contained in the boot options file
         (bof)."
   DEFVAL { none }
   ::= { sysSyncInfo 16 }

ssiSyncForce    OBJECT-TYPE
    SYNTAX      TmnxSsiSyncMode
    MAX-ACCESS  read-write
    STATUS      current
    DESCRIPTION
        "The value of ssiSyncForce specifies the type of synchronization
         operation to perform when an SNMP set is made to this object.
         'config' synchronizes only configuration files.
         'bootEnv' synchronizes all files required to boot the system.
         
         The result of a read operation on this object is always 'none'."
    DEFVAL { none }
    ::= { sysSyncInfo 17 }

ssiSyncStatus   OBJECT-TYPE
    SYNTAX      INTEGER {
                    unknown (0),
                    configOnly (1),
                    bootEnv (2),
                    configFail (3),
                    bootEnvFail (4),
                    configInProgress (5),
                    bootEnvInProgress (6)
                }
    MAX-ACCESS  read-only
    STATUS      current
    DESCRIPTION
        "The value of ssiSyncStatus indicates the results of the last
         synchronization operation between the primary and secondary CPMs."
    ::= { sysSyncInfo 18 }

ssiSyncConfigLastTime   OBJECT-TYPE
    SYNTAX      TimeStamp
    MAX-ACCESS  read-only
    STATUS      current
    DESCRIPTION
        "The value of ssiSyncConfigLastTime is the timestamp of the last
         successful synchronization of the configuration files."
    ::= { sysSyncInfo 19 }

ssiSyncBootEnvLastTime  OBJECT-TYPE
    SYNTAX      TimeStamp
    MAX-ACCESS  read-only
    STATUS      current
    DESCRIPTION
        "The value of ssiSyncBootEnvLastTime is the timestamp of the last
         successful synchronization of the boot environment files."
    ::= { sysSyncInfo 20 }

ssiConfigMaxBackupRevisions OBJECT-TYPE
    SYNTAX      Unsigned32 (1..9)
    MAX-ACCESS  read-write
    STATUS      current
    DESCRIPTION
        "The value of ssiConfigMaxBackupRevisions is the maximum number of
         backup revisions maintained for a configuration file. This value
         also applies to the number of revisions maintained for the BOF
         file."
    DEFVAL { 5 }
    ::= { sysSyncInfo 21 }

ssiSaveConfigResult OBJECT-TYPE
    SYNTAX      INTEGER {
                    none (1),
                    inProgress (2),
                    success (3),
                    failed (4)
                }
    MAX-ACCESS  read-only
    STATUS      current
    DESCRIPTION
        "The value of ssiSaveConfigResult represents the result of the
         last ssiSaveConfig action.
         none(1)            None of the following apply
         inProgress(2)      The action is still in progress
         success(3)         The action completed successfully
         failed(4)          The action failed"
    ::= {sysSyncInfo 22 }

ssiSaveBof    OBJECT-TYPE
    SYNTAX      TmnxActionType
    MAX-ACCESS  read-write
    STATUS      current
    DESCRIPTION
        "Setting ssiSaveBof action variable to 'doAction' causes the
         existing BOF to be backed up and a new BOF file to be created
         with the current boot options information."
    DEFVAL { notApplicable }
    ::= {sysSyncInfo 23 }

ssiSaveBofResult OBJECT-TYPE
    SYNTAX      INTEGER {
                    none (1),
                    inProgress (2),
                    success (3),
                    failed (4)
                }
    MAX-ACCESS  read-only
    STATUS      current
    DESCRIPTION
        "The value of ssiSaveBofResult represents the result of the
         last ssiSaveBof action.
         none(1)            None of the following apply
         inProgress(2)      The action is still in progress
         success(3)         The action completed successfully
         failed(4)          The action failed"
    ::= {sysSyncInfo 24 }

ssiSaveConfigDest   OBJECT-TYPE
    SYNTAX      TmnxDisplayStringURL
    MAX-ACCESS  read-write
    STATUS      current
    DESCRIPTION
        "The value of ssiSaveConfigDest specifies the destination filepath
         or file-URL where the current running configuration information
         will be saved when ssiSaveConfig is set to 'doAction'.  If
         ssiSaveConfigDest is set to the empty string, ''H, the primary
         configuration file pointed to in the boot options file (bof) will
         be backed up and a new primary configuration file will be created
         with the current running configuration information.

         A corresponding persistent SNMP index file is created regardless of
         the setting of the persistence switch in the bof."
    DEFVAL { ''H }  -- empty string
    ::= { sysSyncInfo 25 }

ssiSaveConfigDetail OBJECT-TYPE
    SYNTAX      TruthValue
    MAX-ACCESS  read-write
    STATUS      current
    DESCRIPTION
        "When ssiSaveConfigDetail has a value of 'true', the default
         configuration values will also be included in the current
         running configuration information that will be saved when
         ssiSaveConfig is set to 'doAction'.

         When ssiSaveConfigDetail has a value of 'false', only
         non-default configuration values are saved. "
    DEFVAL { false }
    ::= { sysSyncInfo 26 }

ssiRedFailoverTime  OBJECT-TYPE
    SYNTAX      TimeStamp
    MAX-ACCESS  read-only
    STATUS      current
    DESCRIPTION
        "The value of ssiRedFailoverTime is the timestamp when the last
         redundancy failover occurred causing a switchover from active
         to standby CPM.  If there is no redundant CPM card in this system
         or no failover has occurred since the system last booted,
         ssiRedFailoverTime will always return 0."
   ::= { sysSyncInfo 27 }

ssiRedFailoverReason    OBJECT-TYPE
    SYNTAX      DisplayString (SIZE (0..80))
    MAX-ACCESS  read-only
    STATUS      current
    DESCRIPTION
        "The value of ssiRedFailoverReason is a text string giving an
         explanation of the cause of the last redundancy failover.
         If no failover has occurred, the empty string, ''H, will be
         returned."
    ::= { sysSyncInfo 28 }

ssiSyncRollbackLastTime  OBJECT-TYPE
    SYNTAX      TimeStamp
    MAX-ACCESS  read-only
    STATUS      current
    DESCRIPTION
        "The value of ssiSyncRollbackLastTime is the timestamp of the last
         successful synchronization of the rollback files."
    ::= { sysSyncInfo 29 }

ssiSyncRollbackMode     OBJECT-TYPE
    SYNTAX      TmnxSsiSyncRollbackMode
    MAX-ACCESS  read-write
    STATUS      current
    DESCRIPTION
        "The value of ssiSyncRollbackMode specifies the type of synchronization
         operation to perform between the primary and secondary CPMs
         after a change has been made to the rollback files."
   DEFVAL { none }
   ::= { sysSyncInfo 30 }

ssiSyncRollbackForce    OBJECT-TYPE
    SYNTAX      TmnxSsiSyncRollbackMode
    MAX-ACCESS  read-write
    STATUS      current
    DESCRIPTION
        "The value of ssiSyncRollbackForce specifies the type of synchronization
         operation to perform when an SNMP set is made to this object.
         'rollbackSingle' synchronizes only the rollback file that recently
          changed.
         'rollbackAll' synchronizes all rollback files.

         The result of a read operation on this object is always 'none'."
    DEFVAL { none }
    ::= { sysSyncInfo 31 }

ssiSyncRollbackStatus   OBJECT-TYPE
    SYNTAX      INTEGER {
                    unknown (0),
                    rollbackFail (1),
                    rollbackInProgress (2),
                    rollbackSuccess (3)
                }
    MAX-ACCESS  read-only
    STATUS      current
    DESCRIPTION
        "The value of ssiSyncRollbackStatus indicates the results of the last
         rollback synchronization operation between the primary and secondary 
         CPMs."
    ::= { sysSyncInfo 32 }

ssiSyncCertLastTime  OBJECT-TYPE
    SYNTAX      TimeStamp
    MAX-ACCESS  read-only
    STATUS      current
    DESCRIPTION
        "The value of ssiSyncCertLastTime is the timestamp of the last
         successful synchronization of the certificate files."
    ::= { sysSyncInfo 33 }

ssiSyncCertMode     OBJECT-TYPE
    SYNTAX      TruthValue
    MAX-ACCESS  read-write
    STATUS      current
    DESCRIPTION
        "The value of ssiSyncCertMode specifies whether to synchronize
         certificate files between the primary and secondary CPMs."
   DEFVAL { true }
   ::= { sysSyncInfo 34 }

ssiSyncCertForce    OBJECT-TYPE
    SYNTAX      TmnxActionType
    MAX-ACCESS  read-write
    STATUS      current
    DESCRIPTION
        "The value of ssiSyncCertForce specifies to perform action to
         synchronize certificate files between the primary and secondary CPMs
         when an SNMP set is made to this object.
         
         The value of ssiSyncCertForce will always be returned as
         'notApplicable'."
    DEFVAL { notApplicable }
    ::= { sysSyncInfo 35 }

ssiSyncCertStatus   OBJECT-TYPE
    SYNTAX      INTEGER {
                    unknown (0),
                    fail (1),
                    inProgress (2),
                    success (3)
                }
    MAX-ACCESS  read-only
    STATUS      current
    DESCRIPTION
        "The value of ssiSyncCertStatus indicates the results of the last
         certificate synchronization operation between the primary and
         secondary CPMs."
    ::= { sysSyncInfo 36 }


--
--      System Bootup information
--
sysBootInfo     OBJECT IDENTIFIER ::= { tmnxSysObjs 5 }

sbiConfigStatus OBJECT-TYPE
    SYNTAX      INTEGER {
                    configRead (1),
                    configOK (2),
                    defaultBooted (3),
                    bootConfigFailed (4),
                    bootRestoreFailed (5)
                }
    MAX-ACCESS  read-only
    STATUS      current
    DESCRIPTION
        "The value of sbiConfigStatus indicates the result of the
         last attempt to execute the configuration file upon reboot
         of the system.
            configRead (1) - The configuration file is being read.
            configOK (2) - The configuration file was successfully
                    executed.
            defaultBooted (3) - There was no configuration file and
                    the system booted using a minimal
                    default configuration.
            bootConfigFailed (4) - An error occurred while the
                    configuration file was being executed.
                    The system configuration is incomplete.
            bootRestoreFailed (5) - An error occurred while the
                    restoration was being performed. The system
                    configuration is incomplete."
    ::= { sysBootInfo 1 }

sbiPersistStatus    OBJECT-TYPE
    SYNTAX      INTEGER {
                    persistOK (1),
                    noPersistFile (2),
                    persistMismatch (3),
                    persistIndexFailure (4),
                    persistDisabled (5),
                    persistInvalid (6),
                    persistBoot (7),
                    persistInit (8),
                    persistInProgress (9)

                }
    MAX-ACCESS  read-only
    STATUS      current
    DESCRIPTION
        "The value of sbiPersistStatus indicates the state of the
         rebuild of the SNMP persistent index database upon reboot of the
         system.
            persistOK (1) - The persistent index database was
                successfully created.  Persistent SNMP managed
                objects were recreated with the same SNMP
                indexes they had prior to the system reboot.
            noPersistFile (2) - There was no persistent index file with
                the same pathname as the configuration file.
            persistMismatch (3) -The headers in the persistent index
                file and the configuration file with the same name
                do not match.
            persistIndexFailure (4) - An error occurred while creating
                the persistent index database.
            persistDisabled (5) - The system was administratively
                reconfigured without maintaining persistent SNMP index
                values because sbiPersistIndex has a value of 'false'.
            persistInvalid (6) - Persistent index database was not
                                 initialized.
            persistBoot(7) - The persistent index database was in the
                             pre-initial bootup state.
            persistInit(8) - The persistent index database is initializing.
            persistInProgress(9) - The initial bootup file is loading, using the
                                   persist index database. Once complete, the
                                   persist state will go to 'persistOk (1)' if
                                   successful.

         If sbiConfigStatus has a value of 'configOK' and
         sbiPersistStatus has any value other than 'persistOK', the
         system was reconfigured without maintaining persistent SNMP index
         values.  Unless sbiPersistIndex has a value of 'false',
         sbiSnmpdOperStatus returns 'disabled' and the SNMP daemon will not
         receive SNMP requests until sbiSnmpdAdminStatus variable has
         been set to 'inService'."
    ::= { sysBootInfo 2 }

sbiPersistIndex      OBJECT-TYPE
    SYNTAX      TruthValue
    MAX-ACCESS  read-only
    STATUS      current
    DESCRIPTION
        "When sbiPersistIndex has a value of 'true', the SNMP persistent index
         database was rebuilt when the system was rebooted.  If there was an
         error during the processing of the configuration file the system may
         have been reconfigured without persistent SNMP indexes and the SNMP
         daemon will be suspended until it is manually enabled by setting
         sbiSnmpdAdminStatus to 'inService.  When sbiPersistIndex has a
         value of 'false' the system was reconfigured without maintaining
         persistent SNMP index values and the SNMP daemon was enabled."
    ::= { sysBootInfo 3 }

sbiSnmpdAdminStatus     OBJECT-TYPE
    SYNTAX      TmnxAdminState
    MAX-ACCESS  read-write
    STATUS      current
    DESCRIPTION
        "The value of sbiSnmpdAdminStatus is the desired administrative state
         for the SNMP daemon.  When sbiSnmpdAdminStatus is set to 'inService'
         the SNMP daemon will begin receiving SNMP requests from external
         SNMP managers.  When sbiSnmpdAdminStatus is set to 'outOfService'
         the SNMP daemon is suspended and will no longer receive SNMP requests
         from external SNMP managers."
    DEFVAL { inService }
    ::= { sysBootInfo 4 }

sbiSnmpdOperStatus  OBJECT-TYPE
    SYNTAX      TmnxOperState
    MAX-ACCESS  read-only
    STATUS      current
    DESCRIPTION
        "When sbiSnmpdOperStatus has a value of 'inService', the SNMP daemon
         will receive SNMP requests from external SNMP managers.  When
         sbiSnmpdOperStatus has a value of 'outOfService', the SNMP daemon is
         suspended and will not receive SNMP requests from external SNMP
         managers."
    ::= { sysBootInfo 5 }

sbiSnmpdMaxPktSize  OBJECT-TYPE
    SYNTAX       Integer32 (484..9216)
    MAX-ACCESS   read-write
    STATUS       current
    DESCRIPTION
        "The value of sbiSnmpdMaxPktSize specifies the maximum length in
         octets of an SNMP message which the SNMP daemon can send or
         receive and process."
    DEFVAL { 1500 }
    ::= { sysBootInfo 6 }

sbiSnmpdPortNum     OBJECT-TYPE
    SYNTAX      TTcpUdpPort
    MAX-ACCESS  read-write
    STATUS      current
    DESCRIPTION
        "The value of sbiSnmpdPortNum specifies the UDP port to send and
         receive SNMP messages."
    DEFVAL { 161 }
    ::= { sysBootInfo 7 }

sbiBootConfigOKScript     OBJECT-TYPE
    SYNTAX      DisplayString
    MAX-ACCESS  read-write
    STATUS      current
    DESCRIPTION
        "The value of sbiBootConfigOKScript specifies the location and name of
         the CLI script file executed following successful completion
         of the boot-up configuration file execution. I.e. sbiPersistStatus
         has a value of 'configOK'.  When this object has the empty string
         value, ''H, no CLI script file is executed."
    DEFVAL { ''H }  -- the empty string
    ::= { sysBootInfo 8 }

sbiConfigOKScriptStatus OBJECT-TYPE
    SYNTAX      INTEGER {
                    notRun (0),
                    success (1),
                    fail    (2)
                }
    MAX-ACCESS  read-only
    STATUS      current
    DESCRIPTION
        "The value of sbiConfigOKScriptStatus indicates the results of
         executing the CLI script file specified in sbiBootConfigOKScript."
    ::= { sysBootInfo 9 }

sbiBootConfigFailScript     OBJECT-TYPE
    SYNTAX      DisplayString
    MAX-ACCESS  read-write
    STATUS      current
    DESCRIPTION
        "The value of sbiBootConfigFailScript specifies the location and
         name of the CLI script file executed following failure of the
         boot-up configuration file execution. I.e. sbiPersistStatus
         has a value other than 'configOK'.  When this object has the empty
         string value, ''H, no CLI script file is executed."
    DEFVAL { ''H }  -- the empty string
    ::= { sysBootInfo 10 }

sbiConfigFailScriptStatus OBJECT-TYPE
    SYNTAX      INTEGER {
                    notRun (0),
                    success (1),
                    fail    (2)
                }
    MAX-ACCESS  read-only
    STATUS      current
    DESCRIPTION
        "The value of sbiConfigFailScriptStatus indicates the results of
         executing the CLI script file specified in sbiBootConfigFailScript."
    ::= { sysBootInfo 11 }

sbiRedSwitchoverScript     OBJECT-TYPE
    SYNTAX      DisplayString
    MAX-ACCESS  read-write
    STATUS      current
    DESCRIPTION
        "The value of sbiRedSwitchoverScript specifies the location and
         name of the CLI script file executed following a redundancy
         switchover from the previously active CPM card. A switchover
         can happen because of a fatal failure or by manual action.
         This CLI script file can contain commands for environment settings,
         debug and mirroring settings, and other commands not maintained by
         the configuration redundancy.

         When this object has the empty string value, ''H, no CLI script
         file is executed."
    DEFVAL { ''H }  -- the empty string
    ::= { sysBootInfo 12 }

sbiRedSwitchoverScriptStatus OBJECT-TYPE
    SYNTAX      INTEGER {
                    notRun (0),
                    success (1),
                    fail    (2)
                }
    MAX-ACCESS  read-only
    STATUS      current
    DESCRIPTION
        "The value of sbiRedSwitchoverScriptStatus indicates the results of
         executing the CLI script file specified in sbiRedSwitchoverScript."
    ::= { sysBootInfo 13 }

--
--      RADIUS (Remote Authentication Dial In User Service) Information
--

sysRadiusInfo     OBJECT IDENTIFIER ::= { tmnxSysObjs 6 }

radiusOperStatus  OBJECT-TYPE
    SYNTAX      INTEGER {
                    up (1),
                    down (2)
                }
    MAX-ACCESS  read-only
    STATUS      current
    DESCRIPTION
        "The radiusOperStatus will have a value of 'up' if any
        one of the RADIUS servers in the radiusServerTable has
        the radiusServerOperStatus value of 'up'.
        It will have a value of 'down' if all the RADIUS servers in the
        radiusServerTable have the radiusServerOperStatus value of 'down'."
    ::= { sysRadiusInfo 1 }

radiusServerTable OBJECT-TYPE
    SYNTAX      SEQUENCE OF RadiusServerEntry
    MAX-ACCESS  not-accessible
    STATUS      current
    DESCRIPTION
        "The radiusServerEntry has an entry for each RADIUS server.
        The table can have up to a maximum of 5 entries.

        Use TIMETRA-SECURITY-MIB::tmnxRadiusServerTable to configure entries."
::= { sysRadiusInfo 2 }

radiusServerEntry OBJECT-TYPE
    SYNTAX      RadiusServerEntry
    MAX-ACCESS  not-accessible
    STATUS      current
    DESCRIPTION
        "Each row entry contains information about a RADIUS server."
    INDEX {radiusServerIndex}
    ::= { radiusServerTable 1 }

RadiusServerEntry ::=
    SEQUENCE {
        radiusServerIndex             Unsigned32,
        radiusServerAddress           IpAddress,
        radiusServerOperStatus        INTEGER,
        radiusServerInetAddressType   InetAddressType,
        radiusServerInetAddress       InetAddress
    }

radiusServerIndex OBJECT-TYPE
    SYNTAX      Unsigned32 (1..5)
    MAX-ACCESS  not-accessible
    STATUS      current
    DESCRIPTION
        "The unique value which identifies a specific radius server."
    ::= { radiusServerEntry 1 }

radiusServerAddress OBJECT-TYPE
    SYNTAX      IpAddress
    MAX-ACCESS  read-only
    STATUS      obsolete
    DESCRIPTION
        "The IP address of the RADIUS server.

        This object was made obsolete in the 5.0 release."
    ::= { radiusServerEntry 2 }

radiusServerOperStatus OBJECT-TYPE
    SYNTAX      INTEGER {
                    up (1),
                    down (2)
                }
    MAX-ACCESS  read-only
    STATUS      current
    DESCRIPTION
        "Current status of the RADIUS server."
    ::= { radiusServerEntry 3 }

radiusServerInetAddressType      OBJECT-TYPE
    SYNTAX      InetAddressType
    MAX-ACCESS  read-only
    STATUS      current
    DESCRIPTION
        "The value of radiusServerInetAddressType indicates the address type
         of radiusServerInetAddress address."
    ::= { radiusServerEntry 4 }

radiusServerInetAddress     OBJECT-TYPE
    SYNTAX      InetAddress (SIZE(0|4|16|20))
    MAX-ACCESS  read-only
    STATUS      current
    DESCRIPTION
        "The value of radiusServerInetAddress indicates the address of
         the Radius server."
    ::= { radiusServerEntry 5 }

--
-- Notification Control Objects section
--
tmnxSysNotifyObjs      OBJECT IDENTIFIER ::= { tmnxSysObjs 7 }

tmnxNotifyRow    OBJECT-TYPE
    SYNTAX       RowPointer
    MAX-ACCESS   accessible-for-notify
    STATUS       current
    DESCRIPTION
        "tmnxNotifyRow is used by the configuration modify, create
         and delete traps. tmnxNotifyRow specifies the OID of the
         MIB table entry that was changed."
    ::= { tmnxSysNotifyObjs 1 }

tmnxNotifyRowAdminState     OBJECT-TYPE
    SYNTAX       TmnxAdminState
    MAX-ACCESS   accessible-for-notify
    STATUS       current
    DESCRIPTION
        "tmnxNotifyRowAdminState is used by the state change
         notification to specify the administrative state of
         the MIB table entry reported in the notification."
    ::= { tmnxSysNotifyObjs 2 }

tmnxNotifyRowOperState     OBJECT-TYPE
    SYNTAX       TmnxOperState
    MAX-ACCESS   accessible-for-notify
    STATUS       current
    DESCRIPTION
        "tmnxNotifyRowOperState is used by the state change
         notification to specify the operational state of
         the MIB table entry reported in the notification."
    ::= { tmnxSysNotifyObjs 3 }

tmnxMemoryModule    OBJECT-TYPE
    SYNTAX       TNamedItem
    MAX-ACCESS   accessible-for-notify
    STATUS       current
    DESCRIPTION
        "tmnxMemoryModule is used by the module malloc failed
         notification to specify the memory module for which
         the trap is generated."
    ::= { tmnxSysNotifyObjs 4 }

tmnxModuleMallocSize    OBJECT-TYPE
    SYNTAX       Unsigned32
    UNITS        "bytes"
    MAX-ACCESS   accessible-for-notify
    STATUS       current
    DESCRIPTION
        "tmnxModuleMallocSize is used by the module malloc
         failed notification to specify the memory size (in
         bytes) requested in the failed malloc call."
    ::= { tmnxSysNotifyObjs 5 }

tmnxDroppedTrapID    OBJECT-TYPE
    SYNTAX       OBJECT IDENTIFIER
    MAX-ACCESS   accessible-for-notify
    STATUS       current
    DESCRIPTION
        "tmnxDroppedTrapID is used by the trap dropped
         notification to specify the NOTIFICATION-TYPE
         object identifier of the dropped trap."
    ::= { tmnxSysNotifyObjs 6 }

tmnxTrapDroppedReasonCode    OBJECT-TYPE
    SYNTAX       INTEGER {
                     frequencyExceeded (1)
                 }
    MAX-ACCESS   accessible-for-notify
    STATUS       current
    DESCRIPTION
        "tmnxTrapDroppedReasonCode is used by the trap
         dropped notification to specify the reason for
         which a trap is dropped."
    ::= { tmnxSysNotifyObjs 7 }

tmnxTrapDroppedEntryID    OBJECT-TYPE
    SYNTAX       OBJECT IDENTIFIER
    MAX-ACCESS   accessible-for-notify
    STATUS       current
    DESCRIPTION
        "tmnxTrapDroppedEntryID is used by the trap dropped
         notification to specify the table entry associated
         with the dropped trap."
    ::= { tmnxSysNotifyObjs 8 }

tmnxNotifyEntryOID    OBJECT-TYPE
    SYNTAX       OBJECT IDENTIFIER
    MAX-ACCESS   accessible-for-notify
    STATUS       current
    DESCRIPTION
        "tmnxNotifyEntryOID is used by the configuration modify, create
         and delete traps. tmnxNotifyEntryOID specifies the OID of the
         MIB table that was changed."
    ::= { tmnxSysNotifyObjs 9 }

tmnxSnmpdErrorMsg   OBJECT-TYPE
    SYNTAX      DisplayString
    MAX-ACCESS  accessible-for-notify
    STATUS      current
    DESCRIPTION
        "tmnxSnmpdErrorMsg is used by the tmnxSnmpdError notification to
         indicate the type of SNMP daemon error detected."
    ::= { tmnxSysNotifyObjs 10 }

tmnxPersistencyClient   OBJECT-TYPE
    SYNTAX      DisplayString
    MAX-ACCESS  accessible-for-notify
    STATUS      current
    DESCRIPTION
        "tmnxPersistencyClient is used by the persistencyClosedAlarmRaised,
         persistencyClosedAlarmCleared, persistencyFileSysThresRaised and
         persistencyFileSysThresCleared notification to indicate the affected
         persistent application."
    ::= { tmnxSysNotifyObjs 11 }

tmnxPersistencyFileLocator   OBJECT-TYPE
    SYNTAX      DisplayString
    MAX-ACCESS  accessible-for-notify
    STATUS      current
    DESCRIPTION
        "tmnxPersistencyFileLocator is used by the persistencyClosedAlarmRaised,
         persistencyClosedAlarmCleared, persistencyFileSysThresRaised and
         persistencyFileSysThresCleared notification to indicate the affected
         file used to store persistence data."
    ::= { tmnxSysNotifyObjs 12 }

tmnxPersistencyNotifyMsg   OBJECT-TYPE
    SYNTAX      DisplayString
    MAX-ACCESS  accessible-for-notify
    STATUS      current
    DESCRIPTION
        "tmnxPersistencyNotifyMsg is used by the persistencyClosedAlarmRaised
         persistencyClosedAlarmCleared, persistencyEventReport,
         persistencyFileSysThresRaised and persistencyFileSysThresCleared
         notification to provide additional information related to the event
         that occurred."
    ::= { tmnxSysNotifyObjs 13 }

tmnxPersistenceAffectedCpm   OBJECT-TYPE
    SYNTAX      DisplayString
    MAX-ACCESS  accessible-for-notify
    STATUS      current
    DESCRIPTION
        "tmnxPersistenceAffectedCpm is used by the persistencyClosedAlarmRaised,
         persistencyClosedAlarmCleared, persistencyFileSysThresRaised and
         persistencyFileSysThresCleared notification to indicate the affected
         CPM."
    ::= { tmnxSysNotifyObjs 14 }

tmnxSysTimeSetBy   OBJECT-TYPE
    SYNTAX      INTEGER {
                    ntp (1),
                    sntp (2),
                    snmp (3),
                    manually (4),
                    rtc (5)    -- real time clock
                }
    MAX-ACCESS  accessible-for-notify
    STATUS      current
    DESCRIPTION
        "tmnxSysTimeSetBy is used by tmnxSysTimeSetBy notification to
         indicate who set the time."
    ::= { tmnxSysNotifyObjs 15 }

tmnxFtpFailureMsg   OBJECT-TYPE
    SYNTAX      DisplayString
    MAX-ACCESS  accessible-for-notify
    STATUS      current
    DESCRIPTION
        "tmnxFtpFailureMsg is used by tmnxFtpClientFailure notification to
         indicate FTP error."
    ::= { tmnxSysNotifyObjs 16 }

tmnxFtpFailureDestAddressType OBJECT-TYPE
    SYNTAX      InetAddressType
    MAX-ACCESS  accessible-for-notify
    STATUS      current
    DESCRIPTION
        "tmnxFtpFailureDestAddressType is used by tmnxFtpClientFailure
         notification to indicate the IP address type of the remote host."
    ::= { tmnxSysNotifyObjs 17 }

tmnxFtpFailureDestAddress OBJECT-TYPE
    SYNTAX      InetAddress (SIZE (4|16|20))
    MAX-ACCESS  accessible-for-notify
    STATUS      current
    DESCRIPTION
        "The value of tmnxFtpFailureDestAddress indicates the IP address of
         the remote host to which an ftp operation is being attempted on. The
         value of tmnxFtpFailureDestAddress is used by tmnxFtpClientFailure
         notification."
    ::= { tmnxSysNotifyObjs 18 }

tmnxNotifyObjectName    OBJECT-TYPE
    SYNTAX       DisplayString
    MAX-ACCESS   accessible-for-notify
    STATUS       current
    DESCRIPTION
        "tmnxNotifyObjectName is used by the configuration modify, create,
         delete and state change traps. tmnxNotifyObjectName specifies the 
         human readable name of the OID instance of the MIB table entry that 
         was changed."
    ::= { tmnxSysNotifyObjs 19 }

tmnxSyncFailureReason   OBJECT-TYPE
    SYNTAX      DisplayString
    MAX-ACCESS  accessible-for-notify
    STATUS      current
    DESCRIPTION
        "tmnxSyncFailureReason is used by the ssiSyncConfigFailed,
        ssiSyncBootEnvFailed, and ssiSyncRollbackFailed traps to specify 
        the reason for synchronization failure."
    ::= { tmnxSysNotifyObjs 20 }

tmnxSysExecScript   OBJECT-TYPE
    SYNTAX      DisplayString
    MAX-ACCESS  accessible-for-notify
    STATUS      current
    DESCRIPTION
        "The value of tmnxSysExecScript specifies the location and name of
         the CLI command script file executed by a SROS CLI 'exec' command when
         the value of tmnxLogExRbkOpType is 'exec (1)'. 

         When the value of tmnxLogExRbkOpType is 'vsd (4)', then the value of
         tmnxSysExecScript specifies an empty string.

         It is used by the tmnxSysExecStarted and tmnxSysExecFinished
         notifications."
    ::= { tmnxSysNotifyObjs 21 }

tmnxSysExecResult OBJECT-TYPE
    SYNTAX      INTEGER {
                    none    (0),
                    success (1),
                    fail    (2)
                }
    MAX-ACCESS  accessible-for-notify
    STATUS      current
    DESCRIPTION
        "The value of tmnxSysExecResult indicates the results of
         executing the CLI script file specified in tmnxSysExecScript.
         It is used by the tmnxSysExecFinished notification."
    ::= { tmnxSysNotifyObjs 22 }

tmnxSysRollbackFileType   OBJECT-TYPE
    SYNTAX      INTEGER {
                    rollback (1),
                    rescue (2)
                }
    MAX-ACCESS  accessible-for-notify
    STATUS      current
    DESCRIPTION
        "tmnxSysRollbackFileType is used by tmnxSysRollbackStarted,
        tmnxSysRollbackSaveStarted, tmnxSysRollbackDeleteStarted,
        tmnxSysRollbackStatusChange, tmnxSysRollbackSaveStatusChange, and
        tmnxSysRollbackFileDeleteStatus notifications to indicate
        the type of file involved in a rollback operation."
    ::= { tmnxSysNotifyObjs 23 }

tmnxSysFileErrorType   OBJECT-TYPE
    SYNTAX      INTEGER {
                    read (1),
                    write (2)
                }
    MAX-ACCESS  accessible-for-notify
    STATUS      current
    DESCRIPTION
        "tmnxSysFileErrorType is used by tmnxSysNvsysFileError
         notification to indicate the type of file error occurred."
    ::= { tmnxSysNotifyObjs 24 }

tmnxTrapDroppedCount    OBJECT-TYPE
    SYNTAX       Unsigned32
    MAX-ACCESS   accessible-for-notify
    STATUS       current
    DESCRIPTION
        "The object tmnxTrapDroppedCount is used by the tmnxTrapDropped
         notification to indicate the number of traps dropped.
         
         The value zero indicates that the number of traps dropped is 
         purposely not included in the notification, for example because
         it is not accurately known."
    ::= { tmnxSysNotifyObjs 25 }

tmnxSysDNSSecDomainName OBJECT-TYPE
    SYNTAX      TmnxDisplayStringURL
    MAX-ACCESS  accessible-for-notify
    STATUS      current
    DESCRIPTION
        "tmnxSysDNSSecDomainName is used by the sysDNSSecFailedAuthentication
         notification to indicate the domain name of the DNS query."
    ::= { tmnxSysNotifyObjs 26 }

tmnxSysLicenseErrorReason        OBJECT-TYPE
    SYNTAX       TItemDescription
    MAX-ACCESS   accessible-for-notify
    STATUS       current
    DESCRIPTION
        "The object tmnxSysLicenseErrorReason indicates the reason for an
         invalid license."
    ::= { tmnxSysNotifyObjs 27 }

tmnxSysLicenseTimeLeft           OBJECT-TYPE
    SYNTAX       Unsigned32
    UNITS        "minutes"
    MAX-ACCESS   accessible-for-notify
    STATUS       current
    DESCRIPTION
        "The object tmnxSysLicenseTimeLeft indicates the time remaining for the
         system to reboot as the result of an invalid license."
    ::= { tmnxSysNotifyObjs 28 }

tmnxSysNotifVsdServerName  OBJECT-TYPE
   SYNTAX      TLDisplayString 
   MAX-ACCESS  accessible-for-notify
   STATUS      current
   DESCRIPTION
       "The value of tmnxSysNotifVsdServerName specifies the VSD server name."
   ::= { tmnxSysNotifyObjs 30 }

tmnxSysNotifXmppServerName    OBJECT-TYPE
    SYNTAX          DisplayString (SIZE (0..32))
    MAX-ACCESS      accessible-for-notify
    STATUS          current
    DESCRIPTION
        "The value of tmnxSysNotifXmppServerName indicates the name associated
         with the XMPP Server."
    ::= { tmnxSysNotifyObjs 31 }

tmnxSysLicenseErrorAction        OBJECT-TYPE
    SYNTAX       TItemDescription
    MAX-ACCESS   accessible-for-notify
    STATUS       current
    DESCRIPTION
        "The object tmnxSysLicenseErrorAction indicates the system action taken
         as a result of tmnxSysLicenseErrorReason."
    ::= { tmnxSysNotifyObjs 32 }

tmnxSysNotifAppStatsApplication    OBJECT-TYPE
    SYNTAX       TmnxSysLicenseApplication
    MAX-ACCESS   accessible-for-notify
    STATUS       current
    DESCRIPTION
        "The object tmnxSysNotifAppStatsApplication indicates
         an application in a virtual machine implementation that
         is subject to licensing."
    ::= { tmnxSysNotifyObjs 33 }

tmnxSysNotifAppStatsType    OBJECT-TYPE
    SYNTAX       TmnxSysLicenseAppStatsType
    MAX-ACCESS   accessible-for-notify
    STATUS       current
    DESCRIPTION
        "The object tmnxSysNotifAppStatsType indicates
         a type of statistics collected about an application
         in a virtual machine implementation subject to licensing."
    ::= { tmnxSysNotifyObjs 34 }

tmnxSysNotifAppStatsTime    OBJECT-TYPE
    SYNTAX       DateAndTime
    MAX-ACCESS   accessible-for-notify
    STATUS       current
    DESCRIPTION
        "The object tmnxSysNotifAppStatsTime indicates
         the time that the system collected statistics' values."
    ::= { tmnxSysNotifyObjs 35 }

--
--
--
--
sysLoginControlInfo     OBJECT IDENTIFIER ::= { tmnxSysObjs 8 }

slcFtpInboundMaxSessions     OBJECT-TYPE
    SYNTAX      Unsigned32 (0..5)
    MAX-ACCESS  read-write
    STATUS      current
    DESCRIPTION
        "The maximum number of concurrent inbound FTP sessions permitted."
    DEFVAL { 3 }
    ::= { sysLoginControlInfo 1 }

slcTelnetInboundMaxSessions     OBJECT-TYPE
    SYNTAX      Unsigned32 (0..50)
    MAX-ACCESS  read-write
    STATUS      current
    DESCRIPTION
        "The value of slcTelnetInboundMaxSessions specifies
         the maximum number of concurrent inbound telnet sessions permitted.
         
         Note: The actual number of permitted concurrent inbound TELNET 
         sessions may also be restricted by a system wide cumulative limit of
         50 concurrent inbound (SSH / TELNET) sessions."
    DEFVAL { 5 }
    ::= { sysLoginControlInfo 2 }

slcTelnetOutboundMaxSessions     OBJECT-TYPE
    SYNTAX      Unsigned32 (0..15)
    MAX-ACCESS  read-write
    STATUS      current
    DESCRIPTION
        "The value of slcTelnetOutboundMaxSessions specifies
         the maximum number of concurrent outbound telnet sessions permitted."
    DEFVAL { 5 }
    ::= { sysLoginControlInfo 3 }

slcPreLoginMessage     OBJECT-TYPE
    SYNTAX      TmnxLongDisplayString (SIZE (0..900))
    MAX-ACCESS  read-write
    STATUS      current
    DESCRIPTION
        "The message to be displayed prior to the login prompt of an inbound
         FTP or telnet session."
    DEFVAL { ''H }
    ::= { sysLoginControlInfo 4 }

slcPreLoginMessageInclName     OBJECT-TYPE
    SYNTAX      TruthValue
    MAX-ACCESS  read-write
    STATUS      current
    DESCRIPTION
        "If the value of slcPreLoginMessageInclName is set to 'TRUE', the
         slcPreLoginMessage which is displayed prior to the login prompt
         will contain the system name."
    DEFVAL { false }
    ::= { sysLoginControlInfo 5 }

slcMessageOfTheDay     OBJECT-TYPE
    SYNTAX      TmnxLongDisplayString (SIZE (0..900))
    MAX-ACCESS  read-write
    STATUS      current
    DESCRIPTION
        "The value of object slcMessageOfTheDay specifies
         the message to display when the user successfully logs in
         to an inbound FTP, Telnet, SSH or console session.

         If slcMessageOfTheDayType is set to 'motd-type-none(0)',
         the value of slcMessageOfTheDay is not displayed.

         If slcMessageOfTheDayType is set to 'motd-type-url(1)',
         the syntax of slcMessageOfTheDay is refined to TmnxDisplayStringURL.

         If slcMessageOfTheDayType is set to 'motd-type-text(2)',
         the value of slcMessageOfTheDay is the NVT ASCII text to display.

         Objects slcMessageOfTheDay and slcMessageOfTheDayType must be set
         together in the same SNMP SET request PDU."
    DEFVAL { ''H }
    ::= { sysLoginControlInfo 6 }

slcMessageOfTheDayType     OBJECT-TYPE
    SYNTAX      INTEGER
                {
                    motd-type-none(0),
                    motd-type-url(1),
                    motd-type-text(2)
                }
    MAX-ACCESS  read-write
    STATUS      current
    DESCRIPTION
        "The value of object slcMessageOfTheDayType specifies
         the type of slcMessageOfTheDay.

         If the value of slcMessageOfTheDayType is set to 'motd-type-none(0)',
         then the message of the day is not displayed.

         If the value of slcMessageOfTheDayType is set to 'motd-type-url(1)',
         then the message is fetched from the URL specified in
         object slcMessageOfTheDay.

         If the value of slcMessageOfTheDayType is set to 'motd-type-text(2)',
         then the value of slcMessageOfTheDay is displayed.

         Objects slcMessageOfTheDay and slcMessageOfTheDayType must be set
         together in the same SNMP SET request PDU."
    DEFVAL { motd-type-none }
    ::= { sysLoginControlInfo 7 }

slcLoginBanner     OBJECT-TYPE
    SYNTAX      TruthValue
    MAX-ACCESS  read-write
    STATUS      current
    DESCRIPTION
        "If the value of slcLoginBanner is set to 'true', the
         login banner containing Nokia copyright and version 
         information is displayed prior to the login prompt. If the value 
         is set to 'false', the login banner is not displayed."
    DEFVAL { true }
    ::= { sysLoginControlInfo 8 }

slcLoginExponentialBackOff OBJECT-TYPE
    SYNTAX        TruthValue
    MAX-ACCESS    read-write
    STATUS        current
    DESCRIPTION
        "The value of slcLoginExponentialBackOff specifies if
         exponential-backoff of the login prompt is enabled. Exponential-backoff
         is used to deter dictionary attacks. A value of 'true' specifies that
         exponential-backoff is enabled, while a value of 'false' indicates
         that exponential-backoff is disabled."
    DEFVAL { false }
    ::= { sysLoginControlInfo 9 }

slcTelnetGracefulShutdown OBJECT-TYPE
    SYNTAX      TruthValue
    MAX-ACCESS  read-write
    STATUS      current
    DESCRIPTION
        "The value of slcTelnetGracefulShutdown specifies if
         graceful shutdown is enabled. A value of 'true' specifies that telnet
         sessions are closed gracefully by using a TCP FIN/ACK handshake. 
         A value of 'false' indicates that telnet sessions are disconnected by
         sending a RST (reset) TCP packet."
    DEFVAL { false }
    ::= { sysLoginControlInfo 10 }

slcSSHGracefulShutdown OBJECT-TYPE
    SYNTAX      TruthValue
    MAX-ACCESS  read-write
    STATUS      current
    DESCRIPTION
        "The value of slcSSHGracefulShutdown specifies if
         graceful shutdown is enabled. A value of 'true' specifies that SSH
         sessions are closed gracefully by using a TCP FIN/ACK handshake.
         A value of 'false' indicates that SSH sessions are disconnected by
         sending a RST (reset) TCP packet."
    DEFVAL { true }
    ::= { sysLoginControlInfo 11 }

slcTelnetMinTTLValue OBJECT-TYPE
    SYNTAX      Unsigned32 (0 | 1..255)
    MAX-ACCESS  read-write
    STATUS      current
    DESCRIPTION
        "The value of slcTelnetMinTTLValue specifies the minimum
         TTL value for an incoming packet.

         This object can only be set if the value of tmnxCpmPerPeerQueuing is
         'true (1)'.

         This value is applied after restarting the Telnet server.

         If slcTelnetMinTTLValue is set to zero (0), the
         TTL Security feature is disabled."
    DEFVAL { 0 }
    ::= { sysLoginControlInfo 12 }

slcSSHMinTTLValue OBJECT-TYPE
    SYNTAX      Unsigned32 (0 | 1..255)
    MAX-ACCESS  read-write
    STATUS      current
    DESCRIPTION
        "The value of slcSSHMinTTLValue specifies the minimum
         TTL value for an incoming packet.

         This object can only be set if the value of tmnxCpmPerPeerQueuing is
         'true (1)'.

         This value is applied after restarting the SSH server.

         If slcSSHMinTTLValue is set to zero (0), the
         TTL Security feature is disabled."
    DEFVAL { 0 }
    ::= { sysLoginControlInfo 13 }

slcSSHInboundMaxSessions OBJECT-TYPE
    SYNTAX      Unsigned32 (0..50)
    MAX-ACCESS  read-write
    STATUS      current
    DESCRIPTION
        "The value of slcSSHInboundMaxSessions specifies
         the maximum number of concurrent inbound SSH sessions permitted.
         
         Note: The actual number of permitted concurrent inbound SSH sessions 
         may also be restricted by a system wide cumulative limit of 50 
         concurrent inbound (SSH / TELNET) sessions."
    DEFVAL { 5 }
    ::= { sysLoginControlInfo 14 }

slcSSHOutboundMaxSessions OBJECT-TYPE
    SYNTAX      Unsigned32 (0..15)
    MAX-ACCESS  read-write
    STATUS      current
    DESCRIPTION
        "The value of slcSSHOutboundMaxSessions specifies
         the maximum number of concurrent outbound SSH sessions permitted."
    DEFVAL { 5 }
    ::= { sysLoginControlInfo 15 }

slcIdleTimeout OBJECT-TYPE
    SYNTAX      Unsigned32 (1..1440 | 9999)
    UNITS       "minutes"
    MAX-ACCESS  read-write
    STATUS      current
    DESCRIPTION
        "The value of the object slcIdleTimeout specifies the maximum time of
         how long a user initiated session (console, telnet, SSH, FTP) can be
         inactive before it will be automatically closed by the system. The
         value of 9999 specifies that the system will never automatically close
         an inactive user initiated session."
    DEFVAL { 30 }
    ::= { sysLoginControlInfo 16 }

slcLoginScriptGlobal OBJECT-TYPE
    SYNTAX      TmnxDisplayStringURL
    MAX-ACCESS  read-write
    STATUS      current
    DESCRIPTION
        "The value of the object slcLoginScriptGlobal specifies the URL of a CLI
         script that is executed when any user opens a CLI session.

         This allows an operator, for example, to define a common set of CLI
         aliases that are made available on the router for all users. This
         global login-exec script is executed before any user-specific
         login-exec file that may be configured."
    DEFVAL { ''H }
    ::= { sysLoginControlInfo 17 }

slcLoginScriptPerUserDirectory OBJECT-TYPE
    SYNTAX      TmnxDisplayStringURL
    MAX-ACCESS  read-write
    STATUS      current
    DESCRIPTION
        "The value of the object slcLoginScriptPerUserDirectory specifies
         the user-directory of the per-user login script configured in
         slcLoginScriptPerUserFilename.

         This per-user script is executed before any other user-specific
         login script, like the one configured in tmnxUserConsoleLoginExecFile
         or the one speficied in RADIUS attribute Timetra-Exec-File (6527-8)."
    DEFVAL { ''H }
    ::= { sysLoginControlInfo 18 }

slcLoginScriptPerUserFilename OBJECT-TYPE
    SYNTAX      DisplayString (SIZE (0..180))
    MAX-ACCESS  read-write
    STATUS      current
    DESCRIPTION
        "The value of the object slcLoginScriptPerUserFilename specifies
         the filename of the per-user login script.

         The per-user login script is defined by concatenating the value of
         slcLoginScriptPerUserDirectory, the username, and the value of
         slcLoginScriptPerUserFilename. For example :
         If the value of slcLoginScriptPerUserDirectory is 'cf1:/local/users'
         and the value of slcLoginScriptPerUserFilename is 'login-script.txt',
         then file 'cf1:/local/users/john/login-script.txt' is executed
         when user 'john' opens a CLI session."
    DEFVAL { ''H }
    ::= { sysLoginControlInfo 19 }

sysLACPInfo     OBJECT IDENTIFIER ::= { tmnxSysObjs 9 }

sysLACPSystemPriority     OBJECT-TYPE
    SYNTAX      Unsigned32 (1..65535)
    MAX-ACCESS  read-write
    STATUS      current
    DESCRIPTION
        "sysLACPSystemPriority is the Link Aggregation Control Protocol (LACP)
         system priority which is combined with the system MAC address to
         make up a unique system ID that is used by LACP in communications
         with LACP peer systems on Link Aggregation (LAG) ports."
    DEFVAL      { 32768 }
    ::= { sysLACPInfo 1 }

--
-- TACACS+ (Terminal Access Controller Access Control System Plus) Information
--

sysTacplusInfo     OBJECT IDENTIFIER ::= { tmnxSysObjs 10 }

tacplusOperStatus  OBJECT-TYPE
    SYNTAX      INTEGER {
                    up (1),
                    down (2)
                }
    MAX-ACCESS  read-only
    STATUS      current
    DESCRIPTION
        "The tacplusOperStatus will have a value of 'up' if any
        one of the TACACS+ servers in the tacplusServerTable has
        the tacplusServerOperStatus value of 'up'.
        It will have a value of 'down' if all the TACACS+ servers in the
        tacplusServerTable have the tacplusServerOperStatus value of 'down'."
    ::= { sysTacplusInfo 1 }

tacplusServerTable OBJECT-TYPE
    SYNTAX      SEQUENCE OF TacplusServerEntry
    MAX-ACCESS  not-accessible
    STATUS      current
    DESCRIPTION
        "The tacplusServerEntry has an entry for each TACACS+ server.
        The table can have up to a maximum of 5 entries.

        Use TIMETRA-SECURITY-MIB::tmnxTacPlusServerTable to configure entries."
    ::= { sysTacplusInfo 2 }

tacplusServerEntry OBJECT-TYPE
    SYNTAX      TacplusServerEntry
    MAX-ACCESS  not-accessible
    STATUS      current
    DESCRIPTION
        "Each row entry contains information about a TACACS+ server."
    INDEX { tacplusServerIndex }
    ::= { tacplusServerTable 1 }

TacplusServerEntry ::=
    SEQUENCE {
        tacplusServerIndex           Unsigned32,
        tacplusServerAddress         IpAddress,
        tacplusServerOperStatus      INTEGER,
        tacPlusServerInetAddressType InetAddressType,
        tacPlusServerInetAddress     InetAddress
    }

tacplusServerIndex OBJECT-TYPE
    SYNTAX      Unsigned32 (1..5)
    MAX-ACCESS  not-accessible
    STATUS      current
    DESCRIPTION
        "The unique value which identifies a specific TACACS+ server."
    ::= { tacplusServerEntry 1 }

tacplusServerAddress OBJECT-TYPE
    SYNTAX      IpAddress
    MAX-ACCESS  read-only
    STATUS      obsolete
    DESCRIPTION
        "The IP address of the TACACS+ server.

        This object was made obsolete in the 5.0 release."
    ::= { tacplusServerEntry 2 }

tacplusServerOperStatus OBJECT-TYPE
    SYNTAX      INTEGER {
                    up (1),
                    down (2)
                }
    MAX-ACCESS  read-only
    STATUS      current
    DESCRIPTION
        "Current status of the TACACS+ server."
    ::= { tacplusServerEntry 3 }

tacPlusServerInetAddressType      OBJECT-TYPE
    SYNTAX      InetAddressType
    MAX-ACCESS  read-only
    STATUS      current
    DESCRIPTION
        "The value of tacPlusServerInetAddressType indicates the address type of
         tacPlusServerInetAddress address."
    ::= { tacplusServerEntry 4 }

tacPlusServerInetAddress     OBJECT-TYPE
    SYNTAX      InetAddress (SIZE(0|4|16|20))
    MAX-ACCESS  read-only
    STATUS      current
    DESCRIPTION
        "The value of tacPlusServerInetAddress indicates the address of
         the Tacplus server."
    ::= { tacplusServerEntry 5 }

--
-- Notification Definition section
--
stiDateAndTimeChanged NOTIFICATION-TYPE
    OBJECTS { stiDateAndTime }
    STATUS  current
    DESCRIPTION
        "The date and time changed  event is generated when the time on the
        system is modified either by explicit setting or automatic update in
        case of SNTP."
    ::= { tmnxSysNotifications 1 }

ssiSaveConfigSucceeded NOTIFICATION-TYPE
    STATUS  current
    DESCRIPTION
        "The save config succeeded event is generated when the saving of
        configuration finishes without errors."
    ::= { tmnxSysNotifications 2 }

ssiSaveConfigFailed NOTIFICATION-TYPE
    STATUS  current
    DESCRIPTION
        "The save config failed event is generated when the saving of
        configuration is stopped due to errors."
    ::= { tmnxSysNotifications 3 }

sbiBootConfig NOTIFICATION-TYPE
    OBJECTS {
            sbiConfigStatus,
            sbiPersistStatus,
            sbiPersistIndex
        }
    STATUS  current
    DESCRIPTION
        "The sbiBootConfig notification is generated upon
         completion of the configuration phase following
         a system reboot."
    ::= { tmnxSysNotifications 4 }

sbiBootSnmpd NOTIFICATION-TYPE
    OBJECTS {
        sbiPersistIndex,
        sbiSnmpdAdminStatus,
        sbiSnmpdOperStatus
    }
    STATUS  current
    DESCRIPTION
        "The sbiBootSnmpd notification is generated upon completion
         of the SNMP daemon initialization following a system reboot.
         Some system configuration and initialization errors may result
         in the SNMP daemon being suspended."
    ::= { tmnxSysNotifications 5 }

radiusServerOperStatusChange NOTIFICATION-TYPE
    OBJECTS {
        radiusServerAddress,
        radiusServerOperStatus
    }
    STATUS  obsolete
    DESCRIPTION
        "The radiusServerOperStatusChange notification is generated when the
         operational status of a RADIUS server has transitioned either
         from 'up' to 'down' or from 'down' to 'up'.

         This object was made obsolete in the 5.0 release."
    ::= { tmnxSysNotifications 6 }

radiusOperStatusChange NOTIFICATION-TYPE
    OBJECTS {
        radiusOperStatus
    }
    STATUS  current
    DESCRIPTION
        "The radiusOperStatusChange notification is generated when the
         radiusOperStatus has transitioned either from 'up' to 'down' or
         from 'down' to 'up'"
    ::= { tmnxSysNotifications 7 }

tmnxConfigModify NOTIFICATION-TYPE
    OBJECTS {
        tmnxNotifyRow,
        tmnxNotifyEntryOID,
        tmnxNotifyObjectName
    }
    STATUS  current
    DESCRIPTION
        "A tmnxConfigModify notification is generated when a
         configuration attribute associated with a row entry
         in a MIB table is modified. It can be used by the NMS
         to trigger maintenance polls of the configuration
         information."
    ::= { tmnxSysNotifications 8 }

tmnxConfigCreate NOTIFICATION-TYPE
    OBJECTS {
        tmnxNotifyRow,
        tmnxNotifyEntryOID,
        tmnxNotifyObjectName
    }
    STATUS  current
    DESCRIPTION
        "A tmnxConfigCreate notification is generated when a
         new row entry is created in one of the MIB tables.
         It can be used by the NMS to trigger maintenance
         polls of the configuration information."
    ::= { tmnxSysNotifications 9 }

tmnxConfigDelete NOTIFICATION-TYPE
    OBJECTS {
        tmnxNotifyRow,
        tmnxNotifyEntryOID,
        tmnxNotifyObjectName
    }
    STATUS  current
    DESCRIPTION
        "A tmnxConfigDelete notification is generated when an
         existing row entry in one of the MIB tables is deleted.
         It can be used by the NMS to trigger maintenance polls
         of the configuration information."
    ::= { tmnxSysNotifications 10 }

tmnxStateChange NOTIFICATION-TYPE
    OBJECTS {
        tmnxNotifyRow,
        tmnxNotifyRowAdminState,
        tmnxNotifyRowOperState,
        tmnxNotifyEntryOID,
        tmnxNotifyObjectName
    }
    STATUS  current
    DESCRIPTION
        "A tmnxStateChange notification is generated when there
         is a change in either the administrative or operational
         state of a MIB table entry."
    ::= { tmnxSysNotifications 11 }

tmnxModuleMallocFailed NOTIFICATION-TYPE
    OBJECTS {
        tmnxMemoryModule,
        tmnxModuleMallocSize
    }
    STATUS  current
    DESCRIPTION
        "A tmnxModuleMallocFailed notification is generated when
         a request to allocate memory from a particular module
         fails because the memory module is short on memory and
         cannot support the size that was requested."
    ::= { tmnxSysNotifications 12 }

tmnxTrapDropped NOTIFICATION-TYPE
    OBJECTS {
        tmnxDroppedTrapID,
        tmnxTrapDroppedReasonCode,
        tmnxTrapDroppedEntryID,
        tmnxTrapDroppedCount
    }
    STATUS  current
    DESCRIPTION
        "A tmnxTrapDropped notification is generated when
         a trap is dropped for the reason specified by the
         reason code. The tmnxTrapDroppedEntryID identifies
         the table entry associated with the dropped trap.
         
         A nonzero value of the object tmnxTrapDroppedCount indicates
         the number of traps dropped for the current flow of traps,
         identified by the values of tmnxDroppedTrapID, tmnxTrapDroppedReasonCode
         and tmnxTrapDroppedEntryID."
    ::= { tmnxSysNotifications 13 }

ssiSyncConfigOK NOTIFICATION-TYPE
    STATUS  current
    DESCRIPTION
        "The ssiSyncConfigOK event is generated when the
         synchronization of configuration files between the primary
         and secondary CPMs finishes without errors."
    ::= { tmnxSysNotifications 14 }

ssiSyncConfigFailed NOTIFICATION-TYPE
    OBJECTS {
        tmnxSyncFailureReason
    }
    STATUS  current
    DESCRIPTION
        "The ssiSyncConfigFailed event is generated when the
         synchronization of configuration files between the primary
         and secondary CPMs is stopped due to errors. The 
         tmnxSyncFailureReason will state reason for failure."
    ::= { tmnxSysNotifications 15 }

ssiSyncBootEnvOK NOTIFICATION-TYPE
    STATUS  current
    DESCRIPTION
        "The ssiSyncBootEnvOK event is generated when the
         synchronization of boot environment files between the
         primary and secondary CPMs finishes without errors."
    ::= { tmnxSysNotifications 16 }

ssiSyncBootEnvFailed NOTIFICATION-TYPE
    OBJECTS {
        tmnxSyncFailureReason        
    }
    STATUS  current
    DESCRIPTION
        "The ssiSyncBootEnvFailed event is generated when the
         synchronization of boot environment files between the primary
         and secondary CPMs is stopped due to errors. The 
         tmnxSyncFailureReason will state reason for failure."
    ::= { tmnxSysNotifications 17 }

sntpTimeDiffExceedsThreshold  NOTIFICATION-TYPE
    OBJECTS {
        sntpAdminState
    }
    STATUS  current
    DESCRIPTION
        "The sntpTimeDiffExceedsThreshold event is generated when the
         time differential between the system and the SNTP server is more
         than 10 seconds. In this case the system clock is not automatically
         adjusted."
    ::= { tmnxSysNotifications 18 }

tacplusServerOperStatusChange NOTIFICATION-TYPE
    OBJECTS {
        tacplusServerAddress,
        tacplusServerOperStatus
    }
    STATUS  obsolete
    DESCRIPTION
        "The tacplusServerOperStatusChange notification is generated when the
         operational status of a TACACS+ server has transitioned either
         from 'up' to 'down' or from 'down' to 'up'.

         This object was made obsolete in the 5.0 release."
    ::= { tmnxSysNotifications 19 }

tacplusOperStatusChange NOTIFICATION-TYPE
    OBJECTS {
        tacplusOperStatus
    }
    STATUS  current
    DESCRIPTION
        "The tacplusOperStatusChange notification is generated when the
         tacplusOperStatus has transitioned either from 'up' to 'down' or
         from 'down' to 'up'"
    ::= { tmnxSysNotifications 20 }

tmnxSnmpdError  NOTIFICATION-TYPE
    OBJECTS {
        tmnxSnmpdErrorMsg
    }
    STATUS  current
    DESCRIPTION
        "The tmnxSnmpdError notification is generated when the SNMP daemon
         detects an error condition."
    ::= { tmnxSysNotifications 21 }

tmnxSsiMismatch  NOTIFICATION-TYPE
    OBJECTS {
        ssiSyncMode,
        sbiPersist
    }
    STATUS  current
    DESCRIPTION
            "The tmnxSsiMismatch notification is generated by a system with
         redundant CPM cards after the processing of the bootup
         configuration has completed when ssiSyncMode has a  value of 'none'
         and sbiPersist has a value of 'true'.  This can result in SNMP
         indexes having different values following a system failover."
    ::= { tmnxSysNotifications 22 }

tmnxSnmpdStateChange    NOTIFICATION-TYPE
    OBJECTS {
        sbiSnmpdAdminStatus,
        sbiSnmpdOperStatus
    }
    STATUS  current
    DESCRIPTION
        "The tmnxSnmpdStateChange notification is generated whenever there
         is a change in either the administrative or operational state of
         the SNMP agent."
    ::= { tmnxSysNotifications 23 }

tmnxConfigConflict NOTIFICATION-TYPE
    OBJECTS {
        tmnxNotifyRow,
        tmnxNotifyEntryOID,
        tmnxNotifyObjectName
    }
    STATUS  current
    DESCRIPTION
        "A tmnxConfigConflict notification is generated when a
         configuration attribute associated with a row entry
         in a MIB table is in conflict with another attribute. 
         
         It can be used by the NMS to trigger maintenance polls 
         of the configuration information."
    ::= { tmnxSysNotifications 58 }

--
--  Redundancy notifications
--

ssiRedStandbySyncing     NOTIFICATION-TYPE
   OBJECTS {
        tmnxChassisNotifyHwIndex,
        tmnxHwID,
        tmnxHwClass
    }
    STATUS  current
    DESCRIPTION
        "The ssiRedStandbySyncing notification is generated when
         synchronization of redundancy information onto the standby
         CPM is started.  tmnxChassisNotifyHwIndex identifies the
         standby CPM."
    ::= { tmnxSysNotifications 24 }

ssiRedStandbyReady      NOTIFICATION-TYPE
    OBJECTS {
        tmnxChassisNotifyHwIndex,
        tmnxHwID,
        tmnxHwClass
    }
    STATUS  current
    DESCRIPTION
        "The ssiRedStandbyReady notification is generated when the
         synchronization of redundancy information onto the standby CPM
         has completed.  The standby CPM is now ready to take over
         control of the system if the active CPM fails or a manual
         switchover command is issued.  tmnxChassisNotifyHwIndex
         identifies the standby CPM."
    ::= { tmnxSysNotifications 25 }

ssiRedStandbySyncLost          NOTIFICATION-TYPE
    OBJECTS {
        tmnxChassisNotifyHwIndex,
        tmnxHwID,
        tmnxHwClass
    }
    STATUS  current
    DESCRIPTION
        "The ssiRedStandbySyncLost notification is generated when the active
         CPM looses communication with the standby CPM.
         tmnxChassisNotifyHwIndex identifies the lost standby CPM."
    ::= { tmnxSysNotifications 26 }

ssiRedSwitchover        NOTIFICATION-TYPE
    OBJECTS {
        tmnxChassisNotifyHwIndex,
        tmnxHwID,
        tmnxHwClass,
        ssiRedFailoverTime,
        ssiRedFailoverReason
    }
    STATUS  current
    DESCRIPTION
        "The ssiRedSwitchover notification is generated when the standby
         CPM detects that the active CPM has failed and the standby prepares
         to take over as the new active CPM.  tmnxChassisNotifyHwIndex
         identifies the new active CPM."
    ::= { tmnxSysNotifications 27 }

ssiRedCpmActive     NOTIFICATION-TYPE
    OBJECTS {
        tmnxChassisNotifyHwIndex,
        tmnxHwID,
        tmnxHwClass
    }
    STATUS  current
    DESCRIPTION
        "The ssiRedCpmActive notification is generated following a
         redundancy switchover when the new active CPM has completed
         its audit and is ready to accept management commands via CLI
         or SNMP SET requests.  tmnxChassisNotifyHwIndex identifies
         the new active CPM."
    ::= { tmnxSysNotifications 28 }

ssiRedSingleCpm   NOTIFICATION-TYPE
    OBJECTS {
        tmnxChassisNotifyHwIndex,
        tmnxHwID,
        tmnxHwClass
    }
    STATUS current
    DESCRIPTION
        "The ssiRedSingleCpm notification is generated by a system with
         a chassis with two CPM slots when the active CPM cannot detect a
         standby CPM in the chassis.  When the operating state of
         TIMETRA-CHASSIS-MIB::tmnxCpmCardRedundant for the active CPM card
         transitions to a value of 'singleton (1)', this notification is
         generated.  tmnxChassisNotifyHwIndex identifies the singleton CPM.

         When the active CPM later detects a standby CPM in the chassis, the
         ssiRedStandbySyncing event will be generated followed by a
         ssiRedStandbyReady event to indicate clearing of the CPM singleton
         state.  The value of tmnxCpmCardRedundant will then transition to
         'redundantActive (2)'."
    ::= { tmnxSysNotifications 29 }

--
--  persistency notifications
--
persistencyClosedAlarmRaised  NOTIFICATION-TYPE
   OBJECTS {
        tmnxPersistenceAffectedCpm,
        tmnxPersistencyClient,
        tmnxPersistencyFileLocator,
        tmnxPersistencyNotifyMsg
    }
    STATUS  current
    DESCRIPTION
        "The persistencyClosedAlarmRaised notification is generated when
         the system is unable to store persistency data (e.g. because
         the device is inaccessible, or full)."
    ::= { tmnxSysNotifications 30 }

persistencyClosedAlarmCleared     NOTIFICATION-TYPE
   OBJECTS {
        tmnxPersistenceAffectedCpm,
        tmnxPersistencyClient,
        tmnxPersistencyFileLocator,
        tmnxPersistencyNotifyMsg
    }
    STATUS  current
    DESCRIPTION
        "The persistencyClosedAlarmCleared notification is generated when
        the output device used to store the persistence data is available
        for use again."
    ::= { tmnxSysNotifications 31 }

tmnxSntpOperChange    NOTIFICATION-TYPE
    OBJECTS {
        sntpOperStatus
        }
    STATUS  current
    DESCRIPTION
        "The tmnxSntpOperChange notification is generated whenever there
         is a change in the operational state of SNTP."
    ::= { tmnxSysNotifications 32 }

tmnxSysTimeSet   NOTIFICATION-TYPE
    OBJECTS {
        stiDateAndTime,
        tmnxSysTimeSetBy
        }
    STATUS  current
    DESCRIPTION
        "The tmnxSysTimeSet notification is generated whenever system time is
         set by NTP, SNTP, SNMP, Real Time Clock(RTC) or if it was set manually."
    ::= { tmnxSysNotifications 33 }

tmnxFtpClientFailure    NOTIFICATION-TYPE
    OBJECTS {
        tmnxFtpFailureMsg,
        tmnxFtpFailureDestAddressType,
        tmnxFtpFailureDestAddress
        }
    STATUS  current
    DESCRIPTION
      "The tmnxFtpClientFailure notification is generated when a file transfer
       operation initiated by the FTP client fails."
    ::= { tmnxSysNotifications 34 }

tacplusInetSrvrOperStatusChange NOTIFICATION-TYPE
    OBJECTS {
        tacPlusServerInetAddressType,
        tacPlusServerInetAddress,
        tacplusServerOperStatus
    }
    STATUS  current
    DESCRIPTION
        "The tacplusInetSrvrOperStatusChange notification is generated
         when the operational status of a TACACS+ server has transitioned either
         from 'up' to 'down' or from 'down' to 'up'."
    ::= { tmnxSysNotifications 35 }

radiusInetServerOperStatusChange NOTIFICATION-TYPE
    OBJECTS {
        radiusServerInetAddressType,
        radiusServerInetAddress,
        radiusServerOperStatus
    }
    STATUS  current
    DESCRIPTION
        "The radiusInetServerOperStatusChange notification is generated
         when the operational status of a Radius server has transitioned either
         from 'up' to 'down' or from 'down' to 'up'."
    ::= { tmnxSysNotifications 36 }

persistencyEventReport NOTIFICATION-TYPE
    OBJECTS {
        tmnxPersistencyNotifyMsg
    }
    STATUS  current
    DESCRIPTION
        "The persistencyEventReport notification is generated
         when a client-specific persistence event occurs 
         (e.g. the start and completion of a recover action after system
         startup)."
    ::= { tmnxSysNotifications 37 }

sbiBootConfigFailFileError NOTIFICATION-TYPE
    OBJECTS {
            sbiBootConfigFailScript
        }
    STATUS  current
    DESCRIPTION
        "The sbiBootConfigFailFileError notification is generated when
         sbiBootConfigFailScript file cannot be accessed."
    ::= { tmnxSysNotifications 38 }

sbiBootConfigOKFileError NOTIFICATION-TYPE
    OBJECTS {
            sbiBootConfigOKScript
        }
    STATUS  current
    DESCRIPTION
        "The sbiBootConfigOKFileError notification is generated when
         sbiBootConfigOKScript file cannot be accessed."
    ::= { tmnxSysNotifications 39 }

sbiBootLiConfig NOTIFICATION-TYPE
    OBJECTS {
            sliConfigStatus,
            sbiLiSeparate,
            sbiLiLocalSave
        }
    STATUS  current
    DESCRIPTION
        "The sbiBootLiConfig notification is generated upon completion of 
         the Lawful Intercept (LI) configuration phase following a system 
         reboot.  This notification is generated periodically, about once 
         an hour.
         
         This event is generated only from the LI context."
    ::= { tmnxSysNotifications 40 }
    
persistenceRestoreProblem NOTIFICATION-TYPE
    OBJECTS {
        tmnxPersistencyClient,
        tmnxPersistencyNotifyMsg
    }
    STATUS  current
    DESCRIPTION
        "The persistenceRestoreProblem notification is generated
         when an an error is detected while processing a persistence record."
    ::= { tmnxSysNotifications 41 }

tmnxSysRollbackStarted NOTIFICATION-TYPE
    OBJECTS {
        tmnxSysRollbackIndex,
        tmnxSysRollbackFileType,
        tmnxLogExecRollbackOpIndex
    }
    STATUS  current
    DESCRIPTION
        "[CAUSE] The tmnxSysRollbackStarted notification is generated 
        when the user initiates a revert of the rollback checkpoint file 
        specified by tmnxSysRollbackIndex and tmnxSysRollbackFileType.
        The value of tmnxLogExecRollbackOpIndex indicates the row entry 
        in the TIMETRA-LOG-MIB::tmnxLogExecRollbackOpTable for this rollback
        revert operation. 

        [EFFECT] The specified file is executed and system configuration 
        may change.

        [RECOVERY] There is no recovery required for this notification."
    ::= { tmnxSysNotifications 42 }

tmnxSysRollbackStatusChange NOTIFICATION-TYPE
    OBJECTS {
        tmnxSysRollbackIndex,
        tmnxSysRollbackResult,
        tmnxSysRollbackFileType,
        tmnxLogExecRollbackOpIndex
    }
    STATUS  current
    DESCRIPTION
       "[CAUSE] The tmnxSysRollbackStatusChange notification is 
        generated upon the completion of a rollback revert as specified 
        by tmnxSysRollbackIndex and tmnxSysRollbackFileType.  The value 
        of tmnxLogExecRollbackOpIndex indicates the row entry in the 
        TIMETRA-LOG-MIB::tmnxLogExecRollbackOpTable for this rollback
        revert operation. 
        
        [EFFECT] The result is indicated by the value of tmnxSysRollbackResult.

        [RECOVERY] When the value of tmnxSysRollbackResult is none, 
        inProgress or success no recovery is required. When the value is
        failed, the user should try to determine the reason for the failure.
        The user can attempt a recovery by reverting back to a known good 
        checkpoint. The user may reboot the system with the bof pointing 
        to a saved configuration file." 
    ::= { tmnxSysNotifications 43 }

tmnxSysRollbackSaveStatusChange NOTIFICATION-TYPE
    OBJECTS {
        tmnxSysRollbackSaveResult,
        tmnxSysRollbackFileType
    }
    STATUS  current
    DESCRIPTION
        "[CAUSE] The tmnxSysRollbackSaveStatusChange notification is generated 
         upon the completion of a rollback save as specified by 
         tmnxSysRollbackFileType.
         
         [EFFECT] The result is indicated by value of tmnxSysRollbackSaveResult.

         [RECOVERY] When the value of tmnxSysRollbackSaveResult is none, 
         inProgress or success no recovery is required. When the value is
         is failed, the user should try to determine the reason for the failure.
         The user can attempt a recovery by attempting the rollback save again."
    ::= { tmnxSysNotifications 44 }

tmnxSysRollbackFileDeleteStatus NOTIFICATION-TYPE
    OBJECTS {
        tmnxSysRollbackIndex,
        tmnxSysRollbackFileDeleteResult,
        tmnxSysRollbackFileType
    }
    STATUS  current
    DESCRIPTION
       "[CAUSE] The tmnxSysRollbackFileDeleteStatus notification is generated 
        upon the completion of a rollback file delete as specified by 
        tmnxSysRollbackIndex and tmnxSysRollbackFileType.
        
        [EFFECT] The result is indicated by the value of 
        tmnxSysRollbackFileDeleteResult.

        [RECOVERY] When the value of tmnxSysRollbackFileDeleteResult is none, 
        inProgress or success no recovery is required. When the value is
        failed, the user should try to determine the reason for the failure.
        The user can attempt a recovery by deleting the file again."
    ::= { tmnxSysNotifications 45 }

ssiSyncRollbackOK NOTIFICATION-TYPE
    STATUS  current
    DESCRIPTION
        "[CAUSE]  The ssiSyncRollbackOK event is generated when the
         synchronization of rollback files between the primary
         and secondary CPMs finishes without errors.
         
         [EFFECT] Rollback files are synchronized.

         [RECOVERY] No recovery is necessary."
    ::= { tmnxSysNotifications 46 }

ssiSyncRollbackFailed NOTIFICATION-TYPE
    OBJECTS {
        tmnxSyncFailureReason
    }
    STATUS  current
    DESCRIPTION
        "[CAUSE] The ssiSyncRollbackFailed event is generated when the
         synchronization of rollback files between the primary
         and secondary CPMs is stopped due to errors. The 
         tmnxSyncFailureReason will state the reason for the failure.
         
         [EFFECT] Rollback files are not synchronized.

         [RECOVERY] The user should try to determine the cause of the failure
         and can attempt synchronizing the files again."
    ::= { tmnxSysNotifications 47 }

ssiSyncCertOK NOTIFICATION-TYPE
    STATUS  current
    DESCRIPTION
        "[CAUSE]  The ssiSyncCertOK event is generated when the
         synchronization of certificate files between the primary
         and secondary CPMs finishes without errors.
         
         [EFFECT] Certificate files are synchronized.

         [RECOVERY] No recovery is necessary."
    ::= { tmnxSysNotifications 48 }

ssiSyncCertFailed NOTIFICATION-TYPE
    OBJECTS {
        tmnxSyncFailureReason
    }
    STATUS  current
    DESCRIPTION
        "[CAUSE] The ssiSyncCertFailed event is generated when the
         synchronization of certificate files between the primary
         and secondary CPMs is stopped due to errors. The 
         tmnxSyncFailureReason will state the reason for the failure.
         
         [EFFECT] Certificate files are not synchronized.

         [RECOVERY] The user should try to determine the cause of the failure
         and can attempt synchronizing the files again."
    ::= { tmnxSysNotifications 49 }

persistencyFileSysThresRaised  NOTIFICATION-TYPE
   OBJECTS {
        tmnxPersistenceAffectedCpm,
        tmnxPersistencyClient,
        tmnxPersistencyFileLocator,
        tmnxPersistencyNotifyMsg
    }
    STATUS  current
    DESCRIPTION
        "The persistencyFileSysThresRaised notification is generated 
         when the filesystem reaches 90 percent occupation."
    ::= { tmnxSysNotifications 50 }

persistencyFileSysThresCleared  NOTIFICATION-TYPE
   OBJECTS {
        tmnxPersistenceAffectedCpm,
        tmnxPersistencyClient,
        tmnxPersistencyFileLocator,
        tmnxPersistencyNotifyMsg
    }
    STATUS  current
    DESCRIPTION
        "The persistencyFileSysThresCleared notification is generated 
         when the filesystem drops below 90 percent occupation."
    ::= { tmnxSysNotifications 51 }

tmnxSysExecStarted NOTIFICATION-TYPE
    OBJECTS {
        tmnxSysExecScript,
        tmnxLogExecRollbackOpIndex,
        tmnxLogExecRollbackOpType
    }
    STATUS  current
    DESCRIPTION
        "[CAUSE] The tmnxSysExecStarted notification is generated when the user
         initiates a CLI 'exec' operation to process a file of SROS CLI commands
         or processing of 'vsd' configuration messages have been initiated.
         
         The value of tmnxSysExecScript indicates the command file when the
         value of tmnxLogExecRollbackOpType is 'exec' or an empty string when
         the value of tmnxLogExecRollbackOpType is 'vsd'. The value of
         tmnxLogExecRollbackOpIndex indicates the row entry in
         TIMETRA-LOG-MIB::tmnxLogExecRollbackOpTable for this CLI 'exec' or
         'vsd' operation. 

         [EFFECT] All change notifications generated after the generation of
         this notification and before the tmnxSysExecFinished will be logged
         in the TIMETRA-LOG-MIB::tmnxLogExecRollbackEventEntry. Once the
         tmnxSysExecFinished notification is triggered, a Network Management
         System (NMS) is able to walk the aforementioned log table to retrieve
         the list of all objects that have been modified during this
         transaction.

         [RECOVERY] There is no recovery required for this notification."
    ::= { tmnxSysNotifications 52 }

tmnxSysExecFinished NOTIFICATION-TYPE
    OBJECTS {
        tmnxSysExecScript,
        tmnxSysExecResult,
        tmnxLogExecRollbackOpIndex,
        tmnxLogExecRollbackOpType
    }
    STATUS  current
    DESCRIPTION
        "[CAUSE] The tmnxSysExecFinished notification is generated upon the
         completion of the execution of a CLI command file or execution of
         vsd configuration messages is completed.

         The value of tmnxSysExecScript indicates the command file when the
         value of tmnxLogExecRollbackOpType is 'exec' or an empty string when
         the value of tmnxLogExecRollbackOpType is 'vsd'. The value of
         tmnxLogExecRollbackOpIndex indicates the row entry in 
         TIMETRA-LOG-MIB::tmnxLogExecRollbackOpTable for this CLI 'exec' or
         'vsd' operation. 

         [EFFECT] The effect is that the entry for the specified
         tmnxLogExecRollbackOpIndex won't be updated, and no further
         notifications will be added to the specified index in the logger.

         [RECOVERY] When the value of tmnxSysExecResult is 'none' or 'success',
         no recovery is required. 
         
         When the value is 'fail', the system may be left in an inconsistent
         state and the user should try to determine the reason for the failure.
         The user can attempt a recovery by manually entering CLI commands to
         reverse the failed configuration.  The user can attempt a recovery by 
         performing a rollback revert to a known good checkpoint. The user can 
         attempt a recovery by rebooting the system with the bof pointing to a 
         saved configuration file."
    ::= { tmnxSysNotifications 53 }

tmnxSysRollbackSaveStarted NOTIFICATION-TYPE
    OBJECTS {
        tmnxSysRollbackFileType
    }
    STATUS  current
    DESCRIPTION
        "[CAUSE] The tmnxSysRollbackSaveStarted notification is generated 
        when the user initiates a rollback save as specified by 
        tmnxSysRollbackFileType.

        [EFFECT] The specified configuration file is saved. 

        [RECOVERY] There is no recovery required for this notification."
    ::= { tmnxSysNotifications 54 }

tmnxSysRollbackDeleteStarted NOTIFICATION-TYPE
    OBJECTS {
        tmnxSysRollbackIndex,
        tmnxSysRollbackFileType
    }
    STATUS  current
    DESCRIPTION
        "[CAUSE] The tmnxSysRollbackDeleteStarted notification is generated 
        when the user initiates a rollback delete as specified by  
        by tmnxSysRollbackIndex and tmnxSysRollbackFileType.

        [EFFECT] The specified configuration file is deleted.

        [RECOVERY] There is no recovery required for this notification."
    ::= { tmnxSysNotifications 55 }

tmnxSysNvsysFileError NOTIFICATION-TYPE
    OBJECTS {
        tmnxSysFileErrorType
    }
    STATUS  current
    DESCRIPTION
        "[CAUSE] The tmnxSysNvsysFileError notification is generated 
        when there is a failure in accessing the nvsys file as specified   
        by tmnxSysFileErrorType. 

        [EFFECT] The specified nvsys file operation is unsuccessful. 

        [RECOVERY] The user should investigate why the failure occurred. A
        failure can indicate a problem with the compact flash."
    ::= { tmnxSysNotifications 56 }


sysDNSSecFailedAuthentication NOTIFICATION-TYPE
    OBJECTS {
        sysDNSSecRespCtrl,
        tmnxSysDNSSecDomainName
    }
    STATUS  current
    DESCRIPTION
        "[CAUSE] The sysDNSSecFailedAuthentication notification is generated
         when a DNS response PDU is received with an unset AD-bit and 
         sysDNSSecAdValidation is set to 'true (1)'.

         [EFFECT] This notification is informational only. The message will
         vary depending on the state of sysDNSSecRespCtrl.

         [RECOVERY] There is no recovery required for this notification."
    ::= { tmnxSysNotifications 57 }

tmnxSysLicenseInvalid            NOTIFICATION-TYPE
    OBJECTS {
        tmnxHwClass,
        tmnxSysLicenseErrorReason,
        tmnxSysLicenseTimeLeft,
        tmnxSysLicenseErrorAction
    }
    STATUS  current
    DESCRIPTION
        "[CAUSE] The tmnxSysLicenseInvalid notification is generated when the
         license becomes invalid for the reason specified in
         tmnxSysLicenseErrorReason.

         [EFFECT] The CPM or system will reboot at the end of the time
         remaining, as specified by tmnxSysLicenseTimeLeft and
         tmnxSysLicenseErrorAction.

         [RECOVERY] Configure a valid license file location and file name,
         given the value of tmnxSysLicenseErrorReason."
    ::= { tmnxSysNotifications 59 }

tmnxSysLicenseExpiresSoon        NOTIFICATION-TYPE
    OBJECTS {
        tmnxHwClass,
        tmnxSysLicenseTimeLeft
    }
    STATUS  current
    DESCRIPTION
        "[CAUSE] The tmnxSysLicenseExpiresSoon notification is generated when
         the license is due to expire soon.

         [EFFECT] The system will reboot at the end of the time remaining, as
         specified by tmnxSysLicenseTimeLeft.

         [RECOVERY] Configure a valid license file location and file name."
    ::= { tmnxSysNotifications 60 }

tmnxSysVsdServerAvailable NOTIFICATION-TYPE
    OBJECTS {
       tmnxSysNotifVsdServerName
    }
    STATUS          current
    DESCRIPTION
        "[CAUSE] The tmnxSysVsdServerAvailable notification is generated when
         system discover a new VSD server.

         [EFFECT] System will use this information to establish communication
         with new VSD server as needed.

         [RECOVERY] None needed."
    ::= { tmnxSysNotifications 63 }

tmnxSysVsdServerUnavailable NOTIFICATION-TYPE
    OBJECTS {
       tmnxSysNotifVsdServerName
    }
    STATUS          current
    DESCRIPTION
        "[CAUSE] The tmnxSysVsdServerAvailable notification is generated when
         system loses connection to VSD.

         [EFFECT] System will use this information and stop communication with
         this VSD server as needed.

         [RECOVERY] None needed."
    ::= { tmnxSysNotifications 64 }

tmnxSysXmppServerFunctional NOTIFICATION-TYPE
    OBJECTS {
       tmnxSysNotifXmppServerName
    }
    STATUS          current
    DESCRIPTION
        "[CAUSE] The tmnxSysXmppServerFunctional notification is generated when
         system discover a new XMPP server.

         [EFFECT] System will use this information to establish communication
         with new XMPP server as needed.

         [RECOVERY] None needed."
    ::= { tmnxSysNotifications 65 }

tmnxSysXmppServerNotFunctional NOTIFICATION-TYPE
    OBJECTS {
       tmnxSysNotifXmppServerName
    }
    STATUS          current
    DESCRIPTION
        "[CAUSE] The tmnxSysXmppServerNotFunctional notification is generated
         when system can not communicate with XMPP server.

         [EFFECT] Communication with XMPP server will stop.

         [RECOVERY] Check to see why XMPP server has stopped communicating."
    ::= { tmnxSysNotifications 66 }

tmnxSysLicenseValid              NOTIFICATION-TYPE
    OBJECTS {
        tmnxHwClass
    }
    STATUS  current
    DESCRIPTION
        "[CAUSE] The tmnxSysLicenseValid notification is generated once after
         the system boots up and the license is determined by the system to be
         valid.

         [EFFECT] The system is running with the license specified in
         tmnxSysLicenseName.

         [RECOVERY] No recovery."
    ::= { tmnxSysNotifications 67 }

tmnxSysBaseMacAddressNotSet      NOTIFICATION-TYPE
    OBJECTS {
        tmnxChassisBaseMacAddress
    }
    STATUS  current
    DESCRIPTION
        "[CAUSE] The tmnxSysBaseMacAddressNotSet notification is generated once
         after the system boots up and the value of sbiSystemBaseMacAddress is
         all zeroes.

         [EFFECT] The system software is using the base MAC address specified
         in tmnxChassisBaseMacAddress which may not be unique.

         [RECOVERY] Configure sbiSystemBaseMacAddress to a value other than all
         zeroes."
     ::= { tmnxSysNotifications 68 }


tmnxSmLaunchStartFailed          NOTIFICATION-TYPE
    OBJECTS {
        tmnxEhsHEntryScriptPlcyOwner,
        tmnxEhsHEntryScriptPlcyName,
        smLaunchScriptOwner,
        smLaunchScriptName,
        smLaunchError,
        tmnxSmLaunchExtAuthType,
        tmnxSmRunExtAuthType,
        tmnxSmRunExtUserName
    }
    STATUS  current
    DESCRIPTION
        "[CAUSE] The tmnxSmLaunchStartFailed notification is generated when the
        launch start fails because of one of the following reasons:
           1. The values of smLaunchScriptOwner and smLaunchScriptName don't 
           have an existing entry in the smScriptTable.
           2. The value of smScriptOperStatus is not 'enabled'.
           3. The smScriptSource value is NULL.
           4. The value of smLaunchOperStatus object in smLaunchTable is not 
           'enabled'.
           5. The check to see if the run Index is already in use fails.
           6. The number of currently executing scripts invoked from this 
           smLaunchTable entry is greater than smLaunchMaxRunning.
           
         [EFFECT] The result is indicated by incrementing the value of 
           tmnxEhsHEntryStatsErrLaunch. 
         [RECOVERY] No recovery is necessary.
        "
    ::= { tmnxSysNotifications 69 }

tmnxEhsHandlerInvoked          NOTIFICATION-TYPE
   OBJECTS {
        tmnxEhsHandlerDescription,
        tmnxSmRunExtAuthType,
        tmnxSmRunExtUserName    
    }
    STATUS  current
    DESCRIPTION
        "[CAUSE] The tmnxEhsHandlerInvoked notification is generated when the 
        following checks pass:
        1. A check to see if a event trigger is present for a particular log 
        event based on the log event application-id and event-id/event name.
        2. Evaluation of the log filter associated with the trigger-entry.

        [EFFECT] This may create a run entry to execute scripts. 
        
        [RECOVERY] No recovery is necessary."
    ::= { tmnxSysNotifications 70 }

tmnxEhsDroppedByMinDelay          NOTIFICATION-TYPE
 OBJECTS {
        tmnxEhsHEntryScriptPlcyOwner,
        tmnxEhsHEntryScriptPlcyName,
        smLaunchScriptOwner,
        smLaunchScriptName,
        tmnxEhsHEntryMinDelay,
        tmnxEhsHEntryMinDelayInterval,
        tmnxSmRunExtAuthType,
        tmnxSmRunExtUserName
    }
    STATUS  current
    DESCRIPTION
    "[CAUSE] The tmnxEhsDroppedByMinDelay is generated when two consecutive 
     executions of script policy specified by the same event handler entry 
     occurs with in the time period specified by tmnxEhsHEntryMinDelay.
     
     [EFFECT] The value of tmnxEhsHEntryStatsErrMinDelay gets incremented.

     [RECOVERY] No recovery is necessary."
    ::= { tmnxSysNotifications 71 }
    
tmnxSysAppStats24HrsAvailable    NOTIFICATION-TYPE
 OBJECTS {
        tmnxSysNotifAppStatsTime,
        tmnxSysNotifAppStatsApplication,
        tmnxSysNotifAppStatsType        
    }
    STATUS  current
    DESCRIPTION
    "[CAUSE] The system generates the tmnxSysAppStats24HrsAvailable notification
     when new rows are available in the tmnxSysAppStats24HrsTable.
           
     The value of tmnxSysNotifAppStatsTime indicates the time the system
     collected the values in the new rows.
     
     A non-zero value of tmnxSysNotifAppStatsApplication indicates the
     application; a zero value of tmnxSysNotifAppStatsApplication indicates
     that new values are available for all active applications.
     
     A non-zero value of tmnxSysNotifAppStatsType indicates the
     type of statistics; a zero value of tmnxSysNotifAppStatsType indicates
     that new values are available for all active types.
     
     [EFFECT] None.

     [RECOVERY] No recovery is necessary."
    ::= { tmnxSysNotifications 72 }

tmnxSysAppStatsWeekAvailable     NOTIFICATION-TYPE
 OBJECTS {
        tmnxSysNotifAppStatsTime
    }
    STATUS  current
    DESCRIPTION
    "[CAUSE] The system generates the tmnxSysAppStatsWeekAvailable notification
     when new rows are available in the tmnxSysAppStatsWeekTable.
           
     The value of tmnxSysNotifAppStatsTime indicates the time the system
     collected the values in the new rows.
          
     [EFFECT] None.

     [RECOVERY] No recovery is necessary."
    ::= { tmnxSysNotifications 73 }



--
--  System Boot Options File (BOF) Information
--
sysBofInfo    OBJECT IDENTIFIER ::= { tmnxSysObjs 11 }

sbiActiveIpAddr  OBJECT-TYPE
    SYNTAX      IpAddress
    MAX-ACCESS  read-write
    STATUS      current
    DESCRIPTION
        "The value of sbiActiveIpAddr specifies the IP address of the
         ethernet port on the active CPM."
    DEFVAL { 0 }
    ::= { sysBofInfo 1 }

sbiActiveIpMask  OBJECT-TYPE
    SYNTAX      IpAddressPrefixLength
    MAX-ACCESS  read-write
    STATUS      current
    DESCRIPTION
        "The value of sbiActiveIpMask specifies the mask length of the
         subnet associated with the IP address of the ethernet port on
         the active CPM."
    DEFVAL { 0 }
    ::= { sysBofInfo 2 }

sbiStandbyIpAddr  OBJECT-TYPE
    SYNTAX      IpAddress
    MAX-ACCESS  read-write
    STATUS      current
    DESCRIPTION
        "The value of sbiStandbyIpAddr specifies the IP address of the
         ethernet port on the standby CPM."
    DEFVAL { 0 }
    ::= { sysBofInfo 3 }

sbiStandbyIpMask  OBJECT-TYPE
    SYNTAX      IpAddressPrefixLength
    MAX-ACCESS  read-write
    STATUS      current
    DESCRIPTION
        "The value of sbiStandbyIpMask specifies the mask length of the
         subnet associated with the IP address of the ethernet port on
         the standby CPM."
    DEFVAL { 0 }
    ::= { sysBofInfo 4 }

sbiPrimaryImage  OBJECT-TYPE
    SYNTAX      TmnxDisplayStringURL
    MAX-ACCESS  read-write
    STATUS      current
    DESCRIPTION
        "The value of sbiPrimaryImage specifies the primary location
         of the directory that contains the runtime image files."
    DEFVAL { ''H }
    ::= { sysBofInfo 5 }

sbiSecondaryImage  OBJECT-TYPE
    SYNTAX      TmnxDisplayStringURL
    MAX-ACCESS  read-write
    STATUS      current
    DESCRIPTION
        "The value of sbiSecondaryImage specifies the secondary location
         of the directory that contains the runtime image files."
    DEFVAL { ''H }
    ::= { sysBofInfo 6 }

sbiTertiaryImage  OBJECT-TYPE
    SYNTAX      TmnxDisplayStringURL
    MAX-ACCESS  read-write
    STATUS      current
    DESCRIPTION
        "The value of sbiTertiaryImage specifies the tertiary location
         of the directory that contains the runtime image files."
    DEFVAL { ''H }
    ::= { sysBofInfo 7 }

sbiPrimaryConfigFile  OBJECT-TYPE
    SYNTAX      TmnxDisplayStringURL
    MAX-ACCESS  read-write
    STATUS      current
    DESCRIPTION
        "The value of sbiPrimaryConfigFile specifies the location and
         name of the primary configuration file."
    DEFVAL { ''H }
    ::= { sysBofInfo 8 }

sbiSecondaryConfigFile  OBJECT-TYPE
    SYNTAX      TmnxDisplayStringURL
    MAX-ACCESS  read-write
    STATUS      current
    DESCRIPTION
        "The value of sbiSecondaryConfigFile specifies the location and
         name of the secondary configuration file."
    DEFVAL { ''H }
    ::= { sysBofInfo 9 }

sbiTertiaryConfigFile  OBJECT-TYPE
    SYNTAX      TmnxDisplayStringURL
    MAX-ACCESS  read-write
    STATUS      current
    DESCRIPTION
        "The value of sbiTertiaryConfigFile specifies the location and
         name of the tertiary configuration file."
    DEFVAL { ''H }
    ::= { sysBofInfo 10 }

sbiPersist  OBJECT-TYPE
    SYNTAX      TruthValue
    MAX-ACCESS  read-write
    STATUS      current
    DESCRIPTION
        "The value of sbiPersist specifies whether or not the system
         will preserve SNMP indexes between reboots. When set to 'true',
         persistent indexing is enabled."
    DEFVAL { false }
    ::= { sysBofInfo 11 }

sbiConsoleSpeed  OBJECT-TYPE
    SYNTAX      Unsigned32 (9600|19200|38400|57600|115200)
    UNITS       "bps"
    MAX-ACCESS  read-write
    STATUS      current
    DESCRIPTION
        "The value of sbiConsoleSpeed specifies the baud rate of the
         console port."
    DEFVAL { 115200 }
    ::= { sysBofInfo 12 }

sbiAutoNegotiate  OBJECT-TYPE
    SYNTAX      TruthValue
    MAX-ACCESS  read-write
    STATUS      current
    DESCRIPTION
        "The value of sbiAutoNegotiate determines whether or not the
         speed and duplex parameters will be automatically negotiated
         on the CPM ethernet port. When set to 'true', auto-negotiation
         is enabled."
    DEFVAL { true }
    ::= { sysBofInfo 13 }

sbiSpeed  OBJECT-TYPE
    SYNTAX      Unsigned32 (10|100)
    UNITS       "Mbps"
    MAX-ACCESS  read-write
    STATUS      current
    DESCRIPTION
        "The value of sbiSpeed specifies the speed of the CPM ethernet
         port. This value is ignored if auto-negotiation is enabled."
    DEFVAL { 100 }
    ::= { sysBofInfo 14 }

sbiDuplex  OBJECT-TYPE
    SYNTAX      INTEGER {
                    full(1),
                    half (2)
                }
    MAX-ACCESS  read-write
    STATUS      current
    DESCRIPTION
        "The value of sbiDuplex specifies the duplex mode for the CPM
         ethernet port. This value is ignored if auto-negotiation is
         enabled."
    DEFVAL { full }
    ::= { sysBofInfo 15 }

sbiPrimaryDns  OBJECT-TYPE
    SYNTAX      IpAddress
    MAX-ACCESS  read-write
    STATUS      current
    DESCRIPTION
        "The value of sbiPrimaryDns specifies the IP address of the
         primary DNS server to use for DNS name resolution."
    DEFVAL { 0 }
    ::= { sysBofInfo 16 }

sbiSecondaryDns  OBJECT-TYPE
    SYNTAX      IpAddress
    MAX-ACCESS  read-write
    STATUS      current
    DESCRIPTION
        "The value of sbiSecondaryDns specifies the IP address of the
         secondary DNS server to use for DNS name resolution."
    DEFVAL { 0 }
    ::= { sysBofInfo 17 }

sbiTertiaryDns  OBJECT-TYPE
    SYNTAX      IpAddress
    MAX-ACCESS  read-write
    STATUS      current
    DESCRIPTION
        "The value of sbiTertiaryDns specifies the IP address of the
         tertiary DNS server to use for DNS name resolution."
    DEFVAL { 0 }
    ::= { sysBofInfo 18 }

sbiDnsDomain  OBJECT-TYPE
    SYNTAX      DisplayString (SIZE (0 | 1..178))
    MAX-ACCESS  read-write
    STATUS      current
    DESCRIPTION
        "The value of sbiDnsDomain specifies the domain name to use
         when performing DNS address resolution."
    DEFVAL { ''H }
    ::= { sysBofInfo 19 }

sbiWait  OBJECT-TYPE
    SYNTAX      Unsigned32 (1..10)
    UNITS       "seconds"
    MAX-ACCESS  read-write
    STATUS      current
    DESCRIPTION
        "The value of sbiWait specifies the number of seconds the system
         pauses at the start of the boot process. This pause allows the
         operator to interrupt the system initialization at the console
         and manually override the parameters in the BOF."
    DEFVAL { 3 }
    ::= { sysBofInfo 20 }

sbiStaticRouteTable   OBJECT-TYPE
    SYNTAX      SEQUENCE OF SbiStaticRouteEntry
    MAX-ACCESS  not-accessible
    STATUS      current
    DESCRIPTION
        "The sbiStaticRouteTable contains an entry for each static route
         configured for the CPM ethernet port. These static routes are
         only used to route traffic generated by the CPM ethernet port.
         The table can have up to a maximum of 10 entries."
    ::= { sysBofInfo 21 }

sbiStaticRouteEntry OBJECT-TYPE
    SYNTAX      SbiStaticRouteEntry
    MAX-ACCESS  not-accessible
    STATUS      current
    DESCRIPTION
        "Each row entry contains information about a static route
         configured for the CPM ethernet port.

         Entries in this table can be created and deleted via SNMP
         SET operations to sbiStaticRouteRowStatus."
    INDEX { sbiStaticRouteDest,
            sbiStaticRouteMask }
    ::= { sbiStaticRouteTable 1 }

SbiStaticRouteEntry ::=
    SEQUENCE {
        sbiStaticRouteDest              IpAddress,
        sbiStaticRouteMask              IpAddressPrefixLength,
        sbiStaticRouteNextHop           IpAddress,
        sbiStaticRouteRowStatus         RowStatus
    }

sbiStaticRouteDest  OBJECT-TYPE
    SYNTAX      IpAddress
    MAX-ACCESS  not-accessible
    STATUS      current
    DESCRIPTION
        "The value of sbiStaticRouteDest specifies the destination IP
         address of this static route."
    ::= { sbiStaticRouteEntry 1 }

sbiStaticRouteMask  OBJECT-TYPE
    SYNTAX      IpAddressPrefixLength
    MAX-ACCESS  not-accessible
    STATUS      current
    DESCRIPTION
        "The value of sbiStaticRouteMask specifies the length of the
         subnet mask associated with the destination IP address of this
         static route."
    ::= { sbiStaticRouteEntry 2 }

sbiStaticRouteNextHop  OBJECT-TYPE
    SYNTAX      IpAddress
    MAX-ACCESS  read-create
    STATUS      current
    DESCRIPTION
        "The value of sbiStaticRouteNextHop specifies the IP address of
         the next hop for this static route. This IP address should be
         in the same subnet as the ethernet port on the active CPM.
         The value of sbiStaticRouteNextHop must be set to a valid IP
         address for the row creation to succeed."
    ::= { sbiStaticRouteEntry 3 }

sbiStaticRouteRowStatus  OBJECT-TYPE
    SYNTAX      RowStatus
    MAX-ACCESS  read-create
    STATUS      current
    DESCRIPTION
        "sbiStaticRouteRowStatus controls the creation and deletion of
         rows in the table. To create a row in this table, set the row
         status to createAndGo(4)'. The value of sbiStaticRouteNextHop
         must also be set to a valid IP address for the row creation to
         succeed. To delete a row in this table, set the row status to
         delete(6)."
    ::= { sbiStaticRouteEntry 4 }

sbiActiveIPv6Addr  OBJECT-TYPE
    SYNTAX      InetAddressIPv6
    MAX-ACCESS  read-write
    STATUS      current
    DESCRIPTION
        "The value of sbiActiveIPv6Addr specifies the IPv6 address of the
         ethernet port on the active CPM."
    DEFVAL { '00000000000000000000000000000000'H }
    ::= { sysBofInfo 22 }

sbiActiveIPv6PfxLen  OBJECT-TYPE
    SYNTAX      InetAddressPrefixLength (0..128)
    MAX-ACCESS  read-write
    STATUS      current
    DESCRIPTION
        "The value of sbiActiveIPv6PfxLen specifies the prefix length of the
         subnet associated with the sbiActiveIPv6Addr address of the ethernet
         port on the active CPM."
    DEFVAL { 0 }
    ::= { sysBofInfo 23 }

sbiStandbyIPv6Addr  OBJECT-TYPE
    SYNTAX      InetAddressIPv6
    MAX-ACCESS  read-write
    STATUS      current
    DESCRIPTION
        "The value of sbiStandbyIPv6Addr specifies the IPv6 address of the
         ethernet port on the standby CPM."
    DEFVAL { '00000000000000000000000000000000'H }
    ::= { sysBofInfo 24 }

sbiStandbyIPv6PfxLen  OBJECT-TYPE
    SYNTAX      InetAddressPrefixLength (0..128)
    MAX-ACCESS  read-write
    STATUS      current
    DESCRIPTION
        "The value of sbiStandbyIPv6PfxLen specifies the prefix length of the
         subnet associated with the sbiStandbyIPv6Addr address of the ethernet
         port on the active CPM."
    DEFVAL { 0 }
    ::= { sysBofInfo 25 }

sbiPrimaryDnsIPv6Addr  OBJECT-TYPE
    SYNTAX      InetAddressIPv6
    MAX-ACCESS  read-write
    STATUS      current
    DESCRIPTION
        "The value of sbiPrimaryDnsIPv6Addr specifies the IPv6 address of the
         primary DNS server to use for DNS name resolution."
    DEFVAL { '00000000000000000000000000000000'H }
    ::= { sysBofInfo 26 }

sbiSecondaryDnsIPv6Addr  OBJECT-TYPE
    SYNTAX      InetAddressIPv6
    MAX-ACCESS  read-write
    STATUS      current
    DESCRIPTION
        "The value of sbiSecondaryDnsIPv6Addr specifies the IPv6 address of the
         secondary DNS server to use for DNS name resolution."
    DEFVAL { '00000000000000000000000000000000'H }
    ::= { sysBofInfo 27 }

sbiTertiaryDnsIPv6Addr  OBJECT-TYPE
    SYNTAX      InetAddressIPv6
    MAX-ACCESS  read-write
    STATUS      current
    DESCRIPTION
        "The value of sbiTertiaryDnsIPv6Addr specifies the IPv6 address of the
         tertiary DNS server to use for DNS name resolution."
    DEFVAL { '00000000000000000000000000000000'H }
    ::= { sysBofInfo 28 }

sbiStaticRouteIPv6Table   OBJECT-TYPE
    SYNTAX      SEQUENCE OF SbiStaticRouteIPv6Entry
    MAX-ACCESS  not-accessible
    STATUS      current
    DESCRIPTION
        "The sbiStaticRouteIPv6Table contains an entry for each static IPv6
         route configured for the CPM ethernet port. These static routes are
         only used to route traffic generated by the CPM ethernet port.
         The table can have up to a maximum of 10 entries."
    ::= { sysBofInfo 29 }

sbiStaticRouteIPv6Entry OBJECT-TYPE
    SYNTAX      SbiStaticRouteIPv6Entry
    MAX-ACCESS  not-accessible
    STATUS      current
    DESCRIPTION
        "Each row entry contains information about a static IPv6 route
         configured for the CPM ethernet port.

         Entries in this table can be created and deleted via SNMP
         SET operations to sbiStaticRouteIPv6RowStatus."
    INDEX { sbiStaticRouteIPv6Dest,
            sbiStaticRouteIPv6PfxLen }
    ::= { sbiStaticRouteIPv6Table 1 }

SbiStaticRouteIPv6Entry ::=
    SEQUENCE {
        sbiStaticRouteIPv6Dest             InetAddressIPv6,
        sbiStaticRouteIPv6PfxLen           InetAddressPrefixLength,
        sbiStaticRouteIPv6NextHop          InetAddressIPv6,
        sbiStaticRouteIPv6RowStatus        RowStatus
    }

sbiStaticRouteIPv6Dest  OBJECT-TYPE
    SYNTAX      InetAddressIPv6
    MAX-ACCESS  not-accessible
    STATUS      current
    DESCRIPTION
        "The value of sbiStaticRouteIPv6Dest specifies the destination IPv6
         address of this static route."
    ::= { sbiStaticRouteIPv6Entry 1 }

sbiStaticRouteIPv6PfxLen  OBJECT-TYPE
    SYNTAX      InetAddressPrefixLength (0..128)
    MAX-ACCESS  not-accessible
    STATUS      current
    DESCRIPTION
        "The value of sbiStaticRouteIPv6PfxLen specifies the prefix length of
         sbiStaticRouteIPv6Dest, the destination IPv6 address of this static
         route."
    ::= { sbiStaticRouteIPv6Entry 2 }

sbiStaticRouteIPv6NextHop  OBJECT-TYPE
    SYNTAX      InetAddressIPv6
    MAX-ACCESS  read-create
    STATUS      current
    DESCRIPTION
        "The value of sbiStaticRouteIPv6NextHop specifies the IPv6 address of
         the next hop for this static route. This IPv6 address should be
         in the same subnet as the ethernet port on the active CPM.
         The value of sbiStaticRouteIPv6NextHop must be set to a valid IPv6
         address for the row creation to succeed."
    ::= { sbiStaticRouteIPv6Entry 3 }

sbiStaticRouteIPv6RowStatus  OBJECT-TYPE
    SYNTAX      RowStatus
    MAX-ACCESS  read-create
    STATUS      current
    DESCRIPTION
        "sbiStaticRouteIPv6RowStatus controls the creation and deletion of
         rows in the table. To create a row in this table, set the row
         status to createAndGo(4)'. The value of sbiStaticRouteIPv6NextHop
         must also be set to a valid IPv6 address for the row creation to
         succeed. To delete a row in this table, set the row status to
         delete(6)."
    ::= { sbiStaticRouteIPv6Entry 4 }

sbiLiSeparate    OBJECT-TYPE
    SYNTAX      TruthValue
    MAX-ACCESS  read-write
    STATUS      current
    DESCRIPTION
        "The value of sbiLiSeparate specifies whether or not a non-LI user has
         access to Lawful Intercept (LI) information.  When sbiLiSeparate has
         a value of 'true', a user who does not have the TIMETRA-SECURITY-MIB::
         tmnxUserAccess 'li' bit set will not be allowed to access CLI or 
         SNMP objects in the 'li' context.

         A change to the value of this object does not take affect until
         the system is rebooted."
    DEFVAL { false }
    ::= { sysBofInfo 30 }

sbiLiLocalSave      OBJECT-TYPE
    SYNTAX      TruthValue      
    MAX-ACCESS  read-write
    STATUS      current
    DESCRIPTION
        "The value of sbiLiLocalSave specifies whether or not Lawful
         Intercept (LI) configuration is allowed to be save to a local
         file.

         A change to the value of this object does not take affect until
         the system is rebooted."
    DEFVAL { true }
    ::= { sysBofInfo 31 }

sbiLicenseFile                   OBJECT-TYPE
    SYNTAX      TmnxDisplayStringURL
    MAX-ACCESS  read-write
    STATUS      current
    DESCRIPTION
        "The value of sbiLicenseFile specifies the location and
         name of the license file."
    DEFVAL { ''H }
    ::= { sysBofInfo 32 }


sbiFips1402Level1                OBJECT-TYPE
    SYNTAX      TruthValue
    MAX-ACCESS  read-create
    STATUS      current
    DESCRIPTION
        "The value of sbiFips1402Level1 specifies whether or not the security 
         level 1 of Federal Information Processing Standards 140 series version
         2 (FIPS-140-2) is enabled.

         A change to the value of this object does not take effect until after
         a system reboot.  If the value of sbiFips1402Level1 is 'true (1)', 
         after a system reboot, any configuration that is not supported by 
         FIPS-140-2 level 1, will be retrievable via SNMP requests."
    REFERENCE
        "FIPS PUB 140-2, 'Security Requirement for Cryptographic Modules', 
         May 2001."
    DEFVAL { false }
    ::= { sysBofInfo 34 }

sbiSystemBaseMacAddress          OBJECT-TYPE
    SYNTAX      MacAddress
    MAX-ACCESS  read-write
    STATUS      current
    DESCRIPTION
        "The value of sbiSystemBaseMacAddress specifies the administratively
         configured base system ethernet MAC address. Special purpose MAC
         addresses used by the system software are constructed from this base
         address. The value is the first MAC address in a contiguous range of
         1024 addresses.

         If configured, sbiSystemBaseMacAddress will override the value given
         by tmnxChassisBaseMacAddress.

         A value of all zeroes indicates this object is not configured."
    DEFVAL  { '000000000000'H }
    ::= { sysBofInfo 35 }


sbiEssSystemType                 OBJECT-TYPE
    SYNTAX      TruthValue
    MAX-ACCESS  read-write
    STATUS      current
    DESCRIPTION
        "The value of sbiEssSystemType specifies whether or not the system is
         administratively configured to function as a Nokia SROS Ethernet
         Service Switch (ESS)."
    DEFVAL  { false }
    ::= { sysBofInfo 36 }

--
--  System Persistence Information
--
sysPersistenceInfo  OBJECT IDENTIFIER ::= { tmnxSysObjs 12 }
  sysPersistenceDhcpL2Info  OBJECT IDENTIFIER ::= { sysPersistenceInfo 1 }
  sysPersistenceDhcpL3Info  OBJECT IDENTIFIER ::= { sysPersistenceInfo 2 }
  sysPersistenceSubMgmtInfo OBJECT IDENTIFIER ::= { sysPersistenceInfo 3 }
  sysPersistenceDhcpSrvInfo OBJECT IDENTIFIER ::= { sysPersistenceInfo 4 }
  sysPersistenceNatInfo     OBJECT IDENTIFIER ::= { sysPersistenceInfo 5 }
  sysPersistenceAAInfo      OBJECT IDENTIFIER ::= { sysPersistenceInfo 6 }
  sysPersistenceAncpInfo    OBJECT IDENTIFIER ::= { sysPersistenceInfo 7 }
  sysPersistencePythonInfo  OBJECT IDENTIFIER ::= { sysPersistenceInfo 8 }

spiDhcpL2PersistenceFileLocation OBJECT-TYPE
    SYNTAX      Unsigned32 (0..32)
    MAX-ACCESS  read-write
    STATUS      obsolete
    DESCRIPTION
        "The value of spiDhcpL2PersistenceFileLocation specifies
         the flash device on a CPM card where the data for handling
         DHCP Layer2 persistency is stored.
         The value 0 indicates that no flash device is specified.

         This object was made obsolete in the 5.0 release."
    DEFVAL { 0 }
    ::= { sysPersistenceDhcpL2Info 1 }

spiDhcpL2PersistenceDescription OBJECT-TYPE
    SYNTAX      TItemDescription
    MAX-ACCESS  read-write
    STATUS      obsolete
    DESCRIPTION
        "The value of the object spiDhcpL2PersistenceDescription specifies
         a user provided description related to DHCP Layer-2 persistency.
         It consists of any printable, seven-bit ASCII characters
         up to 80 characters in length.

         This object was made obsolete in the 5.0 release."
    DEFVAL { "" }
    ::= { sysPersistenceDhcpL2Info 2 }

spiDhcpL3PersistenceFileLocation OBJECT-TYPE
    SYNTAX      Unsigned32 (0..32)
    MAX-ACCESS  read-write
    STATUS      obsolete
    DESCRIPTION
        "The value of spiDhcpL3PersistenceFileLocation specifies
         the flash device on a CPM card where the data for handling
         DHCP Layer3 persistency is stored.
         The value 0 indicates that no flash device is specified.

         This object was made obsolete in the 5.0 release."
    DEFVAL { 0 }
    ::= { sysPersistenceDhcpL3Info 1 }

spiDhcpL3PersistenceDescription OBJECT-TYPE
    SYNTAX      TItemDescription
    MAX-ACCESS  read-write
    STATUS      obsolete
    DESCRIPTION
        "The value of the object spiDhcpL3PersistenceDescription specifies
         a user provided description related to DHCP Layer-3 persistency.
         It consists of any printable, seven-bit ASCII characters
         up to 80 characters in length.

         This object was made obsolete in the 5.0 release."
    DEFVAL { "" }
    ::= { sysPersistenceDhcpL3Info 2 }

spiSubMgmtPersistenceFileLocation OBJECT-TYPE
    SYNTAX      Unsigned32 (0..32)
    MAX-ACCESS  read-write
    STATUS      current
    DESCRIPTION
        "The value of spiSubMgmtPersistenceFileLocation specifies the flash
         device on a CPM card where the data for handling subscriber management
         persistency is stored.
         The value 0 indicates that no flash device is specified."
    DEFVAL { 0 }
    ::= { sysPersistenceSubMgmtInfo 1 }

spiSubMgmtPersistenceDescription OBJECT-TYPE
    SYNTAX      TItemDescription
    MAX-ACCESS  read-write
    STATUS      current
    DESCRIPTION
        "The value of the object spiSubMgmtPersistenceDescription specifies
         a user provided description related to subscriber management
         persistency.
         It consists of any printable, seven-bit ASCII characters up to 80
         characters in length."
    DEFVAL { "" }
    ::= { sysPersistenceSubMgmtInfo 2 }

spiDhcpSrvPersistenceFileLoc OBJECT-TYPE
    SYNTAX      Unsigned32 (0..32)
    MAX-ACCESS  read-write
    STATUS      current
    DESCRIPTION
        "The value of spiDhcpSrvPersistenceFileLoc specifies the flash
         device on a CPM card where the data for handling the local DHCP
         server persistency is stored.
         The value 0 indicates that no flash device is specified."
    DEFVAL { 0 }
    ::= { sysPersistenceDhcpSrvInfo 1 }

spiDhcpSrvPersistenceDescr OBJECT-TYPE
    SYNTAX      TItemDescription
    MAX-ACCESS  read-write
    STATUS      current
    DESCRIPTION
        "The value of the object spiDhcpSrvPersistenceDescr specifies
         a user provided description related to the local DHCP server
         persistency.
         It consists of any printable, seven-bit ASCII characters up to 80
         characters in length."
    DEFVAL { "" }
    ::= { sysPersistenceDhcpSrvInfo 2 }

spiNatFwdPersistenceFileLoc OBJECT-TYPE
    SYNTAX      Unsigned32 (0..32)
    MAX-ACCESS  read-write
    STATUS      current
    DESCRIPTION
        "The value of spiNatFwdPersistenceFileLoc specifies the flash
         device on a CPM card where the data for handling 
         the NAT (Network Address Translation) port forwarding persistence 
         is stored.
         
         The value 0 indicates that no flash device is specified."
    DEFVAL { 0 }
    ::= { sysPersistenceNatInfo 1 }

spiNatFwdPersistenceDescr OBJECT-TYPE
    SYNTAX      TItemDescription
    MAX-ACCESS  read-write
    STATUS      current
    DESCRIPTION
        "The value of the object spiNatFwdPersistenceDescr specifies
         a user provided description related to the NAT port forwarding
         persistence.
         It consists of any printable, seven-bit ASCII characters up to 80
         characters in length."
    DEFVAL { "" }
    ::= { sysPersistenceNatInfo 2 }

spiAAPersistenceFileLoc OBJECT-TYPE
    SYNTAX      Unsigned32 (0..32)
    MAX-ACCESS  read-write
    STATUS      current
    DESCRIPTION
        "The value of spiAAPersistenceFileLoc specifies the flash
         device on a CPM card where the data for handling
         the AA (Application Assurance) persistence is stored.
         
         The value 0 indicates that no flash device is specified."
    DEFVAL { 0 }
    ::= { sysPersistenceAAInfo 1 }

spiAAPersistenceDescr OBJECT-TYPE
    SYNTAX      TItemDescription
    MAX-ACCESS  read-write
    STATUS      current
    DESCRIPTION
        "The value of the object spiAAPersistenceDescr specifies
         a user provided description related to the AA (Application Assurance)
         persistence. It consists of any printable, seven-bit ASCII
         characters up to 80 characters in length."
    DEFVAL { "" }
    ::= { sysPersistenceAAInfo 2 }

spiAncpPersistenceFileLoc OBJECT-TYPE
    SYNTAX      Unsigned32 (0..32)
    MAX-ACCESS  read-write
    STATUS      current
    DESCRIPTION
        "The value of spiAncpPersistenceFileLoc specifies the flash
         device on a CPM card where the data for handling
         the Ancp persistence is stored.
         
         The value 0 indicates that no flash device is specified."
    DEFVAL { 0 }
    ::= { sysPersistenceAncpInfo 1 }

spiAncpPersistenceDescr OBJECT-TYPE
    SYNTAX      TItemDescription
    MAX-ACCESS  read-write
    STATUS      current
    DESCRIPTION
        "The value of the object spiAncpPersistenceDescr specifies
         a user provided description related to the Ancp
         persistence. It consists of any printable, seven-bit ASCII
         characters up to 80 characters in length."
    DEFVAL { "" }
    ::= { sysPersistenceAncpInfo 2 }

spiPythonPersistenceFileLoc OBJECT-TYPE
    SYNTAX      Unsigned32 (0..32)
    MAX-ACCESS  read-write
    STATUS      current
    DESCRIPTION
        "The value of spiPythonPersistenceFileLoc specifies the flash
         device on a CPM card where the data for handling
         the python persistence is stored.
         
         The value 0 indicates that no flash device is specified."
    DEFVAL { 0 }
    ::= { sysPersistencePythonInfo 1 }

spiPythonPersistenceDescr OBJECT-TYPE
    SYNTAX      TItemDescription
    MAX-ACCESS  read-write
    STATUS      current
    DESCRIPTION
        "The value of the object spiPythonPersistenceDescr specifies
         a user provided description related to the Python
         persistence. It consists of any printable, seven-bit ASCII
         characters up to 80 characters in length."
    DEFVAL { "" }
    ::= { sysPersistencePythonInfo 2 }

--
--  Generic persistence Information
--
tmnxDhcpLeaseTimeModeThreshold OBJECT-TYPE
    SYNTAX      Unsigned32 (0..631152000) -- max. 20 years
    UNITS       "seconds"
    MAX-ACCESS  read-create
    STATUS      current
    DESCRIPTION
        "The value of tmnxDhcpLeaseTimeModeThreshold specifies
         the threshold time for DHCP leases to be eligible for persistence in
         the 'lease time mode' of operation.
         
         Normally, the expiry time of a DHCP lease is stored in the persistent
         database; in 'lease time mode', however, the full lease time is stored;
         the resource usage penalty is reasonably small for leases with sufficiently
         short lease times.
         
         DHCP leases with a lease time greater than the value of tmnxDhcpLeaseTimeModeThreshold
         have their expiry time stored as usual.
         
         DHCP leases with a lease time smaller than or equal to the value of tmnxDhcpLeaseTimeModeThreshold
         have their full lease time stored."
    DEFVAL { 0 }
    ::= { sysPersistenceInfo 20 }

--
--  System Lawful Intercept Information
--
sysLiInfo  OBJECT IDENTIFIER ::= { tmnxSysObjs 13 }

sliConfigStatus   OBJECT-TYPE
    SYNTAX      INTEGER {
                    notRun (0),
                    success (1),
                    fail    (2)
                }
    MAX-ACCESS  read-only
    STATUS      current
    DESCRIPTION
        "The value of sliConfigStatus indicates the results of restoring
         the Lawful Intercept (LI) configuration at boot-up time."
    ::= { sysLiInfo 1 }

sliSaveConfig   OBJECT-TYPE
    SYNTAX      TmnxActionType
    MAX-ACCESS  read-write
    STATUS      current
    DESCRIPTION
        "The value of sliSaveConfig specifies a desired action.  Setting
         this action variable to 'doAction' causes the current Lawful 
         Intercept (LI) running configuration information, to be saved to 
         a file called li.cfg in the same location as the BOF file.
         If the li.cfg file already exists, it will be renamed and a
         new file is created with the current running configuration.

         An attempt to set this object to 'doAction' when the booted value 
         of sbiLiLocalSave is 'false' will result in an 'inconsistentValue'
         error.

         Default configuration values will be included in the saved 
         configuration information."
    DEFVAL { notApplicable }
    ::= { sysLiInfo 2 }

sliSaveConfigResult OBJECT-TYPE
    SYNTAX      INTEGER {
                    none (1),
                    inProgress (2),
                    success (3),
                    failed (4)
                }
    MAX-ACCESS  read-only
    STATUS      current
    DESCRIPTION
        "The value of sliSaveConfigResult represents the result of the
         last sliSaveConfig action.
         none(1)            None of the following apply
         inProgress(2)      The action is still in progress
         success(3)         The action completed successfully
         failed(4)          The action failed"
    ::= {sysLiInfo 3 }

sliConfigLastModified  OBJECT-TYPE
    SYNTAX      DateAndTime
    MAX-ACCESS  read-only
    STATUS      current
    DESCRIPTION
        "The value of sliConfigLastModified indicates the date and time 
         the Lawful Intercept (LI) running configuration was last modified.
         If sliConfigLastModified is more recent than TIMETRA-CHASSIS-MIB:: 
         tmnxHwSwLastBoot, the current configuration may be different
         than that in the configuration file read upon system initialization."
    ::= { sysLiInfo 4 }

sliConfigLastSaved OBJECT-TYPE
    SYNTAX      DateAndTime
    MAX-ACCESS  read-only
    STATUS      current
    DESCRIPTION
        "The value of sliConfigLastSaved indicates the date and 
         time the current Lawful Intercept (LI) configuration was 
         last saved.  If sliConfigLastSaved is more recent than the 
         value of TIMETRA-CHASSIS-MIB::tmnxHwSwLastBoot, the 
         initial configuration is likely to be different the next 
         time the system is rebooted."
    ::= { sysLiInfo 5 }

sliFilterLock   OBJECT-TYPE
    SYNTAX      INTEGER {
                    locked (0),
                    unlockedForLiUsers (1),
                    unlockedForAll (2)
                }
    MAX-ACCESS  read-write
    STATUS      current
    DESCRIPTION
        "The of sliFilterLock specifies 
         who can modify the Lawful Intercept (LI) filters.
         
         The value:
         'locked':             no users can modify the LI filters
         'unlockedForLiUsers': only users with LI privileges can modify the 
                               LI filters
         'unlockedForAll':     all users can modify the LI filters."
    DEFVAL { locked }
    ::= { sysLiInfo 6 }

--
--  system wide DNS setting
--
sysDNSInfo  OBJECT IDENTIFIER ::= { tmnxSysObjs 14 }

sysDNSInfoLastChanged   OBJECT-TYPE
    SYNTAX      TimeStamp
    MAX-ACCESS  read-only
    STATUS      current
    DESCRIPTION
        "The value of sysDNSInfoLastChanged is the timestamp of the last
         configuration changes to any of the DNS global settings."
    ::= { sysDNSInfo 1 }

sysDNSAddressResolvePref   OBJECT-TYPE
    SYNTAX      INTEGER {
                    ipv4Only  (1),
                    ipv6First (2)
                }
    MAX-ACCESS  read-write
    STATUS      current
    DESCRIPTION
        "The value of sysDNSAddressResolvePref specifies how the DNS
         client will request for address resolution.

         ipv4-only:  The DNS client will only try to resolve a domain name
                     into an ipv4 address.             

         ipv6-first: the DNS client will first try to resolve the
                     domain name in to ipv6 address. If no ipv6 address
                     is available it will try to resolve the domain name 
                     into an ipv4 address."
    DEFVAL { ipv4Only }
    ::= { sysDNSInfo 2 }

--
--  Domain Name System Security Extensions (DNSSEC)
--

sysDNSSecAdValidation           OBJECT-TYPE
    SYNTAX      TruthValue
    MAX-ACCESS  read-write
    STATUS      current
    DESCRIPTION
        "The value of sysDNSSecAdValidation specifies whether or not the 
         presence of the Authenticated Data (AD) bit in responses is validated
         from the DNS servers. 
         
         When sysDNSSecAdValidation is set to 'true (1)', DNSSEC validation is
         enabled and a warning is reported to the SECURITY log if the AD-bit
         is not set in responses from the DNS servers. The notification
         responsible for the warning is sysDNSSecFailedAuthentication.

         When sysDNSSecAdValidation is set to 'false (2)', DNSSEC validation of
         the AD-bit is disabled."
    DEFVAL { false }
    ::= { sysDNSInfo 3 }

sysDNSSecRespCtrl   OBJECT-TYPE
    SYNTAX      INTEGER {
                    fallThrough (1),
                    drop        (2)
                }
    MAX-ACCESS  read-write
    STATUS      current
    DESCRIPTION
        "The value of sysDNSSecRespCtrl specifies whether the system 
         will permit or reject DNS responses that do not pass DNSSEC 
         validation. The value of this object is ignored if 
         sysDNSSecAdValidation is set to 'false (2)'.
         
         When sysDNSSecRespCtrl is set to 'fallThrough (1)', the system 
         will permit DNS responses that do not pass DNSSEC validation,
         allowing the resolution to complete.

         When sysDNSSecRespCtrl is set to 'drop (2)', the system will
         reject DNS responses that do not pass DNSSEC validation, and the 
         resolution will appear to fail."
    DEFVAL { drop }
    ::= { sysDNSInfo 4 }


--
--  System Wide ICMP Vendor Specific settings
--
sysIcmpVSInfo  OBJECT IDENTIFIER ::= { tmnxSysObjs 15 }

sysIcmpVSEnhancement   OBJECT-TYPE
    SYNTAX      TmnxEnabledDisabled
    MAX-ACCESS  read-write
    STATUS      current
    DESCRIPTION
        "The value of sysIcmpVSEnhancement specifies if vendor specific 
         extensions to ICMP is enabled or not."
    DEFVAL { disabled }
    ::= { sysIcmpVSInfo 1 }

sysEthInfo      OBJECT IDENTIFIER ::= { tmnxSysObjs 16 }

sysNewQinqUntaggedSap     OBJECT-TYPE
    SYNTAX      TruthValue
    MAX-ACCESS  read-write
    STATUS      current
    DESCRIPTION
        "The value of sysNewQinqUntaggedSap controls the forwarding of
         packets on a QinQ X.0 access SAP.
 
         When sysNewQinqUntaggedSap is set to true, the SAP will only accept:

         - frames with a single tag matching the SAP's outer tag or,
         - frames with double tag where the outer tag matches the SAP's outer
           tag and inner tag is set to 0.
    
         When sysNewQinqUntaggedSap is set to false, forwarding of packets
         remains unchanged."
    DEFVAL { false }
    ::= { sysEthInfo 1 }

--
-- Rollback Global Information
--

tmnxSysRollbackInfo     OBJECT IDENTIFIER ::= { tmnxSysObjs 17 }

tmnxSysRollbackIndex OBJECT-TYPE
    SYNTAX      Unsigned32 (0..199)
    MAX-ACCESS  read-write 
    STATUS      current
    DESCRIPTION
        "The value of tmnxSysRollbackIndex specifies a specific rollback
         checkpoint file to which a rollback action can be taken. 

         The value of the tmnxSysRollbackIndex corresponds to a rollback 
         checkpoint file with suffix .rb.index. 

         The maximum checkpoint file that can be specified is determined by 
         the rollback location as specified by tmnxSysRollbackLocation. 
         If the location is on a compact flash, then the maximum value of 
         tmnxSysRollbackIndex can be tmnxSysRollbackMaxLocalFiles minus 1.  
         If the location is a remote ftp location, then the maximum 
         value of tmnxSysRollbackIndex can be tmnxSysRollbackMaxRemoteFiles
         minus 1.

         This index is SET along with another action object, including 
         tmnxSysRollbackStart to initiate a rollback revert of a file
         and tmnxSysRollbackFileDelete to delete a rollback file.

         An SNMP GET request on this object should return the last SET value."
    ::= { tmnxSysRollbackInfo 1 }

tmnxSysRollbackStart    OBJECT-TYPE
    SYNTAX      TmnxActionType
    MAX-ACCESS  read-write
    STATUS      current
    DESCRIPTION
        "The value of tmnxSysRollbackStart specifies whether to revert
         the rollback file specified by tmnxSysRollbackIndex.
         
         When SET to the value of 'doAction' the system will revert the
         rollback file specified by tmnxSysRollbackIndex. 
         
         This variable must be set along with tmnxSysRollbackIndex to indicate 
         the specific rollback file to revert.

         An SNMP GET request on this object should return 'notApplicable'." 
    DEFVAL { notApplicable }
    ::= {tmnxSysRollbackInfo 2 }

tmnxSysRollbackResult OBJECT-TYPE
    SYNTAX      INTEGER {
                    none (1),
                    inProgress (2),
                    success (3),
                    failed (4),
                    interrupted (5)
                }
    MAX-ACCESS  read-only
    STATUS      current
    DESCRIPTION
        "The value of tmnxSysRollbackResult indicates the result of the
         last tmnxSysRollbackStart action.

         none(1)            None of the following apply
         inProgress(2)      The action is still in progress
         success(3)         The action completed successfully
         failed(4)          The action failed
         interrupted (5)    The action was interrupted"
    ::= {tmnxSysRollbackInfo 3 }

tmnxSysRollbackSave    OBJECT-TYPE
    SYNTAX      TmnxActionType
    MAX-ACCESS  read-write
    STATUS      current
    DESCRIPTION
        "The value of tmnxSysRollbackSave specifies whether to save the existing
         configuration in a rollback checkpoint file.
         
         When SET to the value of 'doAction' the system will save the
         configuration in a new rollback checkpoint file, with suffix '.rb'. 
         Previously saved rollback files with the same name will increment 
         the filename suffix by 1 up to a maximum of 9.
         For example, file.rb is moved to file.rb.1. The higher the number, 
         the older the file is.
         
         An SNMP GET request on this object should return 'notApplicable'."
    DEFVAL { notApplicable }
    ::= {tmnxSysRollbackInfo 4 }

tmnxSysRollbackSaveResult OBJECT-TYPE
    SYNTAX      INTEGER {
                    none (1),
                    inProgress (2),
                    success (3),
                    failed (4)
                }
    MAX-ACCESS  read-only
    STATUS      current
    DESCRIPTION
        "The value of tmnxSysRollbackSaveResult indicates the result of the
         last tmnxSysRollbackSave action.

         none(1)            None of the following apply
         inProgress(2)      The action is still in progress
         success(3)         The action completed successfully
         failed(4)          The action failed"
    ::= {tmnxSysRollbackInfo 5 }

tmnxSysRollbackLocation   OBJECT-TYPE
    SYNTAX      TmnxDisplayStringURL
    MAX-ACCESS  read-write
    STATUS      current
    DESCRIPTION
        "The value of tmnxSysRollbackLocation specifies the destination filepath
         or file-URL where the current running configuration information
         will be saved when tmnxSysRollbackSave is set to 'doAction'.  If
         the value of tmnxSysRollbackLocation is an empty string the system will
         attempt to store the file in the best available location locally, 
         for example compact flash 1 or 2 if either is present."
    DEFVAL { ''H }  -- empty string
    ::= { tmnxSysRollbackInfo 6 }

tmnxSysRollbackRevertIndex OBJECT-TYPE
    SYNTAX      Unsigned32 (0..199)
    MAX-ACCESS  read-only
    STATUS      current
    DESCRIPTION
        "The value of tmnxSysRollbackRevertIndex indicates the last
         rollback checkpoint file reverted on the system."
    ::= { tmnxSysRollbackInfo 7 }

tmnxSysRollbackRevertEndTime   OBJECT-TYPE
    SYNTAX      DateAndTime 
    MAX-ACCESS  read-only
    STATUS      current
    DESCRIPTION
         "The value of tmnxSysRollbackRevertEndTime indicates the timestamp 
          the last rollback revert on the system is completed.
          The value of tmnxSysRollbackRevertEndTime is affected by the value
          of stiPreferLocalTime.
         "
    ::= { tmnxSysRollbackInfo 8 }

tmnxSysRollbackSavedTime   OBJECT-TYPE
    SYNTAX      DateAndTime 
    MAX-ACCESS  read-only
    STATUS      current
    DESCRIPTION
         "The value of tmnxSysRollbackSavedTime indicates the timestamp  
          the last rollback save on the system is completed.
          The value of tmnxSysRollbackSavedTime is affected by the value
          of stiPreferLocalTime.
         "
    ::= { tmnxSysRollbackInfo 9 }

tmnxSysRollbackRevertStartTime   OBJECT-TYPE
    SYNTAX      DateAndTime 
    MAX-ACCESS  read-only
    STATUS      current
    DESCRIPTION
         "The value of tmnxSysRollbackRevertStartTime indicates the timestamp
          the last rollback file reverted on the system is initiated.
          The value of tmnxSysRollbackRevertStartTime is affected by the value
          of stiPreferLocalTime.
         "
    ::= { tmnxSysRollbackInfo 10 }

tmnxSysRollbackRevertUserName  OBJECT-TYPE
    SYNTAX      TNamedItemOrEmpty
    MAX-ACCESS  read-only 
    STATUS      current
    DESCRIPTION
        "The value of tmnxSysRollbackRevertUserName indicates the name of
         a system user who initiates the last rollback revert."
    DEFVAL { ''H }    -- the empty string
    ::= { tmnxSysRollbackInfo 11 }

tmnxSysRollbackRevertFilename   OBJECT-TYPE
    SYNTAX      TmnxDisplayStringURL
    MAX-ACCESS  read-only
    STATUS      current
    DESCRIPTION
        "The value of tmnxSysRollbackRevertFilename specifies the filepath 
         or file-URL of the last reverted rollback file."
    DEFVAL { ''H }  -- empty string
    ::= { tmnxSysRollbackInfo 12 }

tmnxSysRollbackSaveComment OBJECT-TYPE
    SYNTAX      DisplayString (SIZE(0..255))
    MAX-ACCESS  read-write
    STATUS      current
    DESCRIPTION
       "The value of the object tmnxSysRollbackSaveComment specifies
        a user provided comment related to the rollback checkpoint file about 
        to be saved. 

        It consists of any printable, seven-bit ASCII characters up to 255 
        characters in length."
    DEFVAL { ''H }    -- the empty string
    ::= { tmnxSysRollbackInfo 13 }

tmnxSysRollbackFileDelete    OBJECT-TYPE
    SYNTAX      TmnxActionType
    MAX-ACCESS  read-write
    STATUS      current
    DESCRIPTION
        "The value of tmnxSysRollbackFileDelete specifies whether to delete 
         the rollback file specified by tmnxSysRollbackIndex.
         
         When SET to the value of 'doAction' the system will delete the
         rollback file specified by tmnxSysRollbackIndex. 
         
         This variable must be set along with tmnxSysRollbackIndex to specify
         the specific rollback file to delete.

         An SNMP GET request on this object should return 'notApplicable'." 
    DEFVAL { notApplicable }
    ::= {tmnxSysRollbackInfo 14 }

tmnxSysRollbackFileDeleteResult OBJECT-TYPE
    SYNTAX      INTEGER {
                    none (1),
                    inProgress (2),
                    success (3),
                    failed (4)
                }
    MAX-ACCESS  read-only
    STATUS      current
    DESCRIPTION
        "The value of tmnxSysRollbackFileDeleteResult indicates the result of
         the last tmnxSysRollbackFileDelete action.

         none(1)            None of the following apply
         inProgress(2)      The action is still in progress
         success(3)         The action completed successfully
         failed(4)          The action failed"
    ::= {tmnxSysRollbackInfo 15 }

tmnxSysRollbackAbortRevert    OBJECT-TYPE
    SYNTAX      TmnxActionType
    MAX-ACCESS  read-write
    STATUS      current
    DESCRIPTION
        "The value of tmnxSysRollbackAbortRevert specifies whether to abort the
         rollback revert that's currently in progress.
         
         When SET to the value of 'doAction' the system will abort the active
         rollback revert. This will leave the system in an unknown state, so it
         should be used with care.

         An SNMP GET request on this object should return 'notApplicable'." 
    DEFVAL { notApplicable }
    ::= {tmnxSysRollbackInfo 16 }

tmnxSysRollbackRescueLocation   OBJECT-TYPE
    SYNTAX      TmnxDisplayStringURL
    MAX-ACCESS  read-write
    STATUS      current
    DESCRIPTION
        "The value of tmnxSysRollbackRescueLocation specifies the destination
         file path or file-URL where the rollback rescue configuration file 
         will be saved.  If the value of tmnxSysRollbackRescueLocation is 
         an empty string the system will attempt to store the file in the 
         best available location locally, for example compact flash 1 or 2 
         if either is present."
    DEFVAL { ''H }  -- empty string
    ::= { tmnxSysRollbackInfo 17 }

tmnxSysRollbackRescueRevert    OBJECT-TYPE
    SYNTAX      TmnxActionType
    MAX-ACCESS  read-write
    STATUS      current
    DESCRIPTION
        "The value of tmnxSysRollbackRescueRevert specifies whether to
         revert the rollback rescue file located in tmnxSysRollbackRescueLocation.
         
         When SET to the value of 'doAction' the system will revert the
         rollback rescue file.
         
         An SNMP GET request on this object should return 'notApplicable'." 
    DEFVAL { notApplicable }
    ::= {tmnxSysRollbackInfo 18 }

tmnxSysRollbackRescueSave    OBJECT-TYPE
    SYNTAX      TmnxActionType
    MAX-ACCESS  read-write
    STATUS      current
    DESCRIPTION
        "The value of tmnxSysRollbackRescueSave specifies whether to save
         the existing configuration in the rollback rescue file located in 
         tmnxSysRollbackRescueLocation.
         
         When SET to the value of 'doAction' the system will save the
         configuration to the rollback rescue file.
         
         An SNMP GET request on this object should return 'notApplicable'."
    DEFVAL { notApplicable }
    ::= {tmnxSysRollbackInfo 19 }


tmnxSysRollbackRescueDelete    OBJECT-TYPE
    SYNTAX      TmnxActionType
    MAX-ACCESS  read-write
    STATUS      current
    DESCRIPTION
        "The value of tmnxSysRollbackRescueDelete specifies whether to delete 
         the rollback rescue file located in tmnxSysRollbackRescueLocation. 
         
         When SET to the value of 'doAction' the system will delete the
         rollback rescue file.
         
         An SNMP GET request on this object should return 'notApplicable'." 
    DEFVAL { notApplicable }
    ::= {tmnxSysRollbackInfo 20 }

tmnxSysRollbackRescueSaveRes OBJECT-TYPE
    SYNTAX      INTEGER {
                    none (1),
                    inProgress (2),
                    success (3),
                    failed (4)
                }
    MAX-ACCESS  read-only
    STATUS      current
    DESCRIPTION
        "The value of tmnxSysRollbackRescueSaveRes indicates the result 
         of the last tmnxSysRollbackRescueSave action.

         none(1)            None of the following apply
         inProgress(2)      The action is still in progress
         success(3)         The action completed successfully
         failed(4)          The action failed"
    ::= {tmnxSysRollbackInfo 21 }

tmnxSysRollbackRescueRevertRes OBJECT-TYPE
    SYNTAX      INTEGER {
                    none (1),
                    inProgress (2),
                    success (3),
                    failed (4),
                    interrupted (5)
                }
    MAX-ACCESS  read-only
    STATUS      current
    DESCRIPTION
        "The value of tmnxSysRollbackRescueRevertRes indicates the result 
         of the last tmnxSysRollbackRescueRevert action.

         none(1)            None of the following apply
         inProgress(2)      The action is still in progress
         success(3)         The action completed successfully
         failed(4)          The action failed
         interrupted (5)    The action was interrupted"
    ::= {tmnxSysRollbackInfo 22 }

tmnxSysRollbackRescueDeleteRes OBJECT-TYPE
    SYNTAX      INTEGER {
                    none (1),
                    inProgress (2),
                    success (3),
                    failed (4)
                }
    MAX-ACCESS  read-only
    STATUS      current
    DESCRIPTION
        "The value of tmnxSysRollbackRescueDeleteRes indicates the result of
         the last tmnxSysRollbackRescueDelete action.

         none(1)            None of the following apply
         inProgress(2)      The action is still in progress
         success(3)         The action completed successfully
         failed(4)          The action failed"
    ::= {tmnxSysRollbackInfo 23 }


tmnxSysRollbackRescueSavedTime   OBJECT-TYPE
    SYNTAX      DateAndTime 
    MAX-ACCESS  read-only
    STATUS      current
    DESCRIPTION
         "The value of tmnxSysRollbackRescueSavedTime indicates the timestamp  
          the last rollback rescue save on the system is completed.
          The value of tmnxSysRollbackRescueSavedTime is affected by the value
          of stiPreferLocalTime.
         "
    ::= { tmnxSysRollbackInfo 24 }

tmnxSysRollbackRescueRevStTime   OBJECT-TYPE
    SYNTAX      DateAndTime 
    MAX-ACCESS  read-only
    STATUS      current
    DESCRIPTION
         "The value of tmnxSysRollbackRescueRevStTime indicates the 
          timestamp the last rescue rollback file reverted on the system 
          is initiated.
          The value of tmnxSysRollbackRescueRevStTime is affected by the value
          of stiPreferLocalTime.
         "
    ::= { tmnxSysRollbackInfo 25}

tmnxSysRollbackRescueRevEdTime   OBJECT-TYPE
    SYNTAX      DateAndTime 
    MAX-ACCESS  read-only
    STATUS      current
    DESCRIPTION
         "The value of tmnxSysRollbackRescueRevEdTime indicates the 
          timestamp the last rollback rescue revert on the system is completed.
          The value of tmnxSysRollbackRescueRevEdTime is affected by the value
          of stiPreferLocalTime.
         "
    ::= { tmnxSysRollbackInfo 26 }

tmnxSysRollbackRescueRevUser  OBJECT-TYPE
    SYNTAX      TNamedItemOrEmpty
    MAX-ACCESS  read-only 
    STATUS      current
    DESCRIPTION
        "The value of tmnxSysRollbackRescueRevUser indicates the name of
         a system user who initiates the last rollback rescue revert."
    DEFVAL { ''H }    -- the empty string
    ::= { tmnxSysRollbackInfo 27 }

tmnxSysRollbackRescueSaveComment OBJECT-TYPE
    SYNTAX      DisplayString (SIZE(0..255))
    MAX-ACCESS  read-write
    STATUS      current
    DESCRIPTION
       "The value of the object tmnxSysRollbackRescueSaveComment specifies
        a user provided comment related to the rollback rescue file about 
        to be saved. 

        It consists of any printable, seven-bit ASCII characters up to 255 
        characters in length."
    DEFVAL { ''H }    -- the empty string
    ::= { tmnxSysRollbackInfo 28 }

tmnxSysRollbackRescueAbortRevert    OBJECT-TYPE
    SYNTAX      TmnxActionType
    MAX-ACCESS  read-write
    STATUS      current
    DESCRIPTION
        "The value of tmnxSysRollbackRescueAbortRevert specifies whether to
         abort the rescue revert that's currently in progress.

         When SET to the value of 'doAction' the system will abort the active
         rollback revert. This will leave the system in an unknown state, so it
         should be used with care.

         An SNMP GET request on this object should return 'notApplicable'." 
    DEFVAL { notApplicable }
    ::= {tmnxSysRollbackInfo 29}

tmnxSysRollbackRescueFileExists OBJECT-TYPE
    SYNTAX      TruthValue
    MAX-ACCESS  read-only
    STATUS      current
    DESCRIPTION
        "The value of tmnxSysRollbackRescueFileExists indicates whether 
         a rollback rescue file specified by tmnxSysRollbackRescueLocation  
         and suffix '.rc' is present.

         A value of 'true' indicates the file is present and a value of 'false' 
         indicates the file is not present."
    DEFVAL { false }
    ::= {tmnxSysRollbackInfo 30}

tmnxSysRollbackMaxLocalFiles OBJECT-TYPE
    SYNTAX      Unsigned32 (1..50)
    MAX-ACCESS  read-write
    STATUS      current
    DESCRIPTION
        "The value of tmnxSysRollbackMaxLocalFiles specifies the maximum
         number of rollback checkpoint files that can be saved locally 
         on the compact flash."
    DEFVAL { 10 }
    ::= {tmnxSysRollbackInfo 31} 

tmnxSysRollbackMaxRemoteFiles OBJECT-TYPE
    SYNTAX      Unsigned32 (1..200)
    MAX-ACCESS  read-write
    STATUS      current
    DESCRIPTION
        "The value of tmnxSysRollbackMaxRemoteFiles specifies the maximum
         number of rollback checkpoint files that can be saved at a remote ftp
         location."
    DEFVAL { 10 }
    ::= {tmnxSysRollbackInfo 32} 

tmnxSysRollbackTableLastChanged   OBJECT-TYPE
    SYNTAX      TimeStamp 
    MAX-ACCESS  read-only
    STATUS      current
    DESCRIPTION
         "The value of tmnxSysRollbackTableLastChanged indicates the 
          timestamp of the last configuration changes to any of the rows in 
          tmnxSysRollbackFileTable."
    ::= { tmnxSysObjs 18 }

tmnxSysRollbackFileTable OBJECT-TYPE
    SYNTAX      SEQUENCE OF TmnxSysRollbackFileEntry
    MAX-ACCESS  not-accessible
    STATUS      current
    DESCRIPTION
        "The table tmnxSysRollbackFileTable contains information pertaining 
         to an entry for each rollback checkpoint file.

         If the configured rollback location as specified by 
         tmnxSysRollbackLocation is on compact flash, this table can have
         up to a maximum of tmnxSysRollbackMaxLocalFiles.

         If the configured rollback location as specified by 
         tmnxSysRollbackLocation is a remote ftp location, this table can have
         up to a maximum of tmnxSysRollbackMaxRemoteFiles."
    ::= { tmnxSysObjs 19 }

tmnxSysRollbackFileEntry OBJECT-TYPE
    SYNTAX      TmnxSysRollbackFileEntry
    MAX-ACCESS  not-accessible
    STATUS      current
    DESCRIPTION
        "Each row entry contains information about a rollback checkpoint file."
    INDEX { tmnxSysRollbackFileIndex }
    ::= { tmnxSysRollbackFileTable 1 }

TmnxSysRollbackFileEntry ::=
    SEQUENCE {
        tmnxSysRollbackFileIndex            Unsigned32,
        tmnxSysRollbackFileCreationTime     DateAndTime,
        tmnxSysRollbackFileComment          DisplayString, 
        tmnxSysRollbackFileUserName         TNamedItem,
        tmnxSysRollbackFileVersion          DisplayString 
    }

tmnxSysRollbackFileIndex OBJECT-TYPE
    SYNTAX      Unsigned32 (0..199)
    MAX-ACCESS  not-accessible
    STATUS      current
    DESCRIPTION
        "The value of tmnxSysRollbackFileIndex specifies the index of the 
         rollback checkpoint file."
    ::= { tmnxSysRollbackFileEntry 1 }

tmnxSysRollbackFileCreationTime   OBJECT-TYPE
    SYNTAX      DateAndTime 
    MAX-ACCESS  read-only
    STATUS      current
    DESCRIPTION
       "The value of tmnxSysRollbackFileCreationTime indicates the timestamp of 
        the creation time of this row in tmnxSysRollbackFileTable.
        The value of tmnxSysRollbackFileCreationTime is affected by the value
        of stiPreferLocalTime.
       "
    ::= { tmnxSysRollbackFileEntry 2 }

tmnxSysRollbackFileComment OBJECT-TYPE
    SYNTAX      DisplayString (SIZE(0..255))
    MAX-ACCESS  read-only
    STATUS      current
    DESCRIPTION
       "The value of the object tmnxSysRollbackFileComment specifies
        a user provided comment related to a rollback checkpoint file.

        It consists of any printable, seven-bit ASCII characters up to 255 
        characters in length."
    ::= { tmnxSysRollbackFileEntry 3 }

tmnxSysRollbackFileUserName  OBJECT-TYPE
    SYNTAX      TNamedItem
    MAX-ACCESS  read-only 
    STATUS      current
    DESCRIPTION
        "The value of tmnxSysRollbackFileUserName indicates the name of
         a system user who saves this rollback file."
    ::= { tmnxSysRollbackFileEntry 4 }

tmnxSysRollbackFileVersion   OBJECT-TYPE
    SYNTAX      DisplayString (SIZE(0..32)) 
    MAX-ACCESS  read-only
    STATUS      current
    DESCRIPTION
        "The value of tmnxSysRollbackFileVersion indicates the version number
         of the software running on the system when the rollback file is saved."
    ::= { tmnxSysRollbackFileEntry 5 }


--
--  System Booted Boot Options File (BOF) Information
--
sysBootedBofInfo    OBJECT IDENTIFIER ::= { tmnxSysObjs 20 }

sbbiLiSeparate    OBJECT-TYPE
    SYNTAX      TruthValue
    MAX-ACCESS  read-only
    STATUS      current
    DESCRIPTION
        "This object gives the currently active (booted) value of li-separate. 
         This value specifies whether or not a non-LI user has access to 
         Lawful Intercept (LI) information. When sbbiLiSeparate has a value 
         of 'true', a user who does not have the TIMETRA-SECURITY-MIB::
         tmnxUserAccess 'li' bit set will not be allowed to access CLI or 
         SNMP objects in the 'li' context."
    ::= { sysBootedBofInfo 1 }

sbbiLiLocalSave      OBJECT-TYPE
    SYNTAX      TruthValue      
    MAX-ACCESS  read-only
    STATUS      current
    DESCRIPTION
        "This object gives the currently active (booted) value of 
         li-local-save. This value specifies whether or not Lawful
         Intercept (LI) configuration is allowed to be save to a local
         file."
    ::= { sysBootedBofInfo 2 }

--
-- Registering OID for MG
--

sysMGMCSwitchOverInfo    OBJECT IDENTIFIER ::= { tmnxSysObjs 21 }

--
-- Candidate Config Global Information
--

tmnxSysCandidateCfgInfo     OBJECT IDENTIFIER ::= { tmnxSysObjs 22 }

tmnxSysCandidateCfgState OBJECT-TYPE
    SYNTAX      INTEGER {
                    unmodified  (0),
                    modified    (1),
                    unconfirmed (2)
                }
    MAX-ACCESS  read-only
    STATUS      current
    DESCRIPTION
        "The value of tmnxSysCandidateCfgState indicates the current state of
         the global candidate config.

         A value of 'unmodified(0)' indicates nobody has entered the candidate
         config since boot or the last commit/discard.
         A value of 'modified(1)' indicates there are uncommitted changes in the
         candidate config.
         A value of 'unconfirmed(2)' indicates there are no uncommitted changes
         in the candidate config but the result of the last commit will be
         auto-reverted unless it is confirmed before the timeout expires."
    ::= { tmnxSysCandidateCfgInfo 1 }

tmnxSysCandidateCfgEditors OBJECT-TYPE
    SYNTAX       INTEGER
    MAX-ACCESS  read-only
    STATUS      current
    DESCRIPTION
        "The value of tmnxSysCandidateCfgEditors indicates the current amount
         of users that are editing or reading the candidate config."
    ::= { tmnxSysCandidateCfgInfo 2 }

tmnxSysCandidateCfgCommitState OBJECT-TYPE
    SYNTAX      INTEGER {
                    none               (0),
                    in-progress        (1),
                    success            (2),
                    revert-pending     (3),
                    failed             (4),
                    revert-in-progress (5),
                    reverted           (6),
                    revert-failed      (7)
                }
    MAX-ACCESS  read-only
    STATUS      current
    DESCRIPTION
        "The value of tmnxSysCandidateCfgCommitState indicates the result of
         the last commit performed in the global candidate config.

          A value of 'none(0)' indicates there have been no commits since the
          last reboot of the node.
          A value of 'in-progress(1)' indicates the system is currently
          committing the candidate config.
          A value of 'success(2)' indicates the last commit finished
          successfully.
          A value of 'revert-pending(3)' indicates the last commit finished
          successfully but has not been confirmed yet, and will be auto-reverted
          if it is not confirmed before the time specified in
          tmnxSysCandidateCfgRevertTime.
          A value of 'failed(4)' indicates the last commit failed and has been
          undone.
          A value of 'revert-in-progress(5)' indicates the last commit finished
          successfully but was not confirmed in time and is currently being
          reverted.
          A value of 'reverted(6)' indicates the last commit finished
          successfully but was not confirmed in time and has been reverted.
          A value of 'revert-failed(7)' indicates the last commit finished
          successfully but was not confirmed in time and the system attempted to
          revert it but failed."
    ::= { tmnxSysCandidateCfgInfo 3 }

tmnxSysCandidateCfgCommitTime OBJECT-TYPE
    SYNTAX      DateAndTime
    MAX-ACCESS  read-only
    STATUS      current
    DESCRIPTION
        "The value of tmnxSysCandidateCfgCommitTime indicates the date and time
        the last (attempted) commit of the candidate config was started."
    ::= { tmnxSysCandidateCfgInfo 4 }

tmnxSysCandidateCfgRevertTime OBJECT-TYPE
    SYNTAX      DateAndTime
    MAX-ACCESS  read-only
    STATUS      current
    DESCRIPTION
        "The value of tmnxSysCandidateCfgRevertTime indicates the date and time
         the system will automatically revert the last committed candidate
         config, unless they are confirmed.
         
         If this date and time is in the past it indicates the candidate config 
         was not confirmed and has been reverted.
         
         If no auto-revert was requested at the time of the commit the value
         of this field will be set to zero."
    ::= { tmnxSysCandidateCfgInfo 5 }

tmnxSysCandidateCfgChckptCreated OBJECT-TYPE
    SYNTAX      TruthValue
    MAX-ACCESS  read-only
    STATUS      current
    DESCRIPTION
        "The value of tmnxSysCandidateCfgChckptCreated indicates if a checkpoint
         was created after the last commit of the candidate config."
    ::= { tmnxSysCandidateCfgInfo 6 }

tmnxSysCandidateCfgUser OBJECT-TYPE
    SYNTAX      TNamedItemOrEmpty
    MAX-ACCESS  read-only
    STATUS      current
    DESCRIPTION
        "The value of tmnxSysCandidateCfgUser indicates the name of
         a system user who initiated the last commit of the candidate config."
    ::= { tmnxSysCandidateCfgInfo 7 }

tmnxSysCandidateCfgExclusiveUsr OBJECT-TYPE
    SYNTAX      TNamedItemOrEmpty
    MAX-ACCESS  read-only
    STATUS      current
    DESCRIPTION
        "The value of tmnxSysCandidateCfgExclusiveUsr indicates the name of
         a system user who is currently exclusively modifying the candidate
         config. This indicates no other user can modify the candidate config
         until this system user has finished modifying the candidate config.
         
         If this field is empty no user has requested to exclusively modify the
         candidate config."
    ::= { tmnxSysCandidateCfgInfo 8 }

--
--  NETCONF Global Information
--

tmnxSysNetconfInfo    OBJECT IDENTIFIER ::= { tmnxSysObjs 23 }

tmnxSysNetconfAdminStatus OBJECT-TYPE
    SYNTAX      TmnxAdminState
    MAX-ACCESS  read-write
    STATUS      current
    DESCRIPTION
        "The value of tmnxSysNetconfAdminStatus specifies the desired
         administrative state of the NETCONF daemon. When
         tmnxSysNetconfAdminStatus is set to 'inService', the NETCONF daemon
         will begin receiving NETCONF requests from external NETCONF users.
         When tmnxSysNetconfAdminStatus is set to 'outOfService', the NETCONF
         daemon is suspended and will no longer receive NETCONF requests from
         external NETCONF users."
    DEFVAL { outOfService }
    ::= { tmnxSysNetconfInfo 1 }

tmnxSysNetconfOperStatus OBJECT-TYPE
    SYNTAX      TmnxOperState
    MAX-ACCESS  read-only
    STATUS      current
    DESCRIPTION
        "The value of tmnxSysNetconfOperStatus indicates the state of the
         NETCONF daemon. A value of 'inService' indicates that the NETCONF
         daemon will receive NETCONF requests from external NETCONF users. A
         value of 'outOfService' indicates that the NETCONF daemon is suspended
         and will no longer receive NETCONF requests from external NETCONF
         users."
    ::= { tmnxSysNetconfInfo 2 }

tmnxSysNetconfRequests OBJECT-TYPE
    SYNTAX      Counter32
    MAX-ACCESS  read-only
    STATUS      current
    DESCRIPTION
        "The value of tmnxSysNetconfRequests indicates the total number of
         NETCONF requests which have been accepted and processed by the NETCONF
         server."
    ::= { tmnxSysNetconfInfo 3 }

tmnxSysNetconfGetRequests OBJECT-TYPE
    SYNTAX      Counter32
    MAX-ACCESS  read-only
    STATUS      current
    DESCRIPTION
        "The value of tmnxSysNetconfGetRequests indicates the total number of
         get NETCONF requests which have been accepted and processed by the
         NETCONF server."
    ::= { tmnxSysNetconfInfo 4 }

tmnxSysNetconfGetConfigRequests OBJECT-TYPE
    SYNTAX      Counter32
    MAX-ACCESS  read-only
    STATUS      current
    DESCRIPTION
        "The value of tmnxSysNetconfGetConfigRequests indicates the total
         number of get-config NETCONF requests which have been accepted and
         processed by the NETCONF server."
    ::= { tmnxSysNetconfInfo 5 }

tmnxSysNetconfEditConfigRequests OBJECT-TYPE
    SYNTAX      Counter32
    MAX-ACCESS  read-only
    STATUS      current
    DESCRIPTION
        "The value of tmnxSysNetconfEditConfigRequests indicates the total
         number of edit-config NETCONF requests which have been accepted and
         processed by the NETCONF server."
    ::= { tmnxSysNetconfInfo 6 }

tmnxSysNetconfCloseRequests OBJECT-TYPE
    SYNTAX      Counter32
    MAX-ACCESS  read-only
    STATUS      current
    DESCRIPTION
        "The value of tmnxSysNetconfCloseRequests indicates the total number of
         close-session NETCONF requests which have been accepted and processed
         by the NETCONF server."
    ::= { tmnxSysNetconfInfo 7 }

tmnxSysNetconfKillRequests OBJECT-TYPE
    SYNTAX      Counter32
    MAX-ACCESS  read-only
    STATUS      current
    DESCRIPTION
        "The value of tmnxSysNetconfKillRequests indicates the total number of
         kill-session NETCONF requests which have been accepted and processed
         by the NETCONF server."
    ::= { tmnxSysNetconfInfo 8 }

tmnxSysNetconfResponses OBJECT-TYPE
    SYNTAX      Counter32
    MAX-ACCESS  read-only
    STATUS      current
    DESCRIPTION
        "The value of tmnxSysNetconfResponses indicates the total number of
         NETCONF responses which have been generated and sent by the NETCONF
         server."
    ::= { tmnxSysNetconfInfo 9 }

tmnxSysNetconfErrorResponses OBJECT-TYPE
    SYNTAX      Counter32
    MAX-ACCESS  read-only
    STATUS      current
    DESCRIPTION
        "The value of tmnxSysNetconfErrorResponses indicates the total number
         of NETCONF error responses which have been generated and sent by the
         NETCONF server."
    ::= { tmnxSysNetconfInfo 10 }


tmnxSysNetconfCopyConfigRequests OBJECT-TYPE
    SYNTAX      Counter32
    MAX-ACCESS  read-only
    STATUS      current
    DESCRIPTION
        "The value of tmnxSysNetconfCopyConfigRequests indicates the total
         number of copy-config NETCONF requests which have been accepted and
         processed by the NETCONF server."
    ::= { tmnxSysNetconfInfo 11 }

tmnxSysNetconfDelConfigRequests OBJECT-TYPE
    SYNTAX      Counter32
    MAX-ACCESS  read-only
    STATUS      current
    DESCRIPTION
        "The value of tmnxSysNetconfDelConfigRequests indicates the total
         number of delete-config NETCONF requests which have been accepted and
         processed by the NETCONF server."
    ::= { tmnxSysNetconfInfo 12 }

tmnxSysNetconfValidateRequests OBJECT-TYPE
    SYNTAX      Counter32
    MAX-ACCESS  read-only
    STATUS      current
    DESCRIPTION
        "The value of tmnxSysNetconfValidateRequests indicates the total
         number of validate NETCONF requests which have been accepted and
         processed by the NETCONF server."
    ::= { tmnxSysNetconfInfo 13 }


tmnxSysNetconfFailedEditCfgReqs OBJECT-TYPE
    SYNTAX      Counter32
    MAX-ACCESS  read-only
    STATUS      current
    DESCRIPTION
        "The value of tmnxSysNetconfFailedEditCfgReqs indicates the total
         number of edit-config NETCONF requests which have failed because of
         locks taken by other NETCONF sessions."
    ::= { tmnxSysNetconfInfo 14 }

tmnxSysNetconfFailedLockReqs OBJECT-TYPE
    SYNTAX      Counter32
    MAX-ACCESS  read-only
    STATUS      current
    DESCRIPTION
        "The value of tmnxSysNetconfFailedLockReqs indicates the total
         number of lock NETCONF requests which have failed because of
         locks taken by other NETCONF sessions."
    ::= { tmnxSysNetconfInfo 15 }

tmnxSysNetconfLockRequests OBJECT-TYPE
    SYNTAX      Counter32
    MAX-ACCESS  read-only
    STATUS      current
    DESCRIPTION
        "The value of tmnxSysNetconfLockRequests indicates the total
         number of lock NETCONF requests which have been accepted and
         processed by the NETCONF server."
    ::= { tmnxSysNetconfInfo 16 }

tmnxSysNetconfUnlockRequests OBJECT-TYPE
    SYNTAX      Counter32
    MAX-ACCESS  read-only
    STATUS      current
    DESCRIPTION
        "The value of tmnxSysNetconfUnlockRequests indicates the total
         number of unlock NETCONF requests which have been accepted
         and processed by the NETCONF server."
    ::= { tmnxSysNetconfInfo 17 }

tmnxSysNetconfCommitRequests OBJECT-TYPE
    SYNTAX      Counter32
    MAX-ACCESS  read-only
    STATUS      current
    DESCRIPTION
        "The value of tmnxSysNetconfCommitRequests indicates the total
         number of commit NETCONF requests which have been accepted
         and processed by the NETCONF server."
    ::= { tmnxSysNetconfInfo 18 }

tmnxSysNetconfDiscardRequests OBJECT-TYPE
    SYNTAX      Counter32
    MAX-ACCESS  read-only
    STATUS      current
    DESCRIPTION
        "The value of tmnxSysNetconfDiscardRequests indicates the total
         number of discard change NETCONF requests which have been accepted
         and processed by the NETCONF server."
    ::= { tmnxSysNetconfInfo 19 }

tmnxSysNetconfCapCandidateCfg OBJECT-TYPE
    SYNTAX      TruthValue
    MAX-ACCESS  read-write
    STATUS      current
    DESCRIPTION
        "The value of tmnxSysNetconfCapCandidateCfg specifies whether or not the
         candidate datastore is supported by the NETCONF server. When set to
         'true', the NETCONF server allows access to the candidate datastore."
    DEFVAL { true }
    ::= { tmnxSysNetconfInfo 20 }

tmnxSysNetconfCapRunningCfg OBJECT-TYPE
    SYNTAX      TruthValue
    MAX-ACCESS  read-write
    STATUS      current
    DESCRIPTION
        "The value of tmnxSysNetconfCapRunningCfg specifies whether or not the
         writable running datastore is supported by the NETCONF server. When
         set to 'true', the NETCONF server allows access to the writable
         running datastore."
    DEFVAL { true }
    ::= { tmnxSysNetconfInfo 21 }

tmnxSysNetconfYangBaseR13 OBJECT-TYPE
    SYNTAX      TruthValue
    MAX-ACCESS  read-write
    STATUS      current
    DESCRIPTION
        "The value of tmnxSysNetconfYangBaseR13 specifies whether or not the
         base release 13 Yang models are supported by the NETCONF server. When
         set to 'true', the NETCONF server allows access to base release 13 Yang
         models."
    DEFVAL { true }
    ::= { tmnxSysNetconfInfo 22 }

tmnxSysNetconfYangNokia OBJECT-TYPE
    SYNTAX      TruthValue
    MAX-ACCESS  read-write
    STATUS      current
    DESCRIPTION
        "The value of tmnxSysNetconfYangNokia specifies whether or not the
         Nokia Yang models are supported by the NETCONF server. When
         set to 'true', the NETCONF server allows access to the Nokia Yang
         models."
    DEFVAL { true }
    ::= { tmnxSysNetconfInfo 23 }

--
--  Streaming Feature Global Information
--

tmnxSysStrmInfo    OBJECT IDENTIFIER ::= { tmnxSysObjs 25 }

tmnxSysStrmAdminStatus OBJECT-TYPE
    SYNTAX      TmnxAdminState
    MAX-ACCESS  read-write
    STATUS      current
    DESCRIPTION
        "The value of tmnxSysStrmAdminStatus specifies the desired
         administrative state of the proprietary protocol streaming server
         daemon.  When tmnxSysStrmAdminStatus is set to 'inService', the
         streaming server daemon accepts and processes requests from the
         Nokia 5620 Service Aware Manager (SAM) system. When
         tmnxSysStrmAdminStatus is set to 'outOfService', the streaming server
         daemon is suspended and will no longer accept requests from the SAM
         system."
    DEFVAL { outOfService }
    ::= { tmnxSysStrmInfo 1 }

tmnxSysStrmDumpSnmpRequests OBJECT-TYPE
    SYNTAX      Counter32
    MAX-ACCESS  read-only
    STATUS      current
    DESCRIPTION
        "The value of tmnxSysStrmDumpSnmpRequests indicates the total number of
         streaming snmp dump request PDUs which have been accepted and processed by the
         Nokia 5620 Service Aware Manager (SAM) streaming protocol
         entity."
    ::= { tmnxSysStrmInfo 2 }

tmnxSysStrmGetManyRequests OBJECT-TYPE
    SYNTAX      Counter32
    MAX-ACCESS  read-only
    STATUS      current
    DESCRIPTION
        "The value of tmnxSysStrmGetManyRequests indicates the total number of
         streaming get many request PDUs which have been accepted and processed by the
         Nokia 5620 Service Aware Manager (SAM) streaming protocol
         entity."
    ::= { tmnxSysStrmInfo 3 }

tmnxSysStrmResponses OBJECT-TYPE
    SYNTAX      Counter32
    MAX-ACCESS  read-only
    STATUS      current
    DESCRIPTION
        "The value of tmnxSysStrmResponses indicates the total number of
         streaming response PDUs which have been generated by the
         Nokia 5620 Service Aware Manager (SAM) streaming protocol
         entity."
    ::= { tmnxSysStrmInfo 4 }


--
--      Xmpp Server Information
--

tmnxSysXmppInfo    OBJECT IDENTIFIER ::= { tmnxSysObjs 26 }

tmnxSysXmppServerTable  OBJECT-TYPE
    SYNTAX      SEQUENCE OF TmnxSysXmppServerEntry
    MAX-ACCESS  not-accessible
    STATUS      current
    DESCRIPTION
        "The tmnxSysXmppServerTable contains information pertaining
         to an entry for each server. Row entries are created and
         deleted by the agent."
    ::= { tmnxSysXmppInfo 1 }

tmnxSysXmppServerEntry OBJECT-TYPE
    SYNTAX      TmnxSysXmppServerEntry
    MAX-ACCESS  not-accessible
    STATUS      current
    DESCRIPTION
        "Each row entry contains information about a XMPP server."
    INDEX   {
                tmnxSysXmppServName
            }
    ::= { tmnxSysXmppServerTable 1 }

TmnxSysXmppServerEntry ::=
    SEQUENCE {
        tmnxSysXmppServName                DisplayString,
        tmnxSysXmppServFQDN                DisplayString,
        tmnxSysXmppServRowStatus           RowStatus,
        tmnxSysXmppServUserName            TNamedItemOrEmpty,
        tmnxSysXmppServPassword            DisplayString,
        tmnxSysXmppServLastChanged         TimeStamp,
        tmnxSysXmppServUptime              TimeStamp,    
        tmnxSysXmppServIQSent              Counter64,
        tmnxSysXmppServIQRcvd              Counter64,
        tmnxSysXmppServIQError             Counter64,
        tmnxSysXmppServIQTimedOut          Counter64,
        tmnxSysXmppServIQAckRcvd           Counter64,
        tmnxSysXmppServIQMinRtt            Counter64,
        tmnxSysXmppServIQMaxRtt            Counter64,
        tmnxSysXmppServVsdUpdatesRcvd      Counter64,
        tmnxSysXmppServUpdatesRcvd         Counter64,
        tmnxSysXmppServMsgSent             Counter64,
        tmnxSysXmppServMsgRcvd             Counter64, 
        tmnxSysXmppServMsgAckRcvd          Counter64,
        tmnxSysXmppServMsgError            Counter64,
        tmnxSysXmppServMsgTimedOut         Counter64,
        tmnxSysXmppServMsgMinRtt           Counter64,
        tmnxSysXmppServMsgMaxRtt           Counter64,
        tmnxSysXmppServSubSent             Counter64,
        tmnxSysXmppServUnSubSent           Counter64,
        tmnxSysXmppServState               DisplayString,
        tmnxSysXmppServAdminState          TmnxAdminState,
        tmnxSysXmppServOperUserName        TNamedItemOrEmpty,
        tmnxSysXmppServAuthType            TNamedItemOrEmpty,
        tmnxSysXmppServConnMode            INTEGER,
        tmnxSysXmppServServiceId           TmnxServId,
        tmnxSysXmppServRouterId            TmnxVRtrIDOrZero
    }

tmnxSysXmppServName    OBJECT-TYPE
    SYNTAX          DisplayString (SIZE (0..32))
    MAX-ACCESS      not-accessible
    STATUS          current
    DESCRIPTION
        "The value of tmnxSysXmppServName indicates the name associated
         with the XMPP Server."
    ::= { tmnxSysXmppServerEntry 1 }

tmnxSysXmppServFQDN    OBJECT-TYPE
    SYNTAX          DisplayString (SIZE (0..255))
    MAX-ACCESS      read-create
    STATUS          current
    DESCRIPTION
        "The value of tmnxSysXmppServFQDN specifies the Fully
         Qualified Domain Name (FQDN) associated with the XMPP Server."
    ::= { tmnxSysXmppServerEntry 2 }

tmnxSysXmppServRowStatus OBJECT-TYPE
    SYNTAX     RowStatus
    MAX-ACCESS read-create
    STATUS     current
    DESCRIPTION
        "The value of tmnxSysXmppServRowStatus specifies the row status.
         It is used to create and delete row entries in this table."
    ::= { tmnxSysXmppServerEntry 3 }

tmnxSysXmppServUserName  OBJECT-TYPE
   SYNTAX      TNamedItemOrEmpty
   MAX-ACCESS  read-create
   STATUS      current
   DESCRIPTION
       "The value of tmnxSysXmppServUserName specifies the username that
        is used in the XMPP server access requests. When no username is
        not provided,  the chassis MAC is used as the default user name."
   ::= { tmnxSysXmppServerEntry 4 }

tmnxSysXmppServPassword OBJECT-TYPE
   SYNTAX      DisplayString (SIZE (0..32))
   MAX-ACCESS  read-create
   STATUS      current
   DESCRIPTION
       "The value of tmnxSysXmppServPassword specifies
        the password that is used in the XMPP server access requests."
   DEFVAL { "" }
   ::= {tmnxSysXmppServerEntry 5 }

tmnxSysXmppServLastChanged    OBJECT-TYPE
    SYNTAX          TimeStamp
    MAX-ACCESS      read-only
    STATUS          current
    DESCRIPTION
        "The value of tmnxSysXmppServLastChanged indicates the timestamp
         of last change to this row in tmnxSysXmppServerTable."
   ::= {tmnxSysXmppServerEntry 6 }

tmnxSysXmppServUptime          OBJECT-TYPE
    SYNTAX      TimeStamp
    MAX-ACCESS  read-only
    STATUS      current
    DESCRIPTION
        "The tmnxSysXmppServUptime indicates the uptime of the XMPP server."
    ::= { tmnxSysXmppServerEntry 7 }

tmnxSysXmppServIQSent          OBJECT-TYPE
    SYNTAX          Counter64
    MAX-ACCESS      read-only
    STATUS          current
    DESCRIPTION
        "The value of tmnxSysXmppServIQSent indicates the number of XMPP 
         Info/Query message sent."
    ::= { tmnxSysXmppServerEntry 8 }

tmnxSysXmppServIQRcvd          OBJECT-TYPE
    SYNTAX          Counter64
    MAX-ACCESS      read-only
    STATUS          current
    DESCRIPTION
        "The value of tmnxSysXmppServIQRcvd indicates the number of XMPP 
         Info/Query message received."
    ::= { tmnxSysXmppServerEntry 9 }

tmnxSysXmppServIQError         OBJECT-TYPE
    SYNTAX          Counter64
    MAX-ACCESS      read-only
    STATUS          current
    DESCRIPTION
        "The value of tmnxSysXmppServIQError indicates the number of XMPP 
         Info/Query error messages received."
    ::= { tmnxSysXmppServerEntry 10 }

tmnxSysXmppServIQTimedOut         OBJECT-TYPE
   SYNTAX          Counter64
   MAX-ACCESS      read-only
   STATUS          current
   DESCRIPTION
       "The value of tmnxSysXmppServIQTimedOut indicates the number of XMPP
        Info/Query messages timed out."
   ::= { tmnxSysXmppServerEntry 11 }
      
tmnxSysXmppServIQAckRcvd         OBJECT-TYPE
   SYNTAX          Counter64
   MAX-ACCESS      read-only
   STATUS          current
   DESCRIPTION
       "The value of tmnxSysXmppServIQAckRcvd indicates the number of XMPP
        Info/Query acknowledgement messages received."
   ::= { tmnxSysXmppServerEntry 12 }
   
tmnxSysXmppServIQMinRtt         OBJECT-TYPE
   SYNTAX          Counter64
   UNITS           "milli-seconds"
   MAX-ACCESS      read-only
   STATUS          current
   DESCRIPTION
       "The value of tmnxSysXmppServIQMinRtt indicates the XMPP Info/Query
        minimum round trip time."
   ::= { tmnxSysXmppServerEntry 13 }
  
tmnxSysXmppServIQMaxRtt         OBJECT-TYPE
   SYNTAX          Counter64
   UNITS           "milli-seconds"
   MAX-ACCESS      read-only
   STATUS          current
   DESCRIPTION
       "The value of tmnxSysXmppServIQMaxRtt indicates the XMPP Info/Query
        maximum round trip time."
   ::= { tmnxSysXmppServerEntry 14 }
   
tmnxSysXmppServVsdUpdatesRcvd         OBJECT-TYPE
    SYNTAX          Counter64
    MAX-ACCESS      read-only
    STATUS          current
    DESCRIPTION
        "The value of tmnxSysXmppServVsdUpdatesRcvd indicates the number of
         VSD updates received by the XMPP server."
    ::= { tmnxSysXmppServerEntry 15 }
   
tmnxSysXmppServUpdatesRcvd         OBJECT-TYPE
    SYNTAX          Counter64
    MAX-ACCESS      read-only
    STATUS          current
    DESCRIPTION
        "The value of tmnxSysXmppServUpdatesRcvd indicates the number of
         nuage updates received by the XMPP server."
   ::= { tmnxSysXmppServerEntry 16 }
  
tmnxSysXmppServMsgSent         OBJECT-TYPE
    SYNTAX          Counter64
    MAX-ACCESS      read-only
    STATUS          current
    DESCRIPTION
       "The value of tmnxSysXmppServMsgSent indicates the number of 
        messages sent from the XMPP server."
   ::= { tmnxSysXmppServerEntry 17 }
  
tmnxSysXmppServMsgRcvd         OBJECT-TYPE   
   SYNTAX          Counter64  
   MAX-ACCESS      read-only  
   STATUS          current    
   DESCRIPTION    
       "The value of tmnxSysXmppServMsgRcvd indicates the number of    
        messages received from the XMPP server."  
   ::= { tmnxSysXmppServerEntry 18 }     
  
tmnxSysXmppServMsgAckRcvd         OBJECT-TYPE    
   SYNTAX          Counter64  
   MAX-ACCESS      read-only  
   STATUS          current    
   DESCRIPTION    
       "The value of tmnxSysXmppServMsgAckRcvd indicates the number of     
        message acknowledgements received from the XMPP server."  
   ::= { tmnxSysXmppServerEntry 19 }     
  
tmnxSysXmppServMsgError         OBJECT-TYPE  
   SYNTAX          Counter64  
   MAX-ACCESS      read-only  
   STATUS          current    
   DESCRIPTION    
       "The value of tmnxSysXmppServMsgError indicates the number of   
        error messages received from the XMPP server."    
   ::= { tmnxSysXmppServerEntry 20 }     
  
tmnxSysXmppServMsgTimedOut         OBJECT-TYPE   
   SYNTAX          Counter64  
   MAX-ACCESS      read-only  
   STATUS          current    
   DESCRIPTION    
       "The value of tmnxSysXmppServMsgTimedOut indicates the number of     
         timeout messages received from the XMPP server."    
   ::= { tmnxSysXmppServerEntry 21 }     
  
tmnxSysXmppServMsgMinRtt         OBJECT-TYPE     
   SYNTAX          Counter64  
   UNITS           "milli-seconds"
   MAX-ACCESS      read-only  
   STATUS          current    
   DESCRIPTION    
       "The value of tmnxSysXmppServMsgMinRtt indicates the minimum  
         message round trip time from the XMPP server."  
   ::= { tmnxSysXmppServerEntry 22 }     
  
tmnxSysXmppServMsgMaxRtt         OBJECT-TYPE     
   SYNTAX          Counter64  
   UNITS           "milli-seconds"
   MAX-ACCESS      read-only  
   STATUS          current    
   DESCRIPTION    
       "The value of tmnxSysXmppServMsgMaxRtt indicates the maximum     
         message round trip time from the XMPP server."  
   ::= { tmnxSysXmppServerEntry 23 }     
  
tmnxSysXmppServSubSent         OBJECT-TYPE   
    SYNTAX          Counter64     
    MAX-ACCESS      read-only     
    STATUS          current   
    DESCRIPTION   
        "The value of tmnxSysXmppServSubSent indicates the number of    
          subscriptions sent from the XMPP server."  
    ::= { tmnxSysXmppServerEntry 24 }    
  
tmnxSysXmppServUnSubSent         OBJECT-TYPE    
    SYNTAX          Counter64     
    MAX-ACCESS      read-only     
    STATUS          current   
    DESCRIPTION   
        "The value of tmnxSysXmppServUnSubSent indicates the number of  
          unsubscirptions sent from the XMPP server."    
    ::= { tmnxSysXmppServerEntry 25 }

tmnxSysXmppServState            OBJECT-TYPE
    SYNTAX      DisplayString  (SIZE (0..32))
    MAX-ACCESS  read-only
    STATUS      current
    DESCRIPTION
        "The value of tmnxSysXmppServState indicates the state of the XMPP
         server."
    ::= { tmnxSysXmppServerEntry 26 }       

tmnxSysXmppServAdminState            OBJECT-TYPE
    SYNTAX      TmnxAdminState
    MAX-ACCESS  read-create
    STATUS      current
    DESCRIPTION
        "The value of tmnxSysXmppServAdminState specifies the administrative
         state of the XMPP server."
    DEFVAL { outOfService }
    ::= { tmnxSysXmppServerEntry 27 }       

tmnxSysXmppServOperUserName  OBJECT-TYPE
   SYNTAX      TNamedItemOrEmpty
   MAX-ACCESS  read-only
   STATUS      current
   DESCRIPTION
       "The value of tmnxSysXmppServOperUserName indicates the operational user
        name that is used in the XMPP server access requests. When no user
        name is not provided,  the chassis MAC is used as the default user
        name."
   ::= { tmnxSysXmppServerEntry 28 }

tmnxSysXmppServAuthType  OBJECT-TYPE
   SYNTAX      TNamedItemOrEmpty
   MAX-ACCESS  read-only
   STATUS      current
   DESCRIPTION
       "The value of tmnxSysXmppServAuthType indicates the authentication type
        that is used in the XMPP server access requests."
   ::= { tmnxSysXmppServerEntry 29 }

tmnxSysXmppServConnMode  OBJECT-TYPE
   SYNTAX      INTEGER {
                    inBand (1),
                    outOfBand (2)
               }
   MAX-ACCESS  read-only
   STATUS      current
   DESCRIPTION
       "The value of tmnxSysXmppServConnMode indicates the connection type
        that is used in the XMPP server access requests."
   ::= { tmnxSysXmppServerEntry 30 }

tmnxSysXmppServServiceId  OBJECT-TYPE
    SYNTAX      TmnxServId
    MAX-ACCESS  read-create
    STATUS      current
    DESCRIPTION
        "The tmnxSysXmppServServiceId specifies the routing context which
         provides reachability to the DNS and XMPP servers configured.

         When tmnxSysXmppServRouterId is non-zero, tmnxSysXmppServServiceId
         must be zero and vice-versa."
    DEFVAL { 0 }
    ::= { tmnxSysXmppServerEntry 31 }

tmnxSysXmppServRouterId  OBJECT-TYPE
    SYNTAX      TmnxVRtrIDOrZero
    MAX-ACCESS  read-create
    STATUS      current
    DESCRIPTION
        "The tmnxSysXmppServRouterId specifies the routing context that
         provides reachability to the DNS and XMPP servers configured.

         When tmnxSysXmppServRouterId is non-zero, tmnxSysXmppServServiceId
         must be zero and vice-versa."
    DEFVAL { 0 }
    ::= { tmnxSysXmppServerEntry 32 }

--
--      Virtual Switch VSD Server Information
--

tmnxSysVsdServerTable OBJECT-TYPE
    SYNTAX      SEQUENCE OF TmnxSysVsdServerEntry
    MAX-ACCESS  not-accessible
    STATUS      current
    DESCRIPTION
        "The tmnxSysVsdServerTable contains information pertaining
         to an entry for each server."
    ::= { tmnxSysXmppInfo 2 }

tmnxSysVsdServerEntry OBJECT-TYPE
    SYNTAX      TmnxSysVsdServerEntry
    MAX-ACCESS  not-accessible
    STATUS      current
    DESCRIPTION
        "Each row entry contains information about a VSwitch Controller VSD server."
    INDEX   {
                tmnxSysVsdServerInstance
            }
    ::= { tmnxSysVsdServerTable 1 }

TmnxSysVsdServerEntry ::=
    SEQUENCE {
        tmnxSysVsdServerInstance     Unsigned32,
        tmnxSysVsdServUptime         TimeStamp,
        tmnxSysVsdServUserName       TLDisplayString,
        tmnxSysVsdServerStatus       DisplayString,
        tmnxSysVsdServMsgSent        Counter64,
        tmnxSysVsdServMsgRcvd        Counter64,
        tmnxSysVsdServMsgAckRcvd     Counter64,
        tmnxSysVsdServMsgError       Counter64,
        tmnxSysVsdServMsgTimedOut    Counter64,
        tmnxSysVsdServMsgMinRtt      Counter64,
        tmnxSysVsdServMsgMaxRtt      Counter64
    }

tmnxSysVsdServerInstance     OBJECT-TYPE
    SYNTAX      Unsigned32
    MAX-ACCESS  not-accessible
    STATUS      current
    DESCRIPTION
        "The value of tmnxSysVsdServerInstance specifies an instance of a 
         VSwitch Controller VSD server.
         The instance Id is an internally generated number that is unique 
         for a given  VSD server."
    ::= { tmnxSysVsdServerEntry 1 }

tmnxSysVsdServUptime    OBJECT-TYPE
    SYNTAX          TimeStamp
    MAX-ACCESS      read-only
    STATUS          current
    DESCRIPTION
        "The value of tmnxSysVsdServUptime indicates the timestamp of the 
         uptime of each VSD server entry in tmnxSysXmppServerTable."
    ::= { tmnxSysVsdServerEntry 2 }

tmnxSysVsdServUserName  OBJECT-TYPE
   SYNTAX      TLDisplayString 
   MAX-ACCESS  read-only
   STATUS      current
   DESCRIPTION
       "The value of tmnxSysVsdServUserName specifies the VSD username."
   ::= { tmnxSysVsdServerEntry 3 }

tmnxSysVsdServerStatus  OBJECT-TYPE
    SYNTAX      DisplayString  (SIZE (0..32))
    MAX-ACCESS  read-only
    STATUS      current
    DESCRIPTION
        "The value of tmnxSysVsdServerStatus indicates the status of the
         VSD server."
    ::= { tmnxSysVsdServerEntry 4 }

tmnxSysVsdServMsgSent         OBJECT-TYPE
     SYNTAX          Counter64
     MAX-ACCESS      read-only
     STATUS          current
     DESCRIPTION
         "The value of tmnxSysVsdServMsgSent indicates the number of 
          messages sent from the VSD server."
     ::= { tmnxSysVsdServerEntry 5 }
 
 tmnxSysVsdServMsgRcvd         OBJECT-TYPE
     SYNTAX          Counter64
     MAX-ACCESS      read-only
     STATUS          current
     DESCRIPTION
         "The value of tmnxSysVsdServMsgRcvd indicates the number of 
          messages received from the VSD server."
     ::= { tmnxSysVsdServerEntry 6 }
 
 tmnxSysVsdServMsgAckRcvd         OBJECT-TYPE
     SYNTAX          Counter64
     MAX-ACCESS      read-only
     STATUS          current
     DESCRIPTION
         "The value of tmnxSysVsdServMsgAckRcvd indicates the number of 
          message acknowledgements received from the VSD server."
     ::= { tmnxSysVsdServerEntry 7 }

 tmnxSysVsdServMsgError         OBJECT-TYPE
     SYNTAX          Counter64
     MAX-ACCESS      read-only
     STATUS          current
     DESCRIPTION
         "The value of tmnxSysVsdServMsgError indicates the number of 
          error messages received from the VSD server."
     ::= { tmnxSysVsdServerEntry 8 }
 
 tmnxSysVsdServMsgTimedOut         OBJECT-TYPE
     SYNTAX          Counter64
     MAX-ACCESS      read-only
     STATUS          current
     DESCRIPTION
         "The value of tmnxSysVsdServMsgTimedOut indicates the number of
           timeout messages received from the VSD server."
     ::= { tmnxSysVsdServerEntry 9 }
 
 tmnxSysVsdServMsgMinRtt         OBJECT-TYPE
     SYNTAX          Counter64
     UNITS           "milli-seconds"
     MAX-ACCESS      read-only
     STATUS          current
     DESCRIPTION
         "The value of tmnxSysVsdServMsgMinRtt indicates the minimum
           message round trip time from the VSD server."
     ::= { tmnxSysVsdServerEntry 10 }
 
 tmnxSysVsdServMsgMaxRtt         OBJECT-TYPE
     SYNTAX          Counter64
     UNITS           "milli-seconds"
     MAX-ACCESS      read-only
     STATUS          current
     DESCRIPTION
         "The value of tmnxSysVsdServMsgMaxRtt indicates the maximum
           message round trip time from the VSD server."
     ::= { tmnxSysVsdServerEntry 11 }

-- VSD system-id
tmnxSysVsdInfo         OBJECT IDENTIFIER ::= { tmnxSysObjs 29 }
tmnxSysVsdSystemId OBJECT-TYPE
    SYNTAX      TNamedItemOrEmpty
    MAX-ACCESS  read-write
    STATUS      current
    DESCRIPTION
        "The value of tmnxSysVsdSystemId specifies the name used by this system
         as its identity when communicating with VSD."
    DEFVAL { ''H }
    ::= { tmnxSysVsdInfo 1 }

tmnxSysVsdGwPubSubIsSubscrd OBJECT-TYPE
    SYNTAX      TruthValue
    MAX-ACCESS  read-only
    STATUS      current
    DESCRIPTION
        "The value of tmnxSysVsdGwPubSubIsSubscrd indicates whether the system
         is subscribed to the gateway publish-subscribe node."
    ::= { tmnxSysVsdInfo 2 }

tmnxSysVsdGwPubSubNodeName OBJECT-TYPE
    SYNTAX      DisplayString 
    MAX-ACCESS  read-only
    STATUS      current
    DESCRIPTION
        "The value of tmnxSysVsdGwPubSubNodeName indicates the gateway
         publish-subscribe node name assigned by VSD."
    ::= { tmnxSysVsdInfo 3 }

tmnxSysVsdGwPubSubLstSubscrdTime OBJECT-TYPE
    SYNTAX      TimeStamp
    MAX-ACCESS  read-only
    STATUS      current
    DESCRIPTION
        "The value of tmnxSysVsdGwPubSubLstSubscrdTime indicates the last
         subscription time to the gateway publish-subscribe node."
    ::= { tmnxSysVsdInfo 4 }

tmnxSysVsdGwLastAuditTxTime OBJECT-TYPE
    SYNTAX      TimeStamp
    MAX-ACCESS  read-only
    STATUS      current
    DESCRIPTION
        "The value of tmnxSysVsdGwLastAuditTxTime indicates the time last
         gateway audit was sent to the VSD."
    ::= { tmnxSysVsdInfo 5 }




tmnxSysGrpcInfo                  OBJECT IDENTIFIER ::= { tmnxSysObjs 39 }

tmnxSysGrpcAdminState            OBJECT-TYPE
    SYNTAX      TmnxAdminState
    MAX-ACCESS  read-write
    STATUS      current
    DESCRIPTION
        "The value of tmnxSysGrpcAdminState specifies the desired
         administrative state of the gRPC server."
    DEFVAL      { outOfService }
    ::= { tmnxSysGrpcInfo 1 }

tmnxSysGrpcOperState             OBJECT-TYPE
    SYNTAX      TmnxOperState
    MAX-ACCESS  read-only
    STATUS      current
    DESCRIPTION
        "The value of tmnxSysGrpcOperState indicates the current operational
         state of gRPC server."
    ::= { tmnxSysGrpcInfo 2 }

tmnxSysGrpcTlsServerProfile      OBJECT-TYPE
    SYNTAX      TNamedItemOrEmpty
    MAX-ACCESS  read-write
    STATUS      current
    DESCRIPTION
        "The value of tmnxSysGrpcTlsServerProfile specifies the name of the TLS
         server profile to be used."
    DEFVAL      { ''H }
    ::= { tmnxSysGrpcInfo 3 }

tmnxSysGrpcMaxMsgSize            OBJECT-TYPE
    SYNTAX      Unsigned32 (1..1024)
    UNITS       "megabytes"
    MAX-ACCESS  read-write
    STATUS      current
    DESCRIPTION
        "The value of tmnxSysGrpcMaxMsgSize specifies the maximum size of the
         received decompressed serialized protobuf message without metadata."
    DEFVAL      { 512 }
    ::= { tmnxSysGrpcInfo 4 }

--
--      System Resource Information
--

tmnxSysResInfo                          OBJECT IDENTIFIER ::= { tmnxSysObjs 27 }

tmnxSysResCardInfo                    OBJECT IDENTIFIER ::= { tmnxSysResInfo 1 }

tmnxCardCpuResMonitorTable     OBJECT-TYPE
    SYNTAX      SEQUENCE OF TmnxCardCpuResMonitorEntry
    MAX-ACCESS  not-accessible
    STATUS      current
    DESCRIPTION
        "The tmnxCardCpuResMonitorTable details the specified current card's
         CPU resources.

         The information described in this table is volatile and dependent on
         the current environmental conditions, and specified sample-time.
         Information is only displayed for online cards."
     ::= { tmnxSysResCardInfo 1 }

tmnxCardCpuResMonitorEntry     OBJECT-TYPE
    SYNTAX      TmnxCardCpuResMonitorEntry
    MAX-ACCESS  not-accessible
    STATUS      current
    DESCRIPTION
        "The tmnxCardCpuResMonitorEntry contains the card level CPU monitoring
         statistics over a specified sample-time."

    INDEX { tmnxChassisIndex,
            tmnxCardResourceSlotNum,
            tmnxCardCpuResSampleTime
          }
    ::= { tmnxCardCpuResMonitorTable 1 }

TmnxCardCpuResMonitorEntry       ::= SEQUENCE {
    tmnxCardResourceSlotNum          TmnxSlotNum,
    tmnxCardCpuResSampleTime         TmnxSysMonSampleTime,
    tmnxCardCpuResMonCpuIdle         TmnxSysMonUtilization,
    tmnxCardCpuResMonBusyCoreUtil    TmnxSysMonUtilization,
    tmnxCardCpuResMonBusyGroupName   OCTET STRING,
    tmnxCardCpuResMonBusyGroupUtil   TmnxSysMonUtilization
}

tmnxCardResourceSlotNum          OBJECT-TYPE
    SYNTAX      TmnxSlotNum
    MAX-ACCESS  not-accessible
    STATUS      current
    DESCRIPTION
        "The value of tmnxCardResourceSlotNum specifies the slot number of the
         card to which the resource information is monitored."
    ::= { tmnxCardCpuResMonitorEntry 1 }

tmnxCardCpuResSampleTime       OBJECT-TYPE
    SYNTAX      TmnxSysMonSampleTime
    MAX-ACCESS  not-accessible
    STATUS      current
    DESCRIPTION
        "The value of tmnxCardCpuResSampleTime specifies the sample-time used
         to calculate the utilization results for the row."
    ::= { tmnxCardCpuResMonitorEntry 2 }

tmnxCardCpuResMonCpuIdle            OBJECT-TYPE
    SYNTAX      TmnxSysMonUtilization
    MAX-ACCESS  read-only
    STATUS      current
    DESCRIPTION
        "The value of tmnxCardCpuResMonCpuIdle indicates the overall percentage
         of CPU idleness over the specified sample-time."
    ::= { tmnxCardCpuResMonitorEntry 3 }

tmnxCardCpuResMonBusyCoreUtil        OBJECT-TYPE
    SYNTAX      TmnxSysMonUtilization
    MAX-ACCESS  read-only
    STATUS      current
    DESCRIPTION
        "The value of tmnxCardCpuResMonBusyCoreUtil indicates the utilization
         percentage of the busiest processor core over the specified
         sample-time. On single core CPUs, this is the overall system
         utilization percentage over the specified sample-time."
    ::= { tmnxCardCpuResMonitorEntry 4 }

tmnxCardCpuResMonBusyGroupName       OBJECT-TYPE
    SYNTAX      OCTET STRING (SIZE (0..64))
    MAX-ACCESS  read-only
    STATUS      current
    DESCRIPTION
        "The value of tmnxCardCpuResMonBusyGroupName indicates the name of the
         group that is running at the highest capacity utilization.

         Capacity utilization is the CPU utilization relative to the maximum CPU
         resources available to that group.  A group is a set of related
         applications, services, tasks or protocol handlers that consumes some
         part of the system CPU resources.

         The capacity utilization of the busiest group is indicated by
         tmnxCardCpuResMonBusyGroupUtil."
    ::= { tmnxCardCpuResMonitorEntry 5 }

tmnxCardCpuResMonBusyGroupUtil       OBJECT-TYPE
    SYNTAX      TmnxSysMonUtilization
    MAX-ACCESS  read-only
    STATUS      current
    DESCRIPTION
        "The value of tmnxCardCpuResMonBusyGroupUtil indicates the capacity
         utilization of the group that is running at the highest capacity
         utilization.

         Capacity utilization is the CPU utilization relative to the maximum CPU
         resources available to that group.  A group is a set of related
         applications, services, tasks or protocol handlers that consumes some
         part of the system CPU resources.

         The name of the busiest group is indicated by
         tmnxCardCpuResMonBusyGroupName."
    ::= { tmnxCardCpuResMonitorEntry 6 }

--
--  Card Memory Resource Table
--
tmnxCardMemResMonitorTable     OBJECT-TYPE
    SYNTAX      SEQUENCE OF TmnxCardMemResMonitorEntry
    MAX-ACCESS  not-accessible
    STATUS      current
    DESCRIPTION
        "The tmnxCardMemResMonitorTable details the specified current card's
         memory resources.

         The information described in this table is volatile and dependent on
         the current environmental conditions. Information is only displayed 
         for online cards."
     ::= { tmnxSysResCardInfo 2 }

tmnxCardMemResMonitorEntry     OBJECT-TYPE
    SYNTAX      TmnxCardMemResMonitorEntry
    MAX-ACCESS  not-accessible
    STATUS      current
    DESCRIPTION
        "The tmnxCardMemResMonitorEntry contains the card's memory usage
         statistics."

    INDEX { tmnxChassisIndex,
            tmnxCardResourceSlotNum
          }
    ::= { tmnxCardMemResMonitorTable 1 }

TmnxCardMemResMonitorEntry        ::= SEQUENCE {
    tmnxCardMemResMemoryUsed          Gauge32,
    tmnxCardMemResMemoryAvailable     Gauge32,
    tmnxCardMemResPoolsAllocated      Gauge32
}

tmnxCardMemResMemoryUsed         OBJECT-TYPE
    SYNTAX      Gauge32
    UNITS       "kilobytes"
    MAX-ACCESS  read-only
    STATUS      current
    DESCRIPTION
        "The value of tmnxCardMemResMemoryUsed indicates the total pre-allocated
        pool memory, in kilobytes, currently in use on the card."
    ::= { tmnxCardMemResMonitorEntry 1 }

tmnxCardMemResMemoryAvailable     OBJECT-TYPE
    SYNTAX      Gauge32 
    UNITS       "kilobytes"
    MAX-ACCESS  read-only
    STATUS      current
    DESCRIPTION
        "The value of tmnxCardMemResMemoryAvailable indicates the amount of free
        memory, in kilobytes, in the card that is not allocated to memory pools,
        but is available in case a memory pool needs to grow."
    ::= { tmnxCardMemResMonitorEntry 2 }

tmnxCardMemResPoolsAllocated      OBJECT-TYPE
    SYNTAX      Gauge32
    UNITS       "kilobytes"
    MAX-ACCESS  read-only
    STATUS      current
    DESCRIPTION
        "The value of tmnxCardMemResPoolsAllocated indicates the total memory,
        in kilobytes, currently allocated in memory-pools on the card.

        This memory may or may not be currently in use, but is pre-allocated
        should the software need to use it."
    ::= { tmnxCardMemResMonitorEntry 3 }

--
--      System Resource Information
--

tmnxSysDhcp                          OBJECT IDENTIFIER ::= { tmnxSysObjs 28 }

tmnxSysDhcp6AdvNoaddrsGlobal  OBJECT-TYPE
    SYNTAX      BITS {
                    esmProxy    (0),
                    esmRelay    (1),
                    relay       (2),
                    server      (3)
                }
    MAX-ACCESS  read-write
    STATUS      current
    DESCRIPTION
        "The value of tmnxSysDhcp6AdvNoaddrsGlobal specifies
         the composition of DHCPv6 Advertise Messages in case a DHCP6 application in this system 
         will not assign any addresses to any Identity Association (IA) in a subsequent Request
         from the client.
         
         DHCP6 applications in this system are Relay, Server, Enhanced Subscriber Management (ESM) Proxy and ESM Relay.
         
         By default, a DHCP6 application in this system will send an Advertise message to the client
         that includes the IA containing a Status Code option with status code 'NoAddrsAvail', as specified
         in Errata 2472.
         
         If the bit corresponding to a DHCP6 application is set, that application will send an Advertise message 
         to the client that includes only a Status Code option with code 'NoAddrsAvail'.
         
         This system will refuse bit combinations that are not supported:
         the 'esmRelay' and 'server' bits must be toggled together, and
         the 'esmProxy' and 'relay' bits are read-only."
    REFERENCE
       "RFC3315 Dynamic Host Configuration Protocol for IPv6 (DHCPv6)
       section 17.2.2 Creation and Transmission of Advertise Messages
       
       RFC3315 errata 2472 (section 17.2)"
    DEFVAL { { } }
        ::= { tmnxSysDhcp 1 }

--
--  License information
--
tmnxSysLicense                   OBJECT IDENTIFIER ::= { tmnxSysObjs 30 }

tmnxSysLicenseStatus             OBJECT-TYPE
    SYNTAX      TItemDescription
    MAX-ACCESS  read-only
    STATUS      current
    DESCRIPTION
        "The value of tmnxSysLicenseStatus indicates the current status of the
         license."
    ::= { tmnxSysLicense 1 }

tmnxSysLicenseName               OBJECT-TYPE
    SYNTAX      TItemDescription
    MAX-ACCESS  read-only
    STATUS      current
    DESCRIPTION
        "The value of tmnxSysLicenseName indicates the license name."
    ::= { tmnxSysLicense 2 }

tmnxSysLicenseUuid               OBJECT-TYPE
    SYNTAX      TmnxUuid
    MAX-ACCESS  read-only
    STATUS      current
    DESCRIPTION
        "The value of tmnxSysLicenseUuid indicates the Universally Unique
         Identifier (UUID) for the license of the virtual machine (VM)."
    ::= { tmnxSysLicense 3 }

tmnxSysLicenseDescription        OBJECT-TYPE
    SYNTAX      TItemDescription
    MAX-ACCESS  read-only
    STATUS      current
    DESCRIPTION
        "The value of tmnxSysLicenseDescription indicates the license
         description."
    ::= { tmnxSysLicense 4 }

tmnxSysLicenseProduct            OBJECT-TYPE
    SYNTAX      TItemDescription
    MAX-ACCESS  read-only
    STATUS      current
    DESCRIPTION
        "The value of tmnxSysLicenseProduct indicates the product for which
         the license is valid."
    ::= { tmnxSysLicense 5 }

tmnxSysLicenseSwVersion          OBJECT-TYPE
    SYNTAX      TItemDescription
    MAX-ACCESS  read-only
    STATUS      current
    DESCRIPTION
        "The value of tmnxSysLicenseSwVersion indicates the SROS series system
         software version for which the license is valid."
    ::= { tmnxSysLicense 6 }

tmnxSysLicenseIssueDateAndTime   OBJECT-TYPE
    SYNTAX      DateAndTime
    MAX-ACCESS  read-only
    STATUS      current
    DESCRIPTION
        "The value of tmnxSysLicenseIssueDateAndTime indicates the day and time
         the license was issued."
    ::= { tmnxSysLicense 7 }

tmnxSysLicenseStartDateAndTime   OBJECT-TYPE
    SYNTAX      DateAndTime
    MAX-ACCESS  read-only
    STATUS      current
    DESCRIPTION
        "The value of tmnxSysLicenseStartDateAndTime indicates the day and time
         the license became active."
    ::= { tmnxSysLicense 8 }

tmnxSysLicenseEndDateAndTime     OBJECT-TYPE
    SYNTAX      DateAndTime
    MAX-ACCESS  read-only
    STATUS      current
    DESCRIPTION
        "The value of tmnxSysLicenseEndDateAndTime indicates the day and time
         the license expires."
    ::= { tmnxSysLicense 9 }

tmnxSysLicenseVChassisType       OBJECT-TYPE
    SYNTAX      TNamedItemOrEmpty
    MAX-ACCESS  read-only
    STATUS      current
    DESCRIPTION
        "The value of tmnxSysLicenseVChassisType indicates the virtual chassis
         type for which the license is valid.

         A value of empty string indicates that the license is not associated
         with a virtual chassis."
    ::= { tmnxSysLicense 10 }

tmnxSysLicenseMaxNumCPMs         OBJECT-TYPE
    SYNTAX      Unsigned32
    MAX-ACCESS  read-only
    STATUS      current
    DESCRIPTION
        "The value of tmnxSysLicenseMaxNumCPMs indicates the maximum number of
         CPMs allowed by the license.

         A value of 0 indicates that the number of CPMs is not restricted by
         the license."
    ::= { tmnxSysLicense 11 }

tmnxSysLicenseMaxNumIOMs         OBJECT-TYPE
    SYNTAX      Unsigned32
    MAX-ACCESS  read-only
    STATUS      current
    DESCRIPTION
        "The value of tmnxSysLicenseMaxNumIOMs indicates the maximum number of
         IOMs allowed by the license.

         A value of 0 indicates that the number of IOMs is not restricted by
         the license."
    ::= { tmnxSysLicense 12 }

tmnxSysCpmCardLicenseTable       OBJECT-TYPE
    SYNTAX      SEQUENCE OF TmnxSysCpmCardLicenseEntry
    MAX-ACCESS  not-accessible
    STATUS      current
    DESCRIPTION
        "The tmnxSysCpmCardLicenseTable has an entry for each CPM card in
         the first chassis in the system."
    ::= { tmnxSysLicense 13 }

tmnxSysCpmCardLicenseEntry       OBJECT-TYPE
    SYNTAX      TmnxSysCpmCardLicenseEntry
    MAX-ACCESS  not-accessible
    STATUS      current
    DESCRIPTION
        "Each row represents a CPM card in the first chassis in the system.
         When a tmnxChassisEntry is created, a tmnxSysCpmCardLicenseEntry is
         created for each CPM card in the first chassis. Entries cannot be
         created or deleted via SNMP SET operations."
    INDEX { tmnxChassisIndex,
            tmnxCpmCardSlotNum,
            tmnxCpmCardNum }
    ::= { tmnxSysCpmCardLicenseTable 1 }

TmnxSysCpmCardLicenseEntry ::=
    SEQUENCE {
        tmnxSysCpmCardLicStatus         TItemDescription,
        tmnxSysCpmCardLicName           TItemDescription,
        tmnxSysCpmCardLicUuid           TmnxUuid,
        tmnxSysCpmCardLicDescription    TItemDescription,
        tmnxSysCpmCardLicProduct        TItemDescription,
        tmnxSysCpmCardLicSwVersion      TItemDescription,
        tmnxSysCpmCardLicIssueDateTime  DateAndTime,
        tmnxSysCpmCardLicStartDateTime  DateAndTime,
        tmnxSysCpmCardLicEndDateTime    DateAndTime,
        tmnxSysCpmCardLicVChassisType   TNamedItemOrEmpty,
        tmnxSysCpmCardLicMaxNumCPMs     Unsigned32,
        tmnxSysCpmCardLicMaxNumIOMs     Unsigned32
    }

tmnxSysCpmCardLicStatus          OBJECT-TYPE
    SYNTAX      TItemDescription
    MAX-ACCESS  read-only
    STATUS      current
    DESCRIPTION
        "The value of tmnxSysCpmCardLicStatus indicates the current status of
         the license."
    ::= { tmnxSysCpmCardLicenseEntry 1 }

tmnxSysCpmCardLicName            OBJECT-TYPE
    SYNTAX      TItemDescription
    MAX-ACCESS  read-only
    STATUS      current
    DESCRIPTION
        "The value of tmnxSysCpmCardLicName indicates the license name."
    ::= { tmnxSysCpmCardLicenseEntry 2 }

tmnxSysCpmCardLicUuid            OBJECT-TYPE
    SYNTAX      TmnxUuid
    MAX-ACCESS  read-only
    STATUS      current
    DESCRIPTION
        "The value of tmnxSysCpmCardLicUuid indicates the Universally Unique
         Identifier (UUID) for the license of the CPM card in the virtual
         machine (VM)."
    ::= { tmnxSysCpmCardLicenseEntry 3 }

tmnxSysCpmCardLicDescription     OBJECT-TYPE
    SYNTAX      TItemDescription
    MAX-ACCESS  read-only
    STATUS      current
    DESCRIPTION
        "The value of tmnxSysCpmCardLicDescription indicates the license
         description."
    ::= { tmnxSysCpmCardLicenseEntry 4 }

tmnxSysCpmCardLicProduct         OBJECT-TYPE
    SYNTAX      TItemDescription
    MAX-ACCESS  read-only
    STATUS      current
    DESCRIPTION
        "The value of tmnxSysCpmCardLicProduct indicates the product for
         which the license is valid."
    ::= { tmnxSysCpmCardLicenseEntry 5 }

tmnxSysCpmCardLicSwVersion       OBJECT-TYPE
    SYNTAX      TItemDescription
    MAX-ACCESS  read-only
    STATUS      current
    DESCRIPTION
        "The value of tmnxSysCpmCardLicSwVersion indicates the SROS series
         system software version for which the license is valid."
    ::= { tmnxSysCpmCardLicenseEntry 6 }

tmnxSysCpmCardLicIssueDateTime   OBJECT-TYPE
    SYNTAX      DateAndTime
    MAX-ACCESS  read-only
    STATUS      current
    DESCRIPTION
        "The value of tmnxSysCpmCardLicIssueDateTime indicates the day and
         time the license was issued."
    ::= { tmnxSysCpmCardLicenseEntry 7 }

tmnxSysCpmCardLicStartDateTime   OBJECT-TYPE
    SYNTAX      DateAndTime
    MAX-ACCESS  read-only
    STATUS      current
    DESCRIPTION
        "The value of tmnxSysCpmCardLicStartDateTime indicates the day and
         time the license became active."
    ::= { tmnxSysCpmCardLicenseEntry 8 }

tmnxSysCpmCardLicEndDateTime     OBJECT-TYPE
    SYNTAX      DateAndTime
    MAX-ACCESS  read-only
    STATUS      current
    DESCRIPTION
        "The value of tmnxSysCpmCardLicEndDateTime indicates the day and
         time the license expires."
    ::= { tmnxSysCpmCardLicenseEntry 9 }

tmnxSysCpmCardLicVChassisType    OBJECT-TYPE
    SYNTAX      TNamedItemOrEmpty
    MAX-ACCESS  read-only
    STATUS      current
    DESCRIPTION
        "The value of tmnxSysCpmCardLicVChassisType indicates the virtual
         chassis type for which the license is valid.

         A value of empty string indicates that the license is not associated
         with a virtual chassis."
    ::= { tmnxSysCpmCardLicenseEntry 10 }

tmnxSysCpmCardLicMaxNumCPMs      OBJECT-TYPE
    SYNTAX      Unsigned32
    MAX-ACCESS  read-only
    STATUS      current
    DESCRIPTION
        "The value of tmnxSysCpmCardLicMaxNumCPMs indicates the maximum number
         of CPMs allowed by the license.

         A value of 0 indicates that the number of CPMs is not restricted by
         the license."
    ::= { tmnxSysCpmCardLicenseEntry 11 }

tmnxSysCpmCardLicMaxNumIOMs      OBJECT-TYPE
    SYNTAX      Unsigned32
    MAX-ACCESS  read-only
    STATUS      current
    DESCRIPTION
        "The value of tmnxSysCpmCardLicMaxNumIOMs indicates the maximum number
         of IOMs allowed by the license.

         A value of 0 indicates that the number of IOMs is not restricted by
         the license."
    ::= { tmnxSysCpmCardLicenseEntry 12 }

tmnxSysCpmCardLicFeatureTable    OBJECT-TYPE
    SYNTAX      SEQUENCE OF TmnxSysCpmCardLicFeatureEntry
    MAX-ACCESS  not-accessible
    STATUS      current
    DESCRIPTION
        "The tmnxSysCpmCardLicFeatureTable has an entry for each feature
         supported by the license installed on a CPM card in the chassis with
         TIMETRA-CHASSIS-MIB::tmnxPhysChassisClass 'routerChassis(3)' and
         TIMETRA-CHASSIS-MIB::tmnxPhysChassisNum '1'."
    ::= { tmnxSysLicense 14 }

tmnxSysCpmCardLicFeatureEntry    OBJECT-TYPE
    SYNTAX      TmnxSysCpmCardLicFeatureEntry
    MAX-ACCESS  not-accessible
    STATUS      current
    DESCRIPTION
        "When a TIMETRA-CHASSIS-MIB::tmnxCpmCardEntry is created for a CPM card
         in the chassis with TIMETRA-CHASSIS-MIB::tmnxPhysChassisClass
         'routerChassis(3)' and TIMETRA-CHASSIS-MIB::tmnxPhysChassisNum '1', a
         tmnxSysCpmCardLicFeatureEntry is created for each
         feature supported by the license installed on that CPM card.

         Entries cannot be created or deleted via SNMP SET operations."
    INDEX { tmnxChassisIndex,
            tmnxCpmCardSlotNum,
            tmnxCpmCardNum,
            tmnxSysCpmCardLicFeatApplication,
            tmnxSysCpmCardLicFeatNumber }
    ::= { tmnxSysCpmCardLicFeatureTable 1 }

TmnxSysCpmCardLicFeatureEntry ::=
    SEQUENCE {
        tmnxSysCpmCardLicFeatApplication  TNamedItem,
        tmnxSysCpmCardLicFeatNumber       Unsigned32,
        tmnxSysCpmCardLicFeatDescription  TItemDescription
    }

tmnxSysCpmCardLicFeatApplication OBJECT-TYPE
    SYNTAX      TNamedItem
    MAX-ACCESS  not-accessible
    STATUS      current
    DESCRIPTION
        "The value of tmnxSysCpmCardLicFeatApplication specifies the
         application supported by the license."
    ::= { tmnxSysCpmCardLicFeatureEntry 1 }

tmnxSysCpmCardLicFeatNumber      OBJECT-TYPE
    SYNTAX      Unsigned32 (1..4294967295)
    MAX-ACCESS  not-accessible
    STATUS      current
    DESCRIPTION
        "The value of tmnxSysCpmCardLicFeatNumber specifies the feature
         number associated with the feature supported by the license."
    ::= { tmnxSysCpmCardLicFeatureEntry 2 }

tmnxSysCpmCardLicFeatDescription OBJECT-TYPE
    SYNTAX      TItemDescription
    MAX-ACCESS  read-only
    STATUS      current
    DESCRIPTION
        "The value of tmnxSysCpmCardLicFeatDescription indicates the
         description of the feature supported by the license."
    ::= { tmnxSysCpmCardLicFeatureEntry 3 }


tmnxSysLicenseStatistics  OBJECT IDENTIFIER ::= { tmnxSysLicense 20 }

--
--  License related statistics for virtual machine applications
--  collected the last 24 hours
--
tmnxSysAppStats24HrsTable    OBJECT-TYPE
    SYNTAX      SEQUENCE OF TmnxSysAppStats24HrsEntry
    MAX-ACCESS  not-accessible
    STATUS      current
    DESCRIPTION
        "The tmnxSysAppStats24HrsTable contains statistics about
         a virtual machine application
         collected periodically during the last 24 hours.
         
         These statistics are not used for license validation. They
         are informational only."
    ::= { tmnxSysLicenseStatistics 1 }

tmnxSysAppStats24HrsEntry    OBJECT-TYPE
    SYNTAX      TmnxSysAppStats24HrsEntry
    MAX-ACCESS  not-accessible
    STATUS      current
    DESCRIPTION
        "Each conceptual row contains a specific instance of a statistics value
         at a specific time."
    INDEX { tmnxSysAppStats24HrsApplication,
            tmnxSysAppStats24HrsType,
            tmnxSysAppStats24HrsIndex }
    ::= { tmnxSysAppStats24HrsTable 1 }

TmnxSysAppStats24HrsEntry ::=
    SEQUENCE {
        tmnxSysAppStats24HrsApplication  TmnxSysLicenseApplication,
        tmnxSysAppStats24HrsType         TmnxSysLicenseAppStatsType,
        tmnxSysAppStats24HrsIndex        Unsigned32,
        tmnxSysAppStats24HrsName         DisplayString,
        tmnxSysAppStats24HrsValue        CounterBasedGauge64,
        tmnxSysAppStats24HrsTime         DateAndTime
    }

tmnxSysAppStats24HrsApplication OBJECT-TYPE
    SYNTAX      TmnxSysLicenseApplication
    MAX-ACCESS  not-accessible
    STATUS      current
    DESCRIPTION
        "The value of tmnxSysAppStats24HrsApplication indicates
         the application."
    ::= { tmnxSysAppStats24HrsEntry 1 }
    
tmnxSysAppStats24HrsType OBJECT-TYPE
    SYNTAX      TmnxSysLicenseAppStatsType
    MAX-ACCESS  not-accessible
    STATUS      current
    DESCRIPTION
        "The value of tmnxSysAppStats24HrsType
         indicates the meaning of the statistics in this conceptual row."
    ::= { tmnxSysAppStats24HrsEntry 2 }
    
tmnxSysAppStats24HrsIndex OBJECT-TYPE
    SYNTAX      Unsigned32
    MAX-ACCESS  not-accessible
    STATUS      current
    DESCRIPTION
        "The value of tmnxSysAppStats24HrsIndex is a numerical
         index value generated by this system."
    ::= { tmnxSysAppStats24HrsEntry 3 }
    
tmnxSysAppStats24HrsName OBJECT-TYPE
    SYNTAX      DisplayString (SIZE (1..64))
    MAX-ACCESS  read-only
    STATUS      current
    DESCRIPTION 
       "The value of the object tmnxSysAppStats24HrsName indicates
        the human-readable identifier of the statistics 
        contained in this conceptual row."
    ::= { tmnxSysAppStats24HrsEntry 4 }

tmnxSysAppStats24HrsValue OBJECT-TYPE
    SYNTAX      CounterBasedGauge64
    MAX-ACCESS  read-only
    STATUS      current
    DESCRIPTION 
       "The value of the object tmnxSysAppStats24HrsValue indicates
        the value of the statistics contained in this conceptual row."
    ::= { tmnxSysAppStats24HrsEntry 5 }

tmnxSysAppStats24HrsTime OBJECT-TYPE
    SYNTAX      DateAndTime (SIZE(11))
    MAX-ACCESS  read-only
    STATUS      current
    DESCRIPTION 
       "The value of the object tmnxSysAppStats24HrsTime indicates
        the time the system measured the value of tmnxSysAppStats24HrsValue."
    ::= { tmnxSysAppStats24HrsEntry 6 }

--
--  License related statistics for a virtual machine application
--  collected the last week
--
tmnxSysAppStatsWeekTable    OBJECT-TYPE
    SYNTAX      SEQUENCE OF TmnxSysAppStatsWeekEntry
    MAX-ACCESS  not-accessible
    STATUS      current
    DESCRIPTION
        "The tmnxSysAppStatsWeekTable contains statistics about
         a virtual machine application
         collected periodically during the last week.
         
         These statistics are used for license validation."
    ::= { tmnxSysLicenseStatistics 2 }

tmnxSysAppStatsWeekEntry    OBJECT-TYPE
    SYNTAX      TmnxSysAppStatsWeekEntry
    MAX-ACCESS  not-accessible
    STATUS      current
    DESCRIPTION
        "Each conceptual row contains a specific instance of a statistics
         value associated with a specific 24 hours period."
    INDEX { tmnxSysAppStatsWeekApplication,
            tmnxSysAppStatsWeekType,
            tmnxSysAppStatsWeekIndex }
    ::= { tmnxSysAppStatsWeekTable 1 }

TmnxSysAppStatsWeekEntry ::=
    SEQUENCE {
        tmnxSysAppStatsWeekApplication  TmnxSysLicenseApplication,
        tmnxSysAppStatsWeekType         TmnxSysLicenseAppStatsType,
        tmnxSysAppStatsWeekIndex        Unsigned32,
        tmnxSysAppStatsWeekName         DisplayString,
        tmnxSysAppStatsWeekAverage      CounterBasedGauge64,
        tmnxSysAppStatsWeekPeak         CounterBasedGauge64,
        tmnxSysAppStatsWeekTime         DateAndTime
    }

tmnxSysAppStatsWeekApplication OBJECT-TYPE
    SYNTAX      TmnxSysLicenseApplication
    MAX-ACCESS  not-accessible
    STATUS      current
    DESCRIPTION
        "The value of tmnxSysAppStatsWeekApplication indicates
         the application."
    ::= { tmnxSysAppStatsWeekEntry 1 }
    
tmnxSysAppStatsWeekType OBJECT-TYPE
    SYNTAX      TmnxSysLicenseAppStatsType
    MAX-ACCESS  not-accessible
    STATUS      current
    DESCRIPTION
        "The value of tmnxSysAppStatsWeekType
         indicates the meaning of the statistics in this conceptual row."
    ::= { tmnxSysAppStatsWeekEntry 2 }
    
tmnxSysAppStatsWeekIndex OBJECT-TYPE
    SYNTAX      Unsigned32
    MAX-ACCESS  not-accessible
    STATUS      current
    DESCRIPTION
        "The value of tmnxSysAppStatsWeekIndex is a numerical
         index value generated by this system."
    ::= { tmnxSysAppStatsWeekEntry 3 }
    
tmnxSysAppStatsWeekName OBJECT-TYPE
    SYNTAX      DisplayString (SIZE (1..64))
    MAX-ACCESS  read-only
    STATUS      current
    DESCRIPTION 
       "The value of the object tmnxSysAppStatsWeekName indicates
        the human-readable identifier of the statistics 
        contained in this conceptual row."
    ::= { tmnxSysAppStatsWeekEntry 4 }

tmnxSysAppStatsWeekAverage OBJECT-TYPE
    SYNTAX      CounterBasedGauge64
    MAX-ACCESS  read-only
    STATUS      current
    DESCRIPTION 
       "The value of the object tmnxSysAppStatsWeekAverage indicates
        the average value of the statistics contained in this conceptual row
        for this period of 24 hours."
    ::= { tmnxSysAppStatsWeekEntry 5 }

tmnxSysAppStatsWeekPeak OBJECT-TYPE
    SYNTAX      CounterBasedGauge64
    MAX-ACCESS  read-only
    STATUS      current
    DESCRIPTION 
       "The value of the object tmnxSysAppStatsWeekPeak indicates
        the peak value of the statistics contained in this conceptual row
        for this period of 24 hours."
    ::= { tmnxSysAppStatsWeekEntry 6 }

tmnxSysAppStatsWeekTime OBJECT-TYPE
    SYNTAX      DateAndTime (SIZE(11))
    MAX-ACCESS  read-only
    STATUS      current
    DESCRIPTION 
       "The value of the object tmnxSysAppStatsWeekTime indicates
        the time the system determined the values of tmnxSysAppStatsWeekAverage
        and tmnxSysAppStatsWeekPeak."
    ::= { tmnxSysAppStatsWeekEntry 7 }

--
--  Peak values of license related statistics for virtual machine applications
--
tmnxSysAppStatsPeakTable    OBJECT-TYPE
    SYNTAX      SEQUENCE OF TmnxSysAppStatsPeakEntry
    MAX-ACCESS  not-accessible
    STATUS      current
    DESCRIPTION
        "The tmnxSysAppStatsPeakTable contains peak values
         of statistics about a virtual machine application."
    ::= { tmnxSysLicenseStatistics 3 }

tmnxSysAppStatsPeakEntry    OBJECT-TYPE
    SYNTAX      TmnxSysAppStatsPeakEntry
    MAX-ACCESS  not-accessible
    STATUS      current
    DESCRIPTION
        "Each conceptual row contains a peak value
         of a statistic about a virtual machine application."
    INDEX { tmnxSysAppStatsPeakApplication,
            tmnxSysAppStatsPeakType }
    ::= { tmnxSysAppStatsPeakTable 1 }

TmnxSysAppStatsPeakEntry ::=
    SEQUENCE {
        tmnxSysAppStatsPeakApplication   TmnxSysLicenseApplication,
        tmnxSysAppStatsPeakType          TmnxSysLicenseAppStatsType,
        tmnxSysAppStatsPeakName          DisplayString,
        tmnxSysAppStatsPeakValue         CounterBasedGauge64,
        tmnxSysAppStatsPeakTime          DateAndTime
    }

tmnxSysAppStatsPeakApplication OBJECT-TYPE
    SYNTAX      TmnxSysLicenseApplication
    MAX-ACCESS  not-accessible
    STATUS      current
    DESCRIPTION
        "The value of tmnxSysAppStatsPeakApplication indicates
         the application."
    ::= { tmnxSysAppStatsPeakEntry 1 }
    
tmnxSysAppStatsPeakType OBJECT-TYPE
    SYNTAX      TmnxSysLicenseAppStatsType
    MAX-ACCESS  not-accessible
    STATUS      current
    DESCRIPTION
        "The value of tmnxSysAppStatsPeakType
         indicates the meaning of the statistics in this conceptual row."
    ::= { tmnxSysAppStatsPeakEntry 2 }
    
tmnxSysAppStatsPeakName OBJECT-TYPE
    SYNTAX      DisplayString (SIZE (1..64))
    MAX-ACCESS  read-only
    STATUS      current
    DESCRIPTION 
       "The value of the object tmnxSysAppStatsPeakName indicates
        the human-readable identifier of the statistics 
        contained in this conceptual row."
    ::= { tmnxSysAppStatsPeakEntry 3 }

tmnxSysAppStatsPeakValue OBJECT-TYPE
    SYNTAX      CounterBasedGauge64
    MAX-ACCESS  read-only
    STATUS      current
    DESCRIPTION 
       "The value of the object tmnxSysAppStatsPeakValue indicates
        the value of the statistics contained in this conceptual row."
    ::= { tmnxSysAppStatsPeakEntry 4 }

tmnxSysAppStatsPeakTime OBJECT-TYPE
    SYNTAX      DateAndTime (SIZE(11))
    MAX-ACCESS  read-only
    STATUS      current
    DESCRIPTION 
       "The value of the object tmnxSysAppStatsPeakTime indicates
        the time the system measured the value of tmnxSysAppStatsPeakValue."
    ::= { tmnxSysAppStatsPeakEntry 5 }

tmnxSysFibInfo     OBJECT IDENTIFIER ::= { tmnxSysObjs 31 }

tmnxSysFibSelective     OBJECT-TYPE
    SYNTAX      TruthValue
    MAX-ACCESS  read-write
    STATUS      current
    DESCRIPTION
        "The value of tmnxSysFibSelective specifies whether
         selective FIB is enabled in the system.
         
         If the value of tmnxSysFibSelective is set to false, then 
         all active routes are installed on all line cards.
         
         If the value of tmnxSysFibSelective is set to true, then
         a line card installs a particular IP route only if that route
         is relevant to the card based on the current configuration of
         interfaces and services."
    DEFVAL      { false }
    ::= { tmnxSysFibInfo 1 }
 
tmnxSysSnmpSrcAccessObjs    OBJECT IDENTIFIER ::= { tmnxSysObjs 32 }
  tmnxSysSnmpConfigObjs    OBJECT IDENTIFIER ::= { tmnxSysSnmpSrcAccessObjs 1 }
  tmnxSysSnmpStatsObjs    OBJECT IDENTIFIER ::= { tmnxSysSnmpSrcAccessObjs 2 }

-- ------------------------
--  tmnxSysSnmpSrcAccessTable
-- ------------------------

tmnxSysSnmpSrcAccessTblLstChgd  OBJECT-TYPE
    SYNTAX      TimeStamp
    MAX-ACCESS  read-only
    STATUS      current
    DESCRIPTION
        "The value of tmnxSysSnmpSrcAccessTblLstChgd indicates the sysUpTime at 
         the time of the last modification to tmnxSysSnmpSrcAccessLstTable by 
         adding, deleting an entry or change to a writable object in the table.

         If no changes were made to the table since the last re-initialization 
         of the local network management subsystem, then this object contains a
         zero value."
    ::= { tmnxSysSnmpConfigObjs 1 }

tmnxSysSnmpSrcAccessLstTable   OBJECT-TYPE
    SYNTAX      SEQUENCE OF TmnxSysSnmpSrcAccessLstEntry
    MAX-ACCESS  not-accessible
    STATUS      current
    DESCRIPTION
        "The tmnxSysSnmpSrcAccessLstTable contains objects for creating entries
         corresponding to source access list."
    ::= { tmnxSysSnmpConfigObjs 2 }

tmnxSysSnmpSrcAccessLstEntry   OBJECT-TYPE
    SYNTAX      TmnxSysSnmpSrcAccessLstEntry
    MAX-ACCESS  not-accessible
    STATUS      current
    DESCRIPTION
        "The tmnxSysSnmpSrcAccessLstEntry contains configuration items for 
         creating src-access-list."
    INDEX { IMPLIED tmnxSysSnmpSrcAccessLstName }
    ::= { tmnxSysSnmpSrcAccessLstTable 1 }

TmnxSysSnmpSrcAccessLstEntry ::=
    SEQUENCE {
        tmnxSysSnmpSrcAccessLstName        TNamedItem,
        tmnxSysSnmpSrcAccessLstRowStatus   RowStatus,
        tmnxSysSnmpSrcAccessLstLastChg     TimeStamp
    }

tmnxSysSnmpSrcAccessLstName OBJECT-TYPE
    SYNTAX      TNamedItem
    MAX-ACCESS  not-accessible
    STATUS      current
    DESCRIPTION
        "The value of tmnxSysSnmpSrcAccessLstName specifies the name given to 
         this src-access-list."
    ::= { tmnxSysSnmpSrcAccessLstEntry 1 }

tmnxSysSnmpSrcAccessLstRowStatus    OBJECT-TYPE
    SYNTAX      RowStatus
    MAX-ACCESS  read-create
    STATUS      current
    DESCRIPTION
        "The value of tmnxSysSnmpSrcAccessLstRowStatus specifies the row status
         used for creation and deletion of src-access-list entries."
    ::= { tmnxSysSnmpSrcAccessLstEntry 2 }

tmnxSysSnmpSrcAccessLstLastChg  OBJECT-TYPE
    SYNTAX      TimeStamp
    MAX-ACCESS  read-only
    STATUS      current
    DESCRIPTION
        "The value of tmnxSysSnmpSrcAccessLstLastChg indicates the sysUpTime at
         the time of the last modification of this row.

         If no changes were made to the row since the last re-initialization of
         the local network management subsystem, then this object contains the
         value zero."
    ::= { tmnxSysSnmpSrcAccessLstEntry 3 }

-- ------------------------------------------------
--  tmnxSysSnmpCommunityStatsTable
-- ------------------------------------------------

tmnxSysSnmpCommunityStatsTable  OBJECT-TYPE
    SYNTAX      SEQUENCE OF TmnxSysSnmpCommunityStatsEntry
    MAX-ACCESS  not-accessible
    STATUS      current
    DESCRIPTION
        "The tmnxSysSnmpCommunityStatsTable contains statistics for SNMP 
         Community."
    ::= { tmnxSysSnmpStatsObjs 1 }

tmnxSysSnmpCommunityStatsEntry  OBJECT-TYPE
    SYNTAX      TmnxSysSnmpCommunityStatsEntry
    MAX-ACCESS  not-accessible
    STATUS      current
    DESCRIPTION
        "Each row entry represents a collection of statistics for each SNMP
         Community within a virtual router.
         
         Entries cannot be created and deleted via SNMP SET operations."
    AUGMENTS { snmpCommunityEntry }
    ::= { tmnxSysSnmpCommunityStatsTable 1 }

TmnxSysSnmpCommunityStatsEntry  ::= SEQUENCE {
        tmnxSysSnmpCommunityPktDropped  Gauge32
    }

tmnxSysSnmpCommunityPktDropped  OBJECT-TYPE
    SYNTAX      Gauge32
    MAX-ACCESS  read-only
    STATUS      current
    DESCRIPTION
        "The value of tmnxSysSnmpCommunityPktDropped indicates the total number
         of packets dropped when a SNMP GET request has been made."
    ::= { tmnxSysSnmpCommunityStatsEntry 1 }
 
tmnxSysMgmtProtocolObjs    OBJECT IDENTIFIER ::= { tmnxSysObjs 33 }

-- ------------------------
--  tmnxSysMgmtProtocol
-- ------------------------

tmnxSysMgmtProtocolTblLstChng  OBJECT-TYPE
    SYNTAX      TimeStamp
    MAX-ACCESS  read-only
    STATUS      current
    DESCRIPTION
        "The value of tmnxSysMgmtProtocolTblLstChng indicates the sysUpTime at 
         the time of the last modification to tmnxSysMgmtProtocolTable by 
         change to a writable object in the table.

         If no changes were made to the table since the last re-initialization 
         of the local network management subsystem, then this object contains a
         zero value."
    ::= { tmnxSysMgmtProtocolObjs 1 }

tmnxSysMgmtProtocolTable   OBJECT-TYPE
    SYNTAX      SEQUENCE OF TmnxSysMgmtProtocolEntry
    MAX-ACCESS  not-accessible
    STATUS      current
    DESCRIPTION
        "The tmnxSysMgmtProtocolTable contains objects for managing the
         capabilities of the different network management protocols."
    ::= { tmnxSysMgmtProtocolObjs 2 }

tmnxSysMgmtProtocolEntry   OBJECT-TYPE
    SYNTAX      TmnxSysMgmtProtocolEntry
    MAX-ACCESS  not-accessible
    STATUS      current
    DESCRIPTION
        "The tmnxSysMgmtProtocolEntry contains configuration items for 
         managing the different network management protocols.

         Entries in this table cannot be created or deleted."
    INDEX { tmnxSysMgmtProtocol }
    ::= { tmnxSysMgmtProtocolTable 1 }

TmnxSysMgmtProtocolEntry ::=
    SEQUENCE {
        tmnxSysMgmtProtocol             INTEGER,
        tmnxSysMgmtProtLastChange       TimeStamp,
        tmnxSysMgmtAllowImmediateChange TruthValue
    }

tmnxSysMgmtProtocol OBJECT-TYPE
    SYNTAX      INTEGER {
                    cli (0)
                }
    MAX-ACCESS  not-accessible
    STATUS      current
    DESCRIPTION
        "The value of tmnxSysMgmtProtocol specifies the name of the
         network management protocol to which this row applies."
    ::= { tmnxSysMgmtProtocolEntry 1 }

tmnxSysMgmtProtLastChange  OBJECT-TYPE
    SYNTAX      TimeStamp
    MAX-ACCESS  read-only
    STATUS      current
    DESCRIPTION
        "The value of tmnxSysMgmtProtLastChange indicates the sysUpTime at
         the time of the last modification of this row.

         If no changes were made to the row since the last re-initialization of
         the local network management subsystem, then this object contains the
         value zero."
    ::= { tmnxSysMgmtProtocolEntry 2 }

tmnxSysMgmtAllowImmediateChange    OBJECT-TYPE
    SYNTAX      TruthValue
    MAX-ACCESS  read-create
    STATUS      current
    DESCRIPTION
        "The value of tmnxSysMgmtAllowImmediateChange specifies whether the
         user is allowed to make direct changes to the configuration, or whether
         all changes need to be applied through use of a candidate config."
    DEFVAL { true }
    ::= { tmnxSysMgmtProtocolEntry 3 }

-- ------------------------------------------------------------
--  tmnxSysFileTransProfTable - File Transmission Profile Table
-- ------------------------------------------------------------

tmnxSysFileTransProfObjs         OBJECT IDENTIFIER ::= { tmnxSysObjs 34 }

tmnxSysFileTransProfTableLstChgd OBJECT-TYPE
    SYNTAX      TimeStamp
    MAX-ACCESS  read-only
    STATUS      current
    DESCRIPTION
        "The value of tmnxSysFileTransProfTableLstChgd indicates the time,
         since system startup, when tmnxSysFileTransProfTable last changed 
         configuration.

         A value of zero indicates that no changes were made to this table
         since the system was last initialized."
    ::= { tmnxSysFileTransProfObjs 1 }

tmnxSysFileTransProfTable        OBJECT-TYPE
    SYNTAX      SEQUENCE OF TmnxSysFileTransProfEntry
    MAX-ACCESS  not-accessible
    STATUS      current
    DESCRIPTION
         "The tmnxSysFileTransProfTable contains objects used to configure 
          instances of the file transmission profile, which are used by a device
          to download files from a server (e.g., File Transfer Protocol (FTP) 
          server or Hypertext Transfer Protocol(HTTP) server).

          A file transmission profile specifies 1) the local configuration for
          sending and receiving a file in an Nokia SROS device; and
          2) the behaviours of the device when the transmission fails.
          
          Usage example: 
              Auto Certificate Revocation List (CRL) retrieval: downloading 
              CRL from a FTP or an HTTP server to an Nokia SROS device.

          Entries in this table are created and deleted via SNMP set operations
          to tmnxSysFileTransProfRowStatus."     
    ::= { tmnxSysFileTransProfObjs 2 }

tmnxSysFileTransProfEntry        OBJECT-TYPE
    SYNTAX      TmnxSysFileTransProfEntry
    MAX-ACCESS  not-accessible
    STATUS      current
    DESCRIPTION
        "Each tmnxSysFileTransProfEntry contains the configuration for one
         file transmission profile."
    INDEX { tmnxSysFileTransProfName }
    ::= { tmnxSysFileTransProfTable 1 }

TmnxSysFileTransProfEntry             
    ::= SEQUENCE {
        tmnxSysFileTransProfName         TNamedItem,
        tmnxSysFileTransProfRowStatus    RowStatus,
        tmnxSysFileTransProfLastChanged  TimeStamp,
        tmnxSysFileTransProfRtrId        TmnxVRtrIDOrZero,
        tmnxSysFileTransProfSvcId        TmnxServId,
        tmnxSysFileTransProfSrcAddrV4T   InetAddressType,
        tmnxSysFileTransProfSrcAddrV4    InetAddress,
        tmnxSysFileTransProfSrcAddrV6T   InetAddressType,
        tmnxSysFileTransProfSrcAddrV6    InetAddress,
        tmnxSysFileTransProfTimeout      Unsigned32,
        tmnxSysFileTransProfRetry        Unsigned32,
        tmnxSysFileTransProfRedirection  Unsigned32
    }

tmnxSysFileTransProfName         OBJECT-TYPE
    SYNTAX      TNamedItem
    MAX-ACCESS  not-accessible
    STATUS      current
    DESCRIPTION
        "The value of tmnxSysFileTransProfName uniquely specifies one file 
         transmission profile configured on this system."
    ::= { tmnxSysFileTransProfEntry 1 }

tmnxSysFileTransProfRowStatus    OBJECT-TYPE
    SYNTAX      RowStatus
    MAX-ACCESS  read-create
    STATUS      current
    DESCRIPTION
        "The value of tmnxSysFileTransProfRowStatus specifies the status of this 
         row. It is used to create and delete row entries in 
         tmnxSysFileTransProfTable."
    ::= { tmnxSysFileTransProfEntry 2 }

tmnxSysFileTransProfLastChanged  OBJECT-TYPE
    SYNTAX      TimeStamp
    MAX-ACCESS  read-only
    STATUS      current
    DESCRIPTION
        "The value of tmnxSysFileTransProfLastChanged indicates the time, since
         system startup, that the configuration of this row was created or 
         modified."
    ::= { tmnxSysFileTransProfEntry 3 }

tmnxSysFileTransProfRtrId        OBJECT-TYPE
    SYNTAX      TmnxVRtrIDOrZero
    MAX-ACCESS  read-create
    STATUS      current
    DESCRIPTION
        "The value of tmnxSysFileTransProfRtrId specifies the virtual router 
         instance. The file transmission connection(s) will be established 
         between the virtual router and a server (e.g., FTP or HTTP server).
         
         When the value of tmnxSysFileTransProfRtrId is zero, the virtual 
         router must be specified using tmnxSysFileTransProfSvcId.

         tmnxSysFileTransProfRtrId and tmnxSysFileTransProfSvcId cannot both 
         be zero.

         Only those IDs corresponding to the 'Base' and 'management' virtual 
         routers may be set in this object. Refer to 
         TIMETRA-VRTR-MIB.mib::vRtrName."
    DEFVAL { 1 }
    ::= { tmnxSysFileTransProfEntry 4 }

tmnxSysFileTransProfSvcId        OBJECT-TYPE
    SYNTAX      TmnxServId(0|1..2147483647)
    MAX-ACCESS  read-create
    STATUS      current
    DESCRIPTION
        "The value of tmnxSysFileTransProfSvcId specifies the service 
         identifier for a virtual router. The file transmission connection(s)
         will be established between the virtual router and a server
         (e.g., FTP or HTTP server).
  
         When the value of tmnxSysFileTransProfSvcId is zero, the virtual 
         router must be specified using tmnxSysFileTransProfRtrId.

         tmnxSysFileTransProfRtrId and tmnxSysFileTransProfSvcId cannot be both
         zero.

         Only VPRN service IDs are allowed."
    DEFVAL { 0 }
    ::= { tmnxSysFileTransProfEntry 5 }

tmnxSysFileTransProfSrcAddrV4T   OBJECT-TYPE
    SYNTAX      InetAddressType
    MAX-ACCESS  read-create
    STATUS      current
    DESCRIPTION
        "The value of tmnxSysFileTransProfSrcAddrV4T specifies the IP address
         type of tmnxSysFileTransProfSrcAddrV4.
         
         The value of tmnxSysFileTransProfSrcAddrV4T can be either of 'ipv4(1)'
         or 'unknown (0)'.
         
         The value of 'unknown(0)' specifies no IPv4 source address is 
         configured."
    DEFVAL { unknown }
    ::= { tmnxSysFileTransProfEntry 6 }

tmnxSysFileTransProfSrcAddrV4    OBJECT-TYPE
    SYNTAX      InetAddress (SIZE (0|4))
    MAX-ACCESS  read-create
    STATUS      current
    DESCRIPTION
        "The value of tmnxSysFileTransProfSrcAddrV4 specifies the IPv4 source
         address specified in tmnxSysFileTransProfRtrId.
                   
         The value of an empty string specifies no IPv4 source address is
         configured."
    DEFVAL { ''H }
    ::= { tmnxSysFileTransProfEntry 7 }

tmnxSysFileTransProfSrcAddrV6T   OBJECT-TYPE
    SYNTAX      InetAddressType
    MAX-ACCESS  read-create
    STATUS      current
    DESCRIPTION
        "The value of tmnxSysFileTransProfSrcAddrV6T specifies the IP address
         type of tmnxSysFileTransProfSrcAddrV6.
         
         The value of tmnxSysFileTransProfSrcAddrV6T can be either of 'ipv6(2)' 
         or 'unknown (0)'.
         
         The value of 'unknown(0)' specifies no IPv6 source address is 
         configured."
    DEFVAL { unknown }
    ::= { tmnxSysFileTransProfEntry 8 }

tmnxSysFileTransProfSrcAddrV6    OBJECT-TYPE
    SYNTAX      InetAddress (SIZE (0|16))
    MAX-ACCESS  read-create
    STATUS      current
    DESCRIPTION
        "The value of tmnxSysFileTransProfSrcAddrV6 specifies the IPv6 source
         address specified in tmnxSysFileTransProfRtrId.
        
         The value of an empty string specifies no IPv6 source address is
         configured."
    DEFVAL { ''H }
    ::= { tmnxSysFileTransProfEntry 9 }

tmnxSysFileTransProfTimeout      OBJECT-TYPE
    SYNTAX      Unsigned32 (1..3600)
    UNITS       "seconds"
    MAX-ACCESS  read-create
    STATUS      current
    DESCRIPTION
        "The value of tmnxSysFileTransProfTimeout specifies the connection 
         timeout (in seconds) for the file transmission.
 
         The timeout is the maximum waiting time to receive any data from the 
         server (e.g., FTP or HTTP server)."
    DEFVAL { 60 }
    ::= { tmnxSysFileTransProfEntry 10 }

tmnxSysFileTransProfRetry        OBJECT-TYPE
    SYNTAX      Unsigned32 (0|1..256)
    MAX-ACCESS  read-create
    STATUS      current
    DESCRIPTION
        "The value of tmnxSysFileTransProfRetry specifies the number of retries
         of the file transmission profile.
         
         When the virtual router does not receive any data from a server (e.g.,
         FTP or HTTP server) after the configured tmnxSysFileTransProfTimeout 
         interval, the router may repeat the request to the server. The number
         of retries specifies the maximum number of repeated requests.

         Virtual router instances are configured using
         tmnxSysFileTransProfRtrId. 
        
         The value of zero specifies that the request should not be resent by
         the virtual router after the configured tmnxSysFileTransProfTimeout 
         interval elapsed."
    DEFVAL { 0 }
    ::= { tmnxSysFileTransProfEntry 11 }

tmnxSysFileTransProfRedirection  OBJECT-TYPE
    SYNTAX      Unsigned32 (0|1..8)
    MAX-ACCESS  read-create
    STATUS      current
    DESCRIPTION
        "The value of tmnxSysFileTransProfRedirection specifies the maximum 
         level of redirection of the file transmission profile.
 
         The virtual router may send a new request to another server if the 
         requested resources are not available (e.g., temporarily 
         available to another server).

         Usage example: 
           When a virtual router receives an HTTP response with status code of
           redirection 3xx (e.g., 301 Moved Permanently), the router may send
           a new request to another location. The level of redirection specifies
           the maximum number of new requests that can be sent by a virtual 
           router. 

         For any file transmission protocols (e.g., FTP), which do not support
         redirection, the value of tmnxSysFileTransProfRedirection will be 
         ignored.

         The value of zero specifies that no new request should be sent by a 
         virtual router to another server."
    REFERENCE
        "RFC 2616, 'Hypertext Transfer Protocol -- HTTP/1.1', IETF, June 1999,
         section 10.3 'Redirection 3xx'."
    DEFVAL { 0 }
    ::= { tmnxSysFileTransProfEntry 12 }

--
-- EVENT HANDLING SYSTEM (EHS)
--  AUGMENTS to DISMAN-SCRIPT-MIB tables
-- 
tmnxEhsExtObjs   OBJECT IDENTIFIER ::= { tmnxSysObjs 35 }

--
--  Augmentation of the DISMAN-SCRIPT-MIB::smLaunchTable. 
--  Use of AUGMENTS clause implies a one-to-one dependent relationship
--  between the base table, DISMAN-SCRIPT-MIB::smLaunchTable, and the
--  augmenting table, tmnxSmLaunchExtTable. This in effect extends
--  the smLaunchTable with additional columns. Creation or deletion 
--  of a row in the smLaunch Table results in the same fate for the
--  row in the tmnxSmLaunchExtTable.

tmnxSmLaunchExtTable  OBJECT-TYPE
    SYNTAX      SEQUENCE OF TmnxSmLaunchExtEntry
    MAX-ACCESS  not-accessible
    STATUS      current
    DESCRIPTION
        "The tmnxSmLaunchExtTable is an extension of the
        DISMAN-SCRIPT-MIB::smLaunchTable."
    ::= { tmnxEhsExtObjs 1 }

tmnxSmLaunchExtEntry  OBJECT-TYPE
    SYNTAX      TmnxSmLaunchExtEntry
    MAX-ACCESS  not-accessible
    STATUS      current
    DESCRIPTION
        "Each row entry represents contains additional attributes
         for the smLaunchEntry.
         
         Entries cannot be created and deleted via SNMP SET operations."
    AUGMENTS { smLaunchEntry }
    ::= { tmnxSmLaunchExtTable 1 }

TmnxSmLaunchExtEntry  ::= SEQUENCE {
        tmnxSmLaunchExtAuthType  TmnxScriptAuthType
    }

tmnxSmLaunchExtAuthType  OBJECT-TYPE
    SYNTAX      TmnxScriptAuthType
    MAX-ACCESS  read-only
    STATUS      current
    DESCRIPTION
        "The value of tmnxSmLaunchExtAuthType indicates the module
        that last started a script by writing to
        DISMAN-SCRIPT-MIB::smLaunchStart.  If no script has yet
        been started the value 'none(0)' is returned."
    ::= { tmnxSmLaunchExtEntry 1 }

--
--  Augmentation of the DISMAN-SCRIPT-MIB::smRunTable. 
--  Use of AUGMENTS clause implies a one-to-one dependent relationship
--  between the base table, DISMAN-SCRIPT-MIB::smRunTable, and the
--  augmenting table, tmnxSmRunExtTable. This in effect extends
--  the smRunTable with additional columns. Creation or deletion 
--  of a row in the smLaunch Table results in the same fate for the
--  row in the tmnxSmRunExtTable.

tmnxSmRunExtTable  OBJECT-TYPE
    SYNTAX      SEQUENCE OF TmnxSmRunExtEntry
    MAX-ACCESS  not-accessible
    STATUS      current
    DESCRIPTION
        "The tmnxSmRunExtTable is an extension of the
        DISMAN-SCRIPT-MIB::smRunTable."
    ::= { tmnxEhsExtObjs 2 }

tmnxSmRunExtEntry  OBJECT-TYPE
    SYNTAX      TmnxSmRunExtEntry
    MAX-ACCESS  not-accessible
    STATUS      current
    DESCRIPTION
        "Each row entry represents contains additional attributes
         for the smRunEntry.
         
         Entries cannot be created and deleted via SNMP SET operations."
    AUGMENTS { smRunEntry }
    ::= { tmnxSmRunExtTable 1 }

TmnxSmRunExtEntry  ::= SEQUENCE {
        tmnxSmRunExtAuthType    TmnxScriptAuthType,
        tmnxSmRunExtUserName    TNamedItemOrEmpty
    }

tmnxSmRunExtAuthType  OBJECT-TYPE
    SYNTAX      TmnxScriptAuthType
    MAX-ACCESS  read-only
    STATUS      current
    DESCRIPTION
        "The value of tmnxSmRunExtAuthType indicates the module
        that started this run of a script by writing to
        DISMAN-SCRIPT-MIB::smLaunchStart.  If no script has yet
        been started the value 'none(0)' is returned."
    ::= { tmnxSmRunExtEntry 1 }

tmnxSmRunExtUserName  OBJECT-TYPE
    SYNTAX      TNamedItemOrEmpty
    MAX-ACCESS  read-only
    STATUS      current
    DESCRIPTION
        "The value of tmnxSmRunExtUserName indicates the name of
        the user account used to check access to CLI commands while
        executing the script.  If no script has yet been started 
        the empty string is returned."
    ::= { tmnxSmRunExtEntry 2 }



--
--  tmnxSmRunArgsTable : extending the support for the Event Handling System  
--    


tmnxSmRunArgsTable OBJECT-TYPE
    SYNTAX      SEQUENCE OF TmnxSmRunArgsEntry
    MAX-ACCESS  not-accessible
    STATUS      current
    DESCRIPTION
        "The tmnxSmRunArgsTable contains information pertaining to 
         the arguments passed to the exec script."
    ::= { tmnxEhsExtObjs  3 }

tmnxSmRunArgsEntry OBJECT-TYPE
    SYNTAX      TmnxSmRunArgsEntry
    MAX-ACCESS  not-accessible
    STATUS      current
    DESCRIPTION
        "The tmnxSmRunArgsEntry provides the argument information for a 
         specified exec script."
    INDEX   {
            smLaunchOwner, 
            smLaunchName, 
            smRunIndex,
            tmnxSmRunEventArgIndex 
            }
    ::= { tmnxSmRunArgsTable 1 }

TmnxSmRunArgsEntry ::=
    SEQUENCE {            
            tmnxSmRunEventArgIndex       Unsigned32,
            tmnxSmRunEventArgName        TLNamedItem,
            tmnxSmRunEventArgValue       TItemDescription
            }

tmnxSmRunEventArgIndex    OBJECT-TYPE
    SYNTAX      Unsigned32
    MAX-ACCESS  not-accessible
    STATUS      current
    DESCRIPTION
        "The value of tmnxSmRunEventArgIndex specifies the argument index
         number associated with a particular tmnxSmRunArgsEntry."
    ::= { tmnxSmRunArgsEntry 1 }

tmnxSmRunEventArgName     OBJECT-TYPE
    SYNTAX      TLNamedItem
    MAX-ACCESS  read-only
    STATUS      current
    DESCRIPTION
        "The value of tmnxSmRunEventArgName indicates the name of an argument
         passed to the exec script."
    ::= { tmnxSmRunArgsEntry 2 }

tmnxSmRunEventArgValue      OBJECT-TYPE
    SYNTAX          TItemDescription
    MAX-ACCESS      read-only
    STATUS          current
    DESCRIPTION
        "The value of tmnxSmRunEventArgValue indicates the ASCII printable 
         contents of the specified argument passed to the exec script."
    ::= { tmnxSmRunArgsEntry 3 }

tmnxSysSwReposObjs               OBJECT IDENTIFIER ::= { tmnxSysObjs 36 }

--%%%%%%%%%%%%%%%%%%%%%%%%%%%%%%%%%%%%%%%%%%%%%%%%%%%%%%%%%%%%%%%%%%%%%%%%%%%%%
--
--  TIMETRA-SYSTEM-MIB System Software Repository Table
--
tmnxSysSwReposTableLastChanged   OBJECT-TYPE
    SYNTAX      TimeStamp
    MAX-ACCESS  read-only
    STATUS      current
    DESCRIPTION
        "The value of tmnxSysSwReposTableLastChanged indicates the time, since
         system startup, when tmnxSysSoftwareRepositoryTable last changed
         configuration."
    ::= { tmnxSysSwReposObjs 1 }

tmnxSysSoftwareRepositoryTable   OBJECT-TYPE
    SYNTAX      SEQUENCE OF TmnxSysSoftwareRepositoryEntry
    MAX-ACCESS  not-accessible
    STATUS      current
    DESCRIPTION
        "The tmnxSysSoftwareRepositoryTable contains configuration information
         about the system software repositories for extension chassis."
    ::= { tmnxSysSwReposObjs 2 }

tmnxSysSoftwareRepositoryEntry   OBJECT-TYPE
    SYNTAX      TmnxSysSoftwareRepositoryEntry
    MAX-ACCESS  not-accessible
    STATUS      current
    DESCRIPTION
        "The tmnxSysSoftwareRepositoryEntry consists of the configurable objects
         for the system software repositories."
    INDEX { tmnxSysSwReposName }
    ::= { tmnxSysSoftwareRepositoryTable 1 }

TmnxSysSoftwareRepositoryEntry   ::= SEQUENCE {
    tmnxSysSwReposName               TNamedItem,
    tmnxSysSwReposRowStatus          RowStatus,
    tmnxSysSwReposLastChanged        TimeStamp,
    tmnxSysSwReposDescription        TItemDescription,
    tmnxSysSwReposPrimaryLocation    TmnxDisplayStringURL,
    tmnxSysSwReposSecondaryLocation  TmnxDisplayStringURL,
    tmnxSysSwReposTertiaryLocation   TmnxDisplayStringURL
}

tmnxSysSwReposName               OBJECT-TYPE
    SYNTAX      TNamedItem
    MAX-ACCESS  not-accessible
    STATUS      current
    DESCRIPTION
        "The value of tmnxSysSwReposName specifies a unique name which
         identifies the system software repository."
    ::= { tmnxSysSoftwareRepositoryEntry 1 }

tmnxSysSwReposRowStatus          OBJECT-TYPE
    SYNTAX      RowStatus
    MAX-ACCESS  read-create
    STATUS      current
    DESCRIPTION
        "The value of tmnxSysSwReposRowStatus specifies the row status. It
         allows the creation and deletion of rows in
         tmnxSysSoftwareRepositoryTable."
    ::= { tmnxSysSoftwareRepositoryEntry 2 }

tmnxSysSwReposLastChanged        OBJECT-TYPE
    SYNTAX      TimeStamp
    MAX-ACCESS  read-only
    STATUS      current
    DESCRIPTION
        "The value of tmnxSysSwReposLastChanged indicates the time, since system
         startup, that the configuration of the system software repository was
         created or modified."
    ::= { tmnxSysSoftwareRepositoryEntry 3 }

tmnxSysSwReposDescription        OBJECT-TYPE
    SYNTAX      TItemDescription
    MAX-ACCESS  read-create
    STATUS      current
    DESCRIPTION
        "The value of tmnxSysSwReposDescription specifies the description
         of the system software repository.

         An empty string indicates this object has not been configured."
    DEFVAL  { ''H }
    ::= { tmnxSysSoftwareRepositoryEntry 4 }

tmnxSysSwReposPrimaryLocation    OBJECT-TYPE
    SYNTAX      TmnxDisplayStringURL
    MAX-ACCESS  read-create
    STATUS      current
    DESCRIPTION
        "The value of tmnxSysSwReposPrimaryLocation specifies the primary
         location of the directory that contains the runtime image files
         for the system software repository.

         An empty string indicates this object has not been configured."
    DEFVAL  { ''H }
    ::= { tmnxSysSoftwareRepositoryEntry 5 }

tmnxSysSwReposSecondaryLocation  OBJECT-TYPE
    SYNTAX      TmnxDisplayStringURL
    MAX-ACCESS  read-create
    STATUS      current
    DESCRIPTION
        "The value of tmnxSysSwReposSecondaryLocation specifies the secondary
         location of the directory that contains the runtime image files
         for the system software repository.

         An empty string indicates this object has not been configured."
    DEFVAL  { ''H }
    ::= { tmnxSysSoftwareRepositoryEntry 6 }

tmnxSysSwReposTertiaryLocation   OBJECT-TYPE
    SYNTAX      TmnxDisplayStringURL
    MAX-ACCESS  read-create
    STATUS      current
    DESCRIPTION
        "The value of tmnxSysSwReposTertiaryLocation specifies the tertiary
         location of the directory that contains the runtime image files
         for the system software repository.

         An empty string indicates this object has not been configured."
    DEFVAL  { ''H }
    ::= { tmnxSysSoftwareRepositoryEntry 7 }

--
-- Conformance Information
--
tmnxSysCompliances   OBJECT IDENTIFIER ::= { tmnxSysConformance 1 }
tmnxSysGroups        OBJECT IDENTIFIER ::= { tmnxSysConformance 2 }
tmnxSysMGGroups      OBJECT IDENTIFIER ::= { tmnxSysConformance 3 }
tmnxSysMGCompliances OBJECT IDENTIFIER ::= { tmnxSysConformance 4 }
tmnxSysDCCompliance  OBJECT IDENTIFIER ::= { tmnxSysConformance 5 }
tmnxSysDCGroups      OBJECT IDENTIFIER ::= { tmnxSysConformance 6 }

-- compliance statements

-- tmnxSysCompliance  MODULE-COMPLIANCE
--    ::= { tmnxSysCompliances 1 }

-- tmnxSysR2r1Compliance  MODULE-COMPLIANCE
--    ::= { tmnxSysCompliances 2 }

-- tmnxSysV3v0Compliance  MODULE-COMPLIANCE
--    ::= { tmnxSysCompliances 3 }

tmnxSysV4v0Compliance  MODULE-COMPLIANCE
    STATUS  obsolete
    DESCRIPTION
            "The compliance statement for management of general system
             capabilities on Nokia SROS series systems."
    MODULE  -- this module
        MANDATORY-GROUPS {
            tmnxSysGeneralV3v0Group,
            tmnxSysTimeV4v0Group,
            tmnxSysConfigV3v0Group,
            tmnxSysRadiusServerGroup,
            tmnxSysTacPlusServerGroup,
            tmnxSysBofGroup,
            tmnxSysNotificationV4v0Group,
            tmnxPersistenceV4v0Group
        }
    ::= { tmnxSysCompliances 4 }

tmnxSysV5v0Compliance  MODULE-COMPLIANCE
    STATUS  obsolete
    DESCRIPTION
            "The compliance statement for management of general system
             capabilities on Nokia SROS series systems."
    MODULE  -- this module
        MANDATORY-GROUPS {
            tmnxSysGeneralV3v0Group,
            tmnxSysTimeV4v0Group,
            tmnxSysConfigV3v0Group,
            tmnxSysRadiusServerV5v0Group,
            tmnxSysTacPlusServerV5v0Group,
            tmnxSysBofGroup,
            tmnxSysNotificationV5v0Group,
            tmnxPersistenceV5v0Group
        }
    ::= { tmnxSysCompliances 5 }

tmnxSysV6v0Compliance  MODULE-COMPLIANCE
    STATUS  obsolete
    DESCRIPTION
            "The compliance statement for management of general system
             capabilities on Nokia SROS series systems."
    MODULE  -- this module
        MANDATORY-GROUPS {
            tmnxSysGeneralV3v0Group,
            tmnxSysTimeV4v0Group,
            tmnxSysConfigV3v0Group,
            tmnxSysRadiusServerV5v0Group,
            tmnxSysTacPlusServerV5v0Group,
            tmnxSysBofV6v0Group,
            tmnxSysNotificationV6v0Group,
            tmnxPersistenceV6v0Group,
            tmnxSysIpv6MgmtItfV6v0Group,
            tmnxSysLiV6v0Group
        }
    ::= { tmnxSysCompliances 6 }

tmnxSysV7v0Compliance  MODULE-COMPLIANCE
    STATUS  obsolete
    DESCRIPTION
            "The compliance statement for management of general system
             capabilities on Nokia SROS series systems."
    MODULE  -- this module
        MANDATORY-GROUPS {
            tmnxSysGeneralV3v0Group,
            tmnxSysGeneralV7v0Group,
            tmnxSysTimeV4v0Group,
            tmnxSysConfigV3v0Group,
            tmnxSysRadiusServerV5v0Group,
            tmnxSysTacPlusServerV5v0Group,
            tmnxSysBofV6v0Group,
            tmnxSysNotificationV6v0Group,
            tmnxPersistenceV6v0Group,
            tmnxSysIpv6MgmtItfV6v0Group,
            tmnxSysLiV6v0Group,
            tmnxSystemCpuMonitorGroup
        }
    ::= { tmnxSysCompliances 7 }

tmnxSysV8v0Compliance  MODULE-COMPLIANCE
    STATUS  obsolete
    DESCRIPTION
            "The compliance statement for management of general system
             capabilities on Nokia SROS series systems."
    MODULE  -- this module
        MANDATORY-GROUPS {
            tmnxSysGeneralV3v0Group,
            tmnxSysGeneralV7v0Group,
            tmnxSysTimeV4v0Group,
            tmnxSysConfigV8v0Group,
            tmnxSysLoginControlV8v0Group,
            tmnxSysRadiusServerV5v0Group,
            tmnxSysTacPlusServerV5v0Group,
            tmnxSysBofV6v0Group,
            tmnxSysNotificationV6v0Group,
            tmnxPersistenceV6v0Group,
            tmnxSysIpv6MgmtItfV6v0Group,
            tmnxSysLiV6v0Group,
            tmnxSysIcmpVSV6v1Group,
            tmnxSysEthInfoGroup,
            tmnxSystemCpuMonitorGroup
        }
    ::= { tmnxSysCompliances 8 }

tmnxSysV9v0Compliance  MODULE-COMPLIANCE
    STATUS  obsolete 
    DESCRIPTION
            "The compliance statement for management of general system
             capabilities on Nokia SROS series systems."
    MODULE  -- this module
        MANDATORY-GROUPS {
            tmnxPersistenceV9v0Group,
            tmnxSysBofV6v0Group,
            tmnxSysConfigV8v0Group,
            tmnxSysEthInfoGroup,
            tmnxSysGeneralV3v0Group,
            tmnxSysGeneralV7v0Group,
            tmnxSysIcmpVSV6v1Group,
            tmnxSysIpv6MgmtItfV6v0Group,
            tmnxSysLiFilterGroup,
            tmnxSysLiV6v0Group,
            tmnxSysLoginControlSecGroup,
            tmnxSysLoginControlV8v0Group,
            tmnxSysLoginControlV9v0Group,
            tmnxSysNotificationV6v0Group,
            tmnxSysNotificationV9v0Group,
            tmnxSysRadiusServerV5v0Group,
            tmnxSysRollbackV9v0Group,
            tmnxSysTacPlusServerV5v0Group,
            tmnxSysTimeV4v0Group,
            tmnxSystemCpuMonitorGroup,
            tmnxSysCertGroup,
            tmnxSysNotificationRBGroup
        }
    ::= { tmnxSysCompliances 9 }

tmnxSysBootedBofCompliance MODULE-COMPLIANCE
    STATUS  current
    DESCRIPTION
            "The compliance statement for currently active (booted) BOF 
             capabilities on Nokia SROS series systems."
    MODULE  -- this module
        MANDATORY-GROUPS {
            tmnxSysBootedBofGroup
        }
    ::= { tmnxSysCompliances 10 }

tmnxSysV10v0Compliance  MODULE-COMPLIANCE
    STATUS  obsolete
    DESCRIPTION
            "The compliance statement for management of general system
             capabilities on Nokia SROS series systems."
    MODULE  -- this module
        MANDATORY-GROUPS {
            tmnxPersistenceV9v0Group,
            tmnxSysBofV6v0Group,
            tmnxSysConfigV8v0Group,
            tmnxSysEthInfoGroup,
            tmnxSysGeneralV3v0Group,
            tmnxSysGeneralV7v0Group,
            tmnxSysIcmpVSV6v1Group,
            tmnxSysIpv6MgmtItfV6v0Group,
            tmnxSysLiFilterGroup,
            tmnxSysLiV6v0Group,
            tmnxSysLoginControlSecGroup,
            tmnxSysLoginControlV8v0Group,
            tmnxSysLoginControlV9v0Group,
            tmnxSysNotificationV6v0Group,
            tmnxSysNotificationV9v0Group,
            tmnxSysNotificationV10v0Group,
            tmnxSysRadiusServerV5v0Group,
            tmnxSysRollbackV9v0Group,
            tmnxSysTacPlusServerV5v0Group,
            tmnxSysTimeV4v0Group,
            tmnxSystemCpuMonitorGroup,
            tmnxSysCertGroup,
            tmnxSysRollbackRescueGroup,
            tmnxSysNotificationRBGroup
        }
    ::= { tmnxSysCompliances 11 }

tmnxSysV11v0Compliance  MODULE-COMPLIANCE
    STATUS  obsolete
    DESCRIPTION
            "The compliance statement for management of general system
             capabilities on Nokia SROS series systems."
    MODULE  -- this module
        MANDATORY-GROUPS {
            tmnxPersistenceV11v0Group,
            tmnxSysBofV6v0Group,
            tmnxSysConfigV8v0Group,
            tmnxSysEthInfoGroup,
            tmnxSysGeneralV3v0Group,
            tmnxSysGeneralV7v0Group,
            tmnxSysIcmpVSV6v1Group,
            tmnxSysIpv6MgmtItfV6v0Group,
            tmnxSysLiFilterGroup,
            tmnxSysLiV6v0Group,
            tmnxSysLoginControlSecGroup,
            tmnxSysLoginControlV8v0Group,
            tmnxSysLoginControlV9v0Group,
            tmnxSysNotificationV6v0Group,
            tmnxSysNotificationV9v0Group,
            tmnxSysNotificationV10v0Group,
            tmnxSysRadiusServerV5v0Group,
            tmnxSysRollbackV9v0Group,
            tmnxSysTacPlusServerV5v0Group,
            tmnxSysTimeV4v0Group,
            tmnxSystemCpuMonitorGroup,
            tmnxSysCertGroup,
            tmnxSysRollbackRescueGroup,
            tmnxSysNotificationRBGroup,
            tmnxSysGroupingSystemGroup,
            tmnxSysCandidateCfgGroup,
            tmnxSysNetconfV11v0Group,
            tmnxSysStrmV11v0R4Group
        }
    ::= { tmnxSysCompliances 12 }

tmnxSysV12v0Compliance  MODULE-COMPLIANCE
    STATUS  obsolete
    DESCRIPTION
            "The compliance statement for management of general system
             capabilities on Nokia SROS series systems."
    MODULE  -- this module
        MANDATORY-GROUPS {
            tmnxPersistenceV12v0Group,
            tmnxSysBofV6v0Group,
            tmnxSysCandidateCfgGroup,
            tmnxSysCardResourceGroup,
            tmnxSysCertGroup,
            tmnxSysConfigV8v0Group,
            tmnxSysDNSSecNotifV12v0Group,
            tmnxSysDNSSecV12v0Group,
            tmnxSysEthInfoGroup,
            tmnxSysGeneralV3v0Group,
            tmnxSysGeneralV7v0Group,
            tmnxSysGroupingSystemGroup,
            tmnxSysIcmpVSV6v1Group,
            tmnxSysIpv6MgmtItfV6v0Group,
            tmnxSysLiFilterGroup,
            tmnxSysLiV6v0Group,
            tmnxSysLoginControlSecGroup,
            tmnxSysLoginControlV8v0Group,
            tmnxSysLoginControlV9v0Group,
            tmnxSysNetconfV11v0Group,
            tmnxSysNotificationRBGroup,
            tmnxSysNotificationV10v0Group,
            tmnxSysNotificationV12v0Group,
            tmnxSysNotificationV6v0Group,
            tmnxSysNotificationV9v0Group,
            tmnxSysRadiusServerV5v0Group,
            tmnxSysRollbackRescueGroup,
            tmnxSysRollbackV9v0Group,
            tmnxSysDhcpGroup,
            tmnxSysStrmV11v0R4Group,
            tmnxSysTacPlusServerV5v0Group,
            tmnxSysTimeV4v0Group,
            tmnxSystemCpuMonitorGroup,
            tmnxSysXmppV12v4Group,
            tmnxSysBofV12v0Group,
            tmnxSysLicenseV12v0Group
        }
    ::= { tmnxSysCompliances 13 }

tmnxSysV13v0Compliance  MODULE-COMPLIANCE
    STATUS  obsolete
    DESCRIPTION
            "The compliance statement for management of general system
             capabilities on Nokia SROS series systems."
    MODULE  -- this module
        MANDATORY-GROUPS {
            tmnxPersistenceV12v0Group,
            tmnxSysBofV6v0Group,
            tmnxSysCandidateCfgGroup,
            tmnxSysCardResourceGroup,
            tmnxSysCertGroup,
            tmnxSysConfigV8v0Group,
            tmnxSysDNSSecNotifV12v0Group,
            tmnxSysDNSSecV12v0Group,
            tmnxSysEthInfoGroup,
            tmnxSysGeneralV3v0Group,
            tmnxSysGeneralV7v0Group,
            tmnxSysGroupingSystemGroup,
            tmnxSysIcmpVSV6v1Group,
            tmnxSysIpv6MgmtItfV6v0Group,
            tmnxSysLiFilterGroup,
            tmnxSysLiV6v0Group,
            tmnxSysLoginControlSecGroup,
            tmnxSysLoginControlV8v0Group,
            tmnxSysLoginControlV9v0Group,
            tmnxSysNetconfV11v0Group,
            tmnxSysNotificationRBGroup,
            tmnxSysNotificationV10v0Group,
            tmnxSysNotificationV12v0Group,
            tmnxSysNotificationV6v0Group,
            tmnxSysNotificationV9v0Group,
            tmnxSysRadiusServerV5v0Group,
            tmnxSysRollbackRescueGroup,
            tmnxSysRollbackV9v0Group,
            tmnxSysDhcpGroup,
            tmnxSysStrmV11v0R4Group,
            tmnxSysTacPlusServerV5v0Group,
            tmnxSysTimeV4v0Group,
            tmnxSystemCpuMonitorGroup,
            tmnxSysXmppV12v4Group,
            tmnxSysBofV12v0Group,
            tmnxSysLicenseV12v0Group,
            tmnxSysFibV13v0Group,
            tmnxSysNetconfV13v0Group,
            tmnxSysSnmpSrcAccesLstV13v0Group,
            tmnxSysMgmtProtocolV13v0Group,
            tmnxSysFileTransProfV13v0Group,
            tmnxSysEhsV13v0Group,
            tmnxSysBofV13v0Group,
            tmnxSysLicenseV13v0Group,
            tmnxSysLicenseNotifV13v0Group,
            tmnxSysSwReposV13v0Group
        }
    ::= { tmnxSysCompliances 14 }

tmnxSysV14v0Compliance  MODULE-COMPLIANCE
    STATUS  current
    DESCRIPTION
            "The compliance statement for management of general system
             capabilities on Nokia SROS series systems in release
             14.0."
    MODULE  -- this module
        MANDATORY-GROUPS {
            tmnxPersistenceV12v0Group,
            tmnxSysBofV6v0Group,
            tmnxSysCandidateCfgGroup,
            tmnxSysCardResourceGroup,
            tmnxSysCertGroup,
            tmnxSysConfigV8v0Group,
            tmnxSysDNSSecNotifV12v0Group,
            tmnxSysDNSSecV12v0Group,
            tmnxSysEthInfoGroup,
            tmnxSysGeneralV3v0Group,
            tmnxSysGeneralV7v0Group,
            tmnxSysGroupingSystemGroup,
            tmnxSysIcmpVSV6v1Group,
            tmnxSysIpv6MgmtItfV6v0Group,
            tmnxSysLiFilterGroup,
            tmnxSysLiV6v0Group,
            tmnxSysLoginControlSecGroup,
            tmnxSysLoginControlV8v0Group,
            tmnxSysLoginControlV9v0Group,
            tmnxSysNetconfV11v0Group,
            tmnxSysNotificationRBGroup,
            tmnxSysNotificationV10v0Group,
            tmnxSysNotificationV12v0Group,
            tmnxSysNotificationV6v0Group,
            tmnxSysNotificationV9v0Group,
            tmnxSysRadiusServerV5v0Group,
            tmnxSysRollbackRescueGroup,
            tmnxSysRollbackV9v0Group,
            tmnxSysDhcpGroup,
            tmnxSysStrmV11v0R4Group,
            tmnxSysTacPlusServerV5v0Group,
            tmnxSysTimeV4v0Group,
            tmnxSystemCpuMonitorGroup,
            tmnxSysXmppV12v4Group,
            tmnxSysBofV12v0Group,
            tmnxSysLicenseV12v0Group,
            tmnxSysFibV13v0Group,
            tmnxSysNetconfV13v0Group,
            tmnxSysSnmpSrcAccesLstV13v0Group,
            tmnxSysMgmtProtocolV13v0Group,
            tmnxSysFileTransProfV13v0Group,
            tmnxSysEhsV13v0Group,
            tmnxSysBofV13v0Group,
            tmnxSysLicenseV13v0Group,
            tmnxSysLicenseNotifV13v0Group,
            tmnxSysSwReposV13v0Group,
            tmnxSysBofV14v0Group,
            tmnxSysNotificationV14v0Group,
            tmnxPersistenceV14v0Group,
            tmnxSysNetconfV14v0Group,
            tmnxSysEhsParameterGroup,
            tmnxSysLicenseApplicationGroup,
            tmnxSysNotifyObjsV14v0Group,
            tmnxSysTimeV14v0Group
        }
    ::= { tmnxSysCompliances 15 }

tmnxSysV15v0Compliance  MODULE-COMPLIANCE
    STATUS  current
    DESCRIPTION
            "The compliance statement for management of general system
             capabilities on Nokia SROS series systems in release
             15.0."
    MODULE
        MANDATORY-GROUPS {
            tmnxSysLoginControlV15v0Group,
            tmnxSysGrpcV15v0Group,
            tmnxSysXmppMgmtGroup
        }
    ::= { tmnxSysCompliances 16 }


-- units of conformance

-- tmnxSysGeneralGroup   OBJECT-GROUP
--    ::= { tmnxSysGroups 1 }

-- tmnxSysTimeGroup     OBJECT-GROUP
--    ::= { tmnxSysGroups 2 }

-- tmnxSysConfigGroup     OBJECT-GROUP
--    ::= { tmnxSysGroups 3 }

tmnxSysRadiusServerGroup     OBJECT-GROUP
    OBJECTS {   radiusOperStatus,
                radiusServerAddress,
                radiusServerOperStatus
            }
    STATUS      obsolete
    DESCRIPTION
        "The group of objects supporting management of RADIUS servers
         on Nokia SROS series systems."
    ::= { tmnxSysGroups 4 }

tmnxSysTacPlusServerGroup     OBJECT-GROUP
    OBJECTS {   tacplusOperStatus,
                tacplusServerAddress,
                tacplusServerOperStatus
            }
    STATUS      obsolete
    DESCRIPTION
        "The group of objects supporting management of TACACS+ servers
         on Nokia SROS series systems."
    ::= { tmnxSysGroups 5 }

-- tmnxSysNotifyObjsGroup   OBJECT-GROUP
--    ::= { tmnxSysGroups 6 }

-- tmnxSysNotificationGroup NOTIFICATION-GROUP
--    ::= { tmnxSysGroups 7 }

tmnxSysBofGroup     OBJECT-GROUP
    OBJECTS {   sbiActiveIpAddr,
                sbiActiveIpMask,
                sbiStandbyIpAddr,
                sbiStandbyIpMask,
                sbiPrimaryImage,
                sbiSecondaryImage,
                sbiTertiaryImage,
                sbiPrimaryConfigFile,
                sbiSecondaryConfigFile,
                sbiTertiaryConfigFile,
                sbiPersist,
                sbiConsoleSpeed,
                sbiAutoNegotiate,
                sbiSpeed,
                sbiDuplex,
                sbiPrimaryDns,
                sbiSecondaryDns,
                sbiTertiaryDns,
                sbiDnsDomain,
                sbiWait,
                sbiStaticRouteNextHop,
                sbiStaticRouteRowStatus
            }
    STATUS      obsolete
    DESCRIPTION
        "The group of objects supporting management of the Boot
         Options File (BOF) on Nokia SROS series systems."
    ::= { tmnxSysGroups 8 }

-- tmnxSysNotifyObjsR2r1Group   OBJECT-GROUP
--    ::= { tmnxSysGroups 9 }

-- tmnxSysNotificationR2r1Group NOTIFICATION-GROUP
--    ::= { tmnxSysGroups  10 }

-- tmnxSysConfigR2r1Group     OBJECT-GROUP
--    ::= { tmnxSysGroups 11 }

tmnxSysConfigV3v0Group     OBJECT-GROUP
    OBJECTS {   ssiSaveConfig,
                ssiSyncMode,
                ssiSyncForce,
                ssiSyncStatus,
                ssiSyncConfigLastTime,
                ssiSyncBootEnvLastTime,
                ssiConfigMaxBackupRevisions,
                ssiSaveConfigResult,
                ssiSaveBof,
                ssiSaveBofResult,
                ssiSaveConfigDest,
                ssiSaveConfigDetail,
                ssiRedFailoverTime,
                ssiRedFailoverReason,
                sbiConfigStatus,
                sbiPersistStatus,
                sbiPersistIndex,
                sbiSnmpdAdminStatus,
                sbiSnmpdOperStatus,
                sbiSnmpdMaxPktSize,
                sbiSnmpdPortNum,
                sbiBootConfigOKScript,
                sbiConfigOKScriptStatus,
                sbiBootConfigFailScript,
                sbiConfigFailScriptStatus,
                sbiRedSwitchoverScript,
                sbiRedSwitchoverScriptStatus,
                slcFtpInboundMaxSessions,
                slcTelnetInboundMaxSessions,
                slcTelnetOutboundMaxSessions,
                slcPreLoginMessage,
                slcPreLoginMessageInclName,
                slcMessageOfTheDay,
                slcMessageOfTheDayType,
                slcLoginBanner,
                sysLACPSystemPriority,
                slcLoginExponentialBackOff
            }
    STATUS      obsolete
    DESCRIPTION
        "The group of objects supporting management of boot-up
         configuration and synchronization of active and standby systems
         on Nokia SROS series systems."
    ::= { tmnxSysGroups 12 }

-- tmnxPersistenceDhcpV3v0Group  OBJECT-GROUP
--    ::= { tmnxSysGroups 13 }

-- tmnxSysNotificationV3v0Group NOTIFICATION-GROUP
--    ::= { tmnxSysGroups  14 }

tmnxSysGeneralV3v0Group  OBJECT-GROUP
    OBJECTS {   sgiCpuUsage,
                sgiMemoryUsed,
                sgiMemoryAvailable,
                sgiMemoryPoolAllocated,
                sgiSwMajorVersion,
                sgiSwMinorVersion,
                sgiSwVersionModifier
            }
    STATUS      current
    DESCRIPTION
        "The group of objects supporting management of general system
         capabilities on Nokia SROS series systems, 3.0 Release."
    ::= { tmnxSysGroups 15 }

-- tmnxSysTimeV3v0Group  OBJECT-GROUP
--    ::= { tmnxSysGroups 16 }

tmnxSysObsoleteGroup    OBJECT-GROUP
    OBJECTS {
                stiSummerZoneStartDate,
                stiSummerZoneEndDate,
                tacplusServerAddress,
                radiusServerAddress
            }
    STATUS      obsolete
    DESCRIPTION
        "The group of objects in TIMETRA-SYSTEM-MIB which are obsoleted."
    ::= { tmnxSysGroups 17 }

tmnxPersistenceV4v0Group  OBJECT-GROUP
    OBJECTS {
                spiDhcpL2PersistenceFileLocation,
                spiDhcpL2PersistenceDescription,
                spiDhcpL3PersistenceFileLocation,
                spiDhcpL3PersistenceDescription,
                spiSubMgmtPersistenceFileLocation,
                spiSubMgmtPersistenceDescription
            }
    STATUS      obsolete
    DESCRIPTION
        "The group of objects supporting management of persistency across
         system reboot on Nokia SROS series systems."
    ::= { tmnxSysGroups 18 }

tmnxSysTimeV4v0Group  OBJECT-GROUP
    OBJECTS {   stiDateAndTime,
                stiActiveZone,
                stiHoursOffset,
                stiMinutesOffset,
                stiZoneType,
                stiSummerZoneRowStatus,
                stiSummerZoneOffset,
                stiSummerZoneStartDay,
                stiSummerZoneStartWeek,
                stiSummerZoneStartMonth,
                stiSummerZoneStartHour,
                stiSummerZoneStartMinute,
                stiSummerZoneEndDay,
                stiSummerZoneEndWeek,
                stiSummerZoneEndMonth,
                stiSummerZoneEndHour,
                stiSummerZoneEndMinute,
                sntpState,
                sntpServerRowStatus,
                sntpServerVersion,
                sntpServerPreference,
                sntpServerInterval,
                sntpAdminState,
                sntpOperStatus
            }
    STATUS      current
    DESCRIPTION
        "The group of objects supporting management of time
         on Nokia SROS series systems, 4.0 Release."
    ::= { tmnxSysGroups 19 }

tmnxSysNotifyObjsR4r0Group   OBJECT-GROUP
    OBJECTS {   tmnxNotifyRow,
                tmnxNotifyRowAdminState,
                tmnxNotifyRowOperState,
                tmnxMemoryModule,
                tmnxModuleMallocSize,
                tmnxDroppedTrapID,
                tmnxTrapDroppedReasonCode,
                tmnxTrapDroppedEntryID,
                tmnxNotifyEntryOID,
                tmnxSnmpdErrorMsg,
                tmnxSysTimeSetBy
           }
    STATUS      obsolete
    DESCRIPTION
        "The group of objects supporting notifications for general system
         capabilities on Nokia SROS series systems."
    ::= { tmnxSysGroups 20 }

tmnxSysNotificationV4v0Group NOTIFICATION-GROUP
    NOTIFICATIONS   {   stiDateAndTimeChanged,
                        ssiSaveConfigSucceeded,
                        ssiSaveConfigFailed,
                        sbiBootConfig,
                        sbiBootSnmpd,
                        radiusServerOperStatusChange,
                        radiusOperStatusChange,
                        tmnxConfigModify,
                        tmnxConfigCreate,
                        tmnxConfigDelete,
                        tmnxStateChange,
                        tmnxModuleMallocFailed,
                        tmnxTrapDropped,
                        ssiSyncConfigOK,
                        ssiSyncConfigFailed,
                        ssiSyncBootEnvOK,
                        ssiSyncBootEnvFailed,
                        sntpTimeDiffExceedsThreshold,
                        tacplusServerOperStatusChange,
                        tacplusOperStatusChange,
                        tmnxSnmpdError,
                        tmnxSsiMismatch,
                        tmnxSnmpdStateChange,
                        ssiRedStandbySyncing,
                        ssiRedStandbyReady,
                        ssiRedStandbySyncLost,
                        ssiRedSwitchover,
                        ssiRedCpmActive,
                        ssiRedSingleCpm,
                        persistencyClosedAlarmRaised,
                        persistencyClosedAlarmCleared,
                        tmnxSntpOperChange,
                        tmnxSysTimeSet
                    }
    STATUS      obsolete
    DESCRIPTION
        "The group of notifications supporting the general system
         capabilities on Nokia SROS series systems."
    ::= { tmnxSysGroups 21 }

tmnxSysNotifyObjsV5v0Group   OBJECT-GROUP
    OBJECTS {   
                tmnxPersistencyClient,
                tmnxPersistencyFileLocator,
                tmnxPersistencyNotifyMsg,
                tmnxPersistenceAffectedCpm,
                tmnxNotifyRow,
                tmnxNotifyRowAdminState,
                tmnxNotifyRowOperState,
                tmnxMemoryModule,
                tmnxModuleMallocSize,
                tmnxDroppedTrapID,
                tmnxTrapDroppedReasonCode,
                tmnxTrapDroppedEntryID,
                tmnxNotifyEntryOID,
                tmnxSnmpdErrorMsg,
                tmnxSysTimeSetBy,
                tmnxFtpFailureMsg,
                tmnxFtpFailureDestAddressType,
                tmnxFtpFailureDestAddress
           }
    STATUS      current
    DESCRIPTION
        "The group of objects supporting notifications for general system
         capabilities on Nokia SROS series systems."
    ::= { tmnxSysGroups 22 }

tmnxSysNotificationV5v0Group NOTIFICATION-GROUP
    NOTIFICATIONS   {   stiDateAndTimeChanged,
                        ssiSaveConfigSucceeded,
                        ssiSaveConfigFailed,
                        sbiBootConfig,
                        sbiBootSnmpd,
                        radiusOperStatusChange,
                        tmnxConfigModify,
                        tmnxConfigCreate,
                        tmnxConfigDelete,
                        tmnxStateChange,
                        tmnxModuleMallocFailed,
                        tmnxTrapDropped,
                        ssiSyncConfigOK,
                        ssiSyncConfigFailed,
                        ssiSyncBootEnvOK,
                        ssiSyncBootEnvFailed,
                        sntpTimeDiffExceedsThreshold,
                        tacplusOperStatusChange,
                        tmnxSnmpdError,
                        tmnxSsiMismatch,
                        tmnxSnmpdStateChange,
                        ssiRedStandbySyncing,
                        ssiRedStandbyReady,
                        ssiRedStandbySyncLost,
                        ssiRedSwitchover,
                        ssiRedCpmActive,
                        ssiRedSingleCpm,
                        persistencyClosedAlarmRaised,
                        persistencyClosedAlarmCleared,
                        tmnxSntpOperChange,
                        tmnxSysTimeSet,
                        tmnxFtpClientFailure,
                        tacplusInetSrvrOperStatusChange,
                        radiusInetServerOperStatusChange,
                        persistencyEventReport
                    }
    STATUS      obsolete
    DESCRIPTION
        "The group of notifications supporting the general system
         capabilities on Nokia SROS series systems."
    ::= { tmnxSysGroups 23 }

tmnxSysObsoleteNotificationV5v0Group    NOTIFICATION-GROUP
    NOTIFICATIONS {
                tacplusServerOperStatusChange,
                radiusServerOperStatusChange
            }
    STATUS      current
    DESCRIPTION
        "The group of notification objects in TIMETRA-SYSTEM-MIB which are
         obsoleted."
    ::= { tmnxSysGroups 24}

tmnxSysTacPlusServerV5v0Group     OBJECT-GROUP
    OBJECTS {   tacplusOperStatus,
                tacplusServerOperStatus,
                tacPlusServerInetAddressType,
                tacPlusServerInetAddress
            }
    STATUS      current
    DESCRIPTION
        "The group of objects supporting management of TACACS+ servers
         on Nokia SROS series systems."
    ::= { tmnxSysGroups 25 }

tmnxSysRadiusServerV5v0Group     OBJECT-GROUP
    OBJECTS {   radiusOperStatus,
                radiusServerOperStatus,
                radiusServerInetAddressType,
                radiusServerInetAddress
            }
    STATUS      current
    DESCRIPTION
        "The group of objects supporting management of RADIUS servers
         on Nokia SROS series systems."
    ::= { tmnxSysGroups 26 }

tmnxSysObsoleteV5v0Group    OBJECT-GROUP
    OBJECTS {
                stiSummerZoneStartDate,
                stiSummerZoneEndDate,
                tacplusServerAddress,
                radiusServerAddress,
                spiDhcpL2PersistenceFileLocation,
                spiDhcpL2PersistenceDescription,
                spiDhcpL3PersistenceFileLocation,
                spiDhcpL3PersistenceDescription
            }
    STATUS      current
    DESCRIPTION
        "The group of objects in TIMETRA-SYSTEM-MIB which are obsoleted."
    ::= { tmnxSysGroups 27 }

tmnxPersistenceV5v0Group  OBJECT-GROUP
    OBJECTS {
                spiSubMgmtPersistenceFileLocation,
                spiSubMgmtPersistenceDescription
            }
    STATUS      obsolete
    DESCRIPTION
        "The group of objects supporting management of persistency across
         system reboot on Nokia SROS series systems."
    ::= { tmnxSysGroups 28 }

tmnxSysIpv6MgmtItfV6v0Group     OBJECT-GROUP
    OBJECTS {
                sbiActiveIPv6Addr,
                sbiActiveIPv6PfxLen,
                sbiStandbyIPv6Addr,
                sbiStandbyIPv6PfxLen,
                sbiPrimaryDnsIPv6Addr,
                sbiSecondaryDnsIPv6Addr,
                sbiTertiaryDnsIPv6Addr,
                sbiStaticRouteIPv6NextHop,
                sbiStaticRouteIPv6RowStatus,
                sysDNSInfoLastChanged,
                sysDNSAddressResolvePref
            }
    STATUS      current
    DESCRIPTION
        "The group of objects supporting ipv6 management interface
         on Nokia SROS series systems."
    ::= { tmnxSysGroups 29 }

tmnxPersistenceV6v0Group  OBJECT-GROUP
    OBJECTS {
                spiSubMgmtPersistenceFileLocation,
                spiSubMgmtPersistenceDescription,
                spiDhcpSrvPersistenceFileLoc,
                spiDhcpSrvPersistenceDescr
            }
    STATUS      obsolete
    DESCRIPTION
        "The group of objects supporting management of persistency across
         system reboot on Nokia SROS series systems."
    ::= { tmnxSysGroups 30 }

tmnxSysBofV6v0Group     OBJECT-GROUP
    OBJECTS {   sbiActiveIpAddr,
                sbiActiveIpMask,
                sbiStandbyIpAddr,
                sbiStandbyIpMask,
                sbiPrimaryImage,
                sbiSecondaryImage,
                sbiTertiaryImage,
                sbiPrimaryConfigFile,
                sbiSecondaryConfigFile,
                sbiTertiaryConfigFile,
                sbiPersist,
                sbiConsoleSpeed,
                sbiAutoNegotiate,
                sbiSpeed,
                sbiDuplex,
                sbiPrimaryDns,
                sbiSecondaryDns,
                sbiTertiaryDns,
                sbiDnsDomain,
                sbiWait,
                sbiStaticRouteNextHop,
                sbiStaticRouteRowStatus,
                sbiLiSeparate,
                sbiLiLocalSave
            }
    STATUS      current
    DESCRIPTION
        "The group of objects supporting management of the Boot
         Options File (BOF) on Nokia SROS series systems."
    ::= { tmnxSysGroups 31 }

tmnxSysNotificationV6v0Group NOTIFICATION-GROUP
    NOTIFICATIONS   {   stiDateAndTimeChanged,
                        ssiSaveConfigSucceeded,
                        ssiSaveConfigFailed,
                        sbiBootConfig,
                        sbiBootSnmpd,
                        sbiBootConfigFailFileError,
                        sbiBootConfigOKFileError,
                        sbiBootLiConfig,
                        radiusOperStatusChange,
                        tmnxConfigModify,
                        tmnxConfigCreate,
                        tmnxConfigDelete,
                        tmnxStateChange,
                        tmnxModuleMallocFailed,
                        tmnxTrapDropped,
                        ssiSyncConfigOK,
                        ssiSyncConfigFailed,
                        ssiSyncBootEnvOK,
                        ssiSyncBootEnvFailed,
                        sntpTimeDiffExceedsThreshold,
                        tacplusOperStatusChange,
                        tmnxSnmpdError,
                        tmnxSsiMismatch,
                        tmnxSnmpdStateChange,
                        ssiRedStandbySyncing,
                        ssiRedStandbyReady,
                        ssiRedStandbySyncLost,
                        ssiRedSwitchover,
                        ssiRedCpmActive,
                        ssiRedSingleCpm,
                        persistencyClosedAlarmRaised,
                        persistencyClosedAlarmCleared,
                        tmnxSntpOperChange,
                        tmnxSysTimeSet,
                        tmnxFtpClientFailure,
                        tacplusInetSrvrOperStatusChange,
                        radiusInetServerOperStatusChange,
                        persistencyEventReport
                    }
    STATUS      current
    DESCRIPTION
        "The group of notifications supporting the general system
         capabilities on Nokia SROS series systems."
    ::= { tmnxSysGroups 32 }

tmnxSysLiV6v0Group  OBJECT-GROUP
    OBJECTS {
                sliConfigStatus,
                sliSaveConfig,
                sliSaveConfigResult,
                sliConfigLastModified,
                sliConfigLastSaved
            }
    STATUS      current
    DESCRIPTION
        "The group of objects supporting management of Lawful Intercept
         configuration on Nokia SROS series systems."
    ::= { tmnxSysGroups 33 }

tmnxSysNotifyObjsV6v0Group  OBJECT-GROUP
    OBJECTS {   tmnxNotifyObjectName,
                tmnxSyncFailureReason
            }
    STATUS      current
    DESCRIPTION
        "The group of objects added in 6.0 release to support system
         notifications."
    ::= { tmnxSysGroups 34 }

tmnxSysGeneralV7v0Group  OBJECT-GROUP
    OBJECTS {   sgiSnmpInGetBulks,
                sgiKbMemoryUsed,
                sgiKbMemoryAvailable,
                sgiKbMemoryPoolAllocated
            }
    STATUS      current
    DESCRIPTION
        "The group of objects supporting management of general system
         capabilities on Nokia SROS series systems added in 
         7.0 Release."
    ::= { tmnxSysGroups 35 }

tmnxSysIcmpVSV6v1Group  OBJECT-GROUP
    OBJECTS {   sysIcmpVSEnhancement
            }
    STATUS      current
    DESCRIPTION
        "The group of objects supporting management of ICMP vendor specific 
         enhancement capabilities on Nokia SROS series systems."
    ::= { tmnxSysGroups 36 }

tmnxSysConfigV8v0Group     OBJECT-GROUP
    OBJECTS {   ssiSaveConfig,
                ssiSyncMode,
                ssiSyncForce,
                ssiSyncStatus,
                ssiSyncConfigLastTime,
                ssiSyncBootEnvLastTime,
                ssiConfigMaxBackupRevisions,
                ssiSaveConfigResult,
                ssiSaveBof,
                ssiSaveBofResult,
                ssiSaveConfigDest,
                ssiSaveConfigDetail,
                ssiRedFailoverTime,
                ssiRedFailoverReason,
                sbiConfigStatus,
                sbiPersistStatus,
                sbiPersistIndex,
                sbiSnmpdAdminStatus,
                sbiSnmpdOperStatus,
                sbiSnmpdMaxPktSize,
                sbiSnmpdPortNum,
                sbiBootConfigOKScript,
                sbiConfigOKScriptStatus,
                sbiBootConfigFailScript,
                sbiConfigFailScriptStatus,
                sbiRedSwitchoverScript,
                sbiRedSwitchoverScriptStatus,
                sysLACPSystemPriority
            }
    STATUS      current
    DESCRIPTION
        "The group of objects supporting management of boot-up
         configuration and synchronization of active and standby systems
         on Nokia SROS series systems."
    ::= { tmnxSysGroups 37 }

tmnxSysLoginControlV8v0Group    OBJECT-GROUP
    OBJECTS {   slcFtpInboundMaxSessions,
                slcTelnetInboundMaxSessions,
                slcTelnetOutboundMaxSessions,
                slcPreLoginMessage,
                slcPreLoginMessageInclName,
                slcMessageOfTheDay,
                slcMessageOfTheDayType,
                slcLoginBanner,
                slcLoginExponentialBackOff,
                slcTelnetGracefulShutdown,
                slcSSHGracefulShutdown
            }
    STATUS      current
    DESCRIPTION
        "The group of objects supporting management of login control
         on Nokia SROS series systems."
    ::= { tmnxSysGroups 38 }

tmnxSysEthInfoGroup OBJECT-GROUP
    OBJECTS {
               sysNewQinqUntaggedSap
            }
    STATUS      current
    DESCRIPTION
        "The group of objects supporting management of Ethernet Info
         on Nokia SROS series systems."
    ::= { tmnxSysGroups 39 }

tmnxPersistenceV9v0Group  OBJECT-GROUP
    OBJECTS {
                spiSubMgmtPersistenceFileLocation,
                spiSubMgmtPersistenceDescription,
                spiDhcpSrvPersistenceFileLoc,
                spiDhcpSrvPersistenceDescr,
                spiNatFwdPersistenceFileLoc,
                spiNatFwdPersistenceDescr,
                spiAAPersistenceFileLoc,
                spiAAPersistenceDescr
            }
    STATUS      obsolete
    DESCRIPTION
        "The group of objects supporting management of persistency across
         system reboot on Nokia SROS series systems release 9.0."
    ::= { tmnxSysGroups 40 }

tmnxSysLoginControlSecGroup    OBJECT-GROUP
    OBJECTS {
                slcTelnetMinTTLValue,
                slcSSHMinTTLValue
            }
    STATUS      current
    DESCRIPTION
        "The group of objects supporting management of login control
         on Nokia SROS series systems."
    ::= { tmnxSysGroups 41 }

tmnxSysLiFilterGroup  OBJECT-GROUP
    OBJECTS {
                sliFilterLock
            }
    STATUS      current
    DESCRIPTION
        "The group of objects supporting management of Lawful Intercept
         configuration on Nokia SROS series systems."
    ::= { tmnxSysGroups 42 }

tmnxSysNotificationV9v0Group NOTIFICATION-GROUP
    NOTIFICATIONS   {   
        persistenceRestoreProblem,
        tmnxSysRollbackStarted,
        tmnxSysRollbackStatusChange,
        tmnxSysRollbackSaveStatusChange,
        tmnxSysRollbackFileDeleteStatus,
        ssiSyncRollbackOK,
        ssiSyncRollbackFailed,
        ssiSyncCertOK,
        ssiSyncCertFailed
                    }
    STATUS      current
    DESCRIPTION
        "The group of notifications supporting the general system
         capabilities added in release 9.0 of SROS."
    ::= { tmnxSysGroups 43 }

tmnxSysRollbackV9v0Group     OBJECT-GROUP
    OBJECTS { 
              tmnxSysRollbackIndex,
              tmnxSysRollbackStart,
              tmnxSysRollbackResult,
              tmnxSysRollbackSave,
              tmnxSysRollbackSaveResult,
              tmnxSysRollbackLocation,
              tmnxSysRollbackRevertIndex,
              tmnxSysRollbackRevertEndTime,
              tmnxSysRollbackTableLastChanged,
              tmnxSysRollbackFileCreationTime,
              tmnxSysRollbackFileComment,
              tmnxSysRollbackFileUserName,
              tmnxSysRollbackSavedTime,
              ssiSyncRollbackLastTime,
              tmnxSysRollbackRevertStartTime,
              tmnxSysRollbackRevertUserName,
              tmnxSysRollbackRevertFilename,
              tmnxSysRollbackSaveComment,
              tmnxSysRollbackAbortRevert,
              tmnxSysRollbackFileVersion,
              tmnxSysRollbackFileDelete,
              tmnxSysRollbackFileDeleteResult,
              ssiSyncRollbackMode,
              ssiSyncRollbackForce,
              ssiSyncRollbackStatus
            }
    STATUS      current
    DESCRIPTION
        "The group of objects supporting management of the Rollback Files 
         on Nokia SROS series systems."
    ::= { tmnxSysGroups 44 }

tmnxSysLoginControlV9v0Group    OBJECT-GROUP
    OBJECTS {
                slcSSHInboundMaxSessions,
                slcSSHOutboundMaxSessions
            }
    STATUS      current
    DESCRIPTION
        "The group of objects supporting management of login control
         on Nokia SROS series systems, added in release 9.0."
    ::= { tmnxSysGroups 45 }

tmnxSystemCpuMonitorGroup        OBJECT-GROUP
    OBJECTS {
                tmnxSysCpuMonCpuIdle,
                tmnxSysCpuMonBusyCoreUtil,
                tmnxSysCpuMonBusyGroupName,
                tmnxSysCpuMonBusyGroupUtil
            }
    STATUS      current
    DESCRIPTION
        "The group of objects, added in release 7.0, used for monitoring system
         CPU utilization on Nokia SROS series systems."
    ::= { tmnxSysGroups 46 }

tmnxSysCertGroup OBJECT-GROUP
    OBJECTS {
       ssiSyncCertForce,  
       ssiSyncCertLastTime,  
       ssiSyncCertMode,  
       ssiSyncCertStatus
    }
    STATUS      current
    DESCRIPTION
        "The group of objects supporting management of the synchronization of 
         certificate Files on Nokia SROS series systems."
    ::= { tmnxSysGroups 47 }

tmnxSysBootedBofGroup OBJECT-GROUP
    OBJECTS {
       sbbiLiSeparate,  
       sbbiLiLocalSave
    }
    STATUS      current
    DESCRIPTION
        "The group of objects giving the value of the currently active 
         (booted) Boot Options File (BOF) parameters on Nokia SROS 
         series systems."
    ::= { tmnxSysGroups 48 }

tmnxSysRollbackRescueGroup     OBJECT-GROUP
    OBJECTS { 
              tmnxSysRollbackRescueLocation,
              tmnxSysRollbackRescueSave,
              tmnxSysRollbackRescueRevert,
              tmnxSysRollbackRescueDelete,
              tmnxSysRollbackRescueSaveRes,
              tmnxSysRollbackRescueRevertRes,
              tmnxSysRollbackRescueDeleteRes,
              tmnxSysRollbackRescueSavedTime,
              tmnxSysRollbackRescueRevStTime,
              tmnxSysRollbackRescueRevEdTime,
              tmnxSysRollbackRescueRevUser,
              tmnxSysRollbackRescueSaveComment,
              tmnxSysRollbackRescueAbortRevert,
              tmnxSysRollbackRescueFileExists,
              tmnxSysRollbackMaxLocalFiles,
              tmnxSysRollbackMaxRemoteFiles
            }
    STATUS      current
    DESCRIPTION
        "The group of objects supporting management of the Rollback Rescue file 
         on Nokia SROS series systems."
    ::= { tmnxSysGroups 49 }

tmnxSysNotificationV10v0Group NOTIFICATION-GROUP
    NOTIFICATIONS   {   
        persistencyFileSysThresRaised,
        persistencyFileSysThresCleared,
        tmnxSysExecStarted,
        tmnxSysExecFinished
                    }
    STATUS      current
    DESCRIPTION
        "The group of notifications supporting the general system
         capabilities added in release 10.0 of SROS."
    ::= { tmnxSysGroups 50 }


tmnxSysNotifyObjsV10v0Group OBJECT-GROUP
    OBJECTS {
              tmnxSysRollbackFileType,
              tmnxSysExecScript,
              tmnxSysExecResult
            }
    STATUS      current
    DESCRIPTION
        "The group of accessible-for-notify objects supporting notifications
         on Nokia SROS series systems added in SROS release 10.0."
    ::= { tmnxSysGroups 51 }

tmnxSysNotificationRBGroup NOTIFICATION-GROUP
    NOTIFICATIONS   {
            tmnxSysRollbackSaveStarted,
            tmnxSysRollbackDeleteStarted,
            tmnxSysNvsysFileError
           }
    STATUS      current
    DESCRIPTION
        "The group of notifications supporting the general system
         capabilities added in Nokia SROS series systems."
    ::= { tmnxSysGroups 52 }

tmnxSysNotifyObjsGenGroup OBJECT-GROUP
    OBJECTS {
              tmnxSysFileErrorType
            }
    STATUS      current
    DESCRIPTION
        "The group of accessible-for-notify objects supporting notifications
         on Nokia SROS series systems added in SROS."
    ::= { tmnxSysGroups 53 }

tmnxSysGroupingSystemGroup     OBJECT-GROUP
    OBJECTS { 
                sgiSystemGroupID,
                sgiSystemSubGroupID
            }
    STATUS      current
    DESCRIPTION
        "The group of objects supporting management of the grouping systems 
         on Nokia SROS series systems."
    ::= { tmnxSysGroups 54 }

tmnxSysCandidateCfgGroup     OBJECT-GROUP
    OBJECTS { 
                tmnxSysCandidateCfgState,
                tmnxSysCandidateCfgEditors, 
                tmnxSysCandidateCfgCommitState,
                tmnxSysCandidateCfgCommitTime,
                tmnxSysCandidateCfgRevertTime,
                tmnxSysCandidateCfgChckptCreated,
                tmnxSysCandidateCfgExclusiveUsr,
                tmnxSysCandidateCfgUser
            }
    STATUS      current
    DESCRIPTION
        "The group of objects supporting the candidate config
         on Nokia SROS series system added in SROS release 11.0."
    ::= { tmnxSysGroups 55 }

tmnxPersistenceV11v0Group  OBJECT-GROUP
    OBJECTS {
                spiSubMgmtPersistenceFileLocation,
                spiSubMgmtPersistenceDescription,
                spiDhcpSrvPersistenceFileLoc,
                spiDhcpSrvPersistenceDescr,
                spiNatFwdPersistenceFileLoc,
                spiNatFwdPersistenceDescr,
                spiAAPersistenceFileLoc,
                spiAAPersistenceDescr,
                spiAncpPersistenceFileLoc,
                spiAncpPersistenceDescr
            }
    STATUS      obsolete
    DESCRIPTION
        "The group of objects supporting management of persistency across
         system reboot on Nokia SROS series systems release 11.0."
    ::= { tmnxSysGroups 56 }

tmnxSysNetconfV11v0Group     OBJECT-GROUP
    OBJECTS { 
                tmnxSysNetconfAdminStatus,
                tmnxSysNetconfOperStatus,
                tmnxSysNetconfRequests,
                tmnxSysNetconfGetRequests,
                tmnxSysNetconfGetConfigRequests,
                tmnxSysNetconfEditConfigRequests,
                tmnxSysNetconfCloseRequests,
                tmnxSysNetconfKillRequests,
                tmnxSysNetconfResponses,
                tmnxSysNetconfErrorResponses
            }
    STATUS      current
    DESCRIPTION
        "The group of objects supporting management of the NETCONF on
         Nokia SROS series system added in SROS release 11.0."
    ::= { tmnxSysGroups 57 }

tmnxSysStrmV11v0R4Group     OBJECT-GROUP
    OBJECTS {
                tmnxSysStrmAdminStatus,
                tmnxSysStrmDumpSnmpRequests,
                tmnxSysStrmGetManyRequests,
                tmnxSysStrmResponses
            }
    STATUS      current
    DESCRIPTION
        "The group of objects supporting management of the sam streaming on
         Nokia SROS series system added in SROS release 11.0 R4."
    ::= { tmnxSysGroups 58 }

tmnxSysNotifyObjsV11v0Group   OBJECT-GROUP
    OBJECTS {   
                tmnxTrapDroppedCount
           }
    STATUS      current
    DESCRIPTION
        "The group of objects supporting notifications for general system
         capabilities, added in Nokia SROS release 11.0."
    ::= { tmnxSysGroups 59 }

tmnxSysV12v0Groups               OBJECT IDENTIFIER ::= { tmnxSysGroups 60 }

tmnxPersistenceV12v0Group  OBJECT-GROUP
    OBJECTS {
                spiSubMgmtPersistenceFileLocation,
                spiSubMgmtPersistenceDescription,
                spiDhcpSrvPersistenceFileLoc,
                spiDhcpSrvPersistenceDescr,
                spiNatFwdPersistenceFileLoc,
                spiNatFwdPersistenceDescr,
                spiAAPersistenceFileLoc,
                spiAAPersistenceDescr,
                spiAncpPersistenceFileLoc,
                spiAncpPersistenceDescr,
                spiPythonPersistenceFileLoc,
                spiPythonPersistenceDescr
            }
    STATUS      current
    DESCRIPTION
        "The group of objects supporting management of persistency across
         system reboot on Nokia SROS series systems release 12.0."
    ::= { tmnxSysV12v0Groups 1 }

tmnxSysDNSSecV12v0Group  OBJECT-GROUP
    OBJECTS {
                sysDNSSecAdValidation,
                sysDNSSecRespCtrl
            }
    STATUS      current
    DESCRIPTION
        "The group of objects supporting Domain Name System Security 
         Extensions on Nokia SROS series systems in release 12.0."
    ::= { tmnxSysV12v0Groups 2 }

tmnxSysDNSSecNotifV12v0Group NOTIFICATION-GROUP
    NOTIFICATIONS   {   
                sysDNSSecFailedAuthentication
                    }
    STATUS      current
    DESCRIPTION
        "The group of notifications supporting Domain Name System Security
         Extension capabilities added in release 12.0 of SROS."
    ::= { tmnxSysV12v0Groups 3 }

tmnxSysNotificationV12v0Group NOTIFICATION-GROUP
    NOTIFICATIONS {
        tmnxConfigConflict,
        tmnxSysLicenseInvalid,
        tmnxSysLicenseExpiresSoon,
        tmnxSysVsdServerAvailable,
        tmnxSysVsdServerUnavailable,
        tmnxSysXmppServerFunctional,
        tmnxSysXmppServerNotFunctional
    }
    STATUS      current
    DESCRIPTION
        "The group of notifications supporting the general system
         capabilities added in release 12.0 of SROS."
    ::= { tmnxSysV12v0Groups 4 }

tmnxSysXmppV12v4Group  OBJECT-GROUP
      OBJECTS {
        tmnxSysVsdSystemId,
        tmnxSysVsdGwPubSubIsSubscrd,
        tmnxSysVsdGwPubSubNodeName,
        tmnxSysVsdGwPubSubLstSubscrdTime,
        tmnxSysVsdGwLastAuditTxTime,
        tmnxSysXmppServFQDN,
        tmnxSysXmppServRowStatus,
        tmnxSysXmppServUserName,
        tmnxSysXmppServPassword,
        tmnxSysXmppServLastChanged,
        tmnxSysXmppServUptime,
        tmnxSysXmppServIQSent,
        tmnxSysXmppServIQRcvd,
        tmnxSysXmppServIQError,
        tmnxSysXmppServIQTimedOut,
        tmnxSysXmppServIQAckRcvd,
        tmnxSysXmppServIQMinRtt,
        tmnxSysXmppServIQMaxRtt,
        tmnxSysXmppServVsdUpdatesRcvd,
        tmnxSysXmppServUpdatesRcvd,
        tmnxSysXmppServMsgSent,
        tmnxSysXmppServMsgRcvd,
        tmnxSysXmppServMsgAckRcvd,
        tmnxSysXmppServMsgError,
        tmnxSysXmppServMsgTimedOut,
        tmnxSysXmppServMsgMinRtt,
        tmnxSysXmppServMsgMaxRtt,
        tmnxSysXmppServSubSent,
        tmnxSysXmppServUnSubSent,
        tmnxSysXmppServState,
        tmnxSysXmppServAdminState,
        tmnxSysVsdServUptime,
        tmnxSysVsdServUserName,
        tmnxSysVsdServerStatus,
        tmnxSysVsdServMsgSent,
        tmnxSysVsdServMsgRcvd,
        tmnxSysVsdServMsgAckRcvd,
        tmnxSysVsdServMsgError,
        tmnxSysVsdServMsgTimedOut,
        tmnxSysVsdServMsgMinRtt,
        tmnxSysVsdServMsgMaxRtt,
        tmnxSysXmppServOperUserName,
        tmnxSysXmppServAuthType,
        tmnxSysXmppServConnMode
    }
    STATUS      current
    DESCRIPTION
    "The group of objects supporting XMPP server information
     on Nokia SROS series systems in release 12.0 R4."
    ::= { tmnxSysV12v0Groups 5 }

tmnxSysCardResourceGroup         OBJECT-GROUP
    OBJECTS {
        tmnxCardCpuResMonCpuIdle,
        tmnxCardCpuResMonBusyCoreUtil,
        tmnxCardCpuResMonBusyGroupName,
        tmnxCardCpuResMonBusyGroupUtil,
        tmnxCardMemResMemoryUsed,
        tmnxCardMemResMemoryAvailable,
        tmnxCardMemResPoolsAllocated
    }
    STATUS      current
    DESCRIPTION
        "The group of objects supporting the resource monitoring of cards in the
         system on Nokia SROS series systems in release 12.0."
    ::= { tmnxSysV12v0Groups 6 }

tmnxSysNotifyObjsV12v0Group   OBJECT-GROUP
    OBJECTS {
        tmnxSysDNSSecDomainName,
        tmnxSysNotifVsdServerName,
        tmnxSysNotifXmppServerName,
        tmnxSysLicenseErrorReason,
        tmnxSysLicenseTimeLeft
    }
    STATUS      current
    DESCRIPTION
        "The group of objects supporting notifications for general system
         capabilities, added in Nokia SROS release 12.0."
    ::= { tmnxSysV12v0Groups 7 }

tmnxSysBofV12v0Group             OBJECT-GROUP
    OBJECTS {   
        sbiLicenseFile
    }
    STATUS      current
    DESCRIPTION
        "The group of additional objects supporting bof configuration on
         Nokia SROS series systems in release 12.0."
    ::= { tmnxSysV12v0Groups 8 }

tmnxSysDhcpGroup OBJECT-GROUP
    OBJECTS {
        tmnxSysDhcp6AdvNoaddrsGlobal
    }
    STATUS      current
    DESCRIPTION
        "The group of objects supporting the configuration of DHCP at the system level."
    ::= { tmnxSysGroups 61 }

tmnxSysLicenseV12v0Group         OBJECT-GROUP
    OBJECTS {
        tmnxSysLicenseStatus,
        tmnxSysLicenseName,
        tmnxSysLicenseUuid,
        tmnxSysLicenseDescription,
        tmnxSysLicenseProduct,
        tmnxSysLicenseSwVersion,
        tmnxSysLicenseIssueDateAndTime,
        tmnxSysLicenseStartDateAndTime,
        tmnxSysLicenseEndDateAndTime
    }
    STATUS      current
    DESCRIPTION
        "The group of objects supporting license information on
         Nokia SROS series systems in release 12.0."
    ::= { tmnxSysV12v0Groups 9 }

tmnxSysFibV13v0Group OBJECT-GROUP
    OBJECTS {
        tmnxSysFibSelective
    }
    STATUS      current
    DESCRIPTION
        "The group of objects supporting the configuration of FIB at the system level."
    ::= { tmnxSysGroups 62 }    
    
tmnxSysNetconfV13v0Group     OBJECT-GROUP
    OBJECTS { 
                tmnxSysNetconfCopyConfigRequests,
                tmnxSysNetconfDelConfigRequests,
                tmnxSysNetconfValidateRequests
            }
    STATUS      current
    DESCRIPTION
        "The group of objects supporting management of the NETCONF on
         Nokia SROS series system added in SROS release 13.0."
    ::= { tmnxSysGroups 63 }

tmnxSysSnmpSrcAccesLstV13v0Group  OBJECT-GROUP
    OBJECTS {
        tmnxSysSnmpSrcAccessTblLstChgd,
        tmnxSysSnmpSrcAccessLstRowStatus,
        tmnxSysSnmpSrcAccessLstLastChg,
        tmnxSysSnmpCommunityPktDropped
    }
    STATUS  current
    DESCRIPTION
        "The group of objects supporting the configuration of source access list
        on Nokia SROS series system added in SROS release 13.0."
    ::= { tmnxSysGroups 64 }

tmnxSysMgmtProtocolV13v0Group  OBJECT-GROUP
    OBJECTS {
        tmnxSysMgmtProtocolTblLstChng,
        tmnxSysMgmtProtLastChange,
        tmnxSysMgmtAllowImmediateChange
    }
    STATUS  current
    DESCRIPTION
        "The group of objects supporting the configuration of network 
         management protocols on Nokia SROS series system added 
         in SROS release 13.0."
    ::= { tmnxSysGroups 65 }

tmnxSysFileTransProfV13v0Group      OBJECT-GROUP
    OBJECTS {
        tmnxSysFileTransProfTableLstChgd,
        tmnxSysFileTransProfRowStatus,
        tmnxSysFileTransProfLastChanged,
        tmnxSysFileTransProfRtrId,
        tmnxSysFileTransProfSvcId,
        tmnxSysFileTransProfSrcAddrV4T,
        tmnxSysFileTransProfSrcAddrV4,  
        tmnxSysFileTransProfSrcAddrV6T, 
        tmnxSysFileTransProfSrcAddrV6,
        tmnxSysFileTransProfTimeout,    
        tmnxSysFileTransProfRetry,      
        tmnxSysFileTransProfRedirection
    }
    STATUS current
    DESCRIPTION
        "The group of objects supporting the configuration of file transmission
         profiles on Nokia SROS series system added in SROS release 
         13.0."
    ::= { tmnxSysGroups 66 }

tmnxSysEhsV13v0Group      OBJECT-GROUP
    OBJECTS {
        tmnxSmLaunchExtAuthType,
        tmnxSmRunExtAuthType,
        tmnxSmRunExtUserName
    }
    STATUS current
    DESCRIPTION
        "The group of objects supporting the extension of tables in
         DISMAN-SCRIPT-MIB to support the Event Handling System (EHS)
         feature added in Nokia SROS release 13.0"
    ::= { tmnxSysGroups 67 }

tmnxSysLicenseV13v0Group         OBJECT-GROUP
    OBJECTS {
        tmnxSysLicenseVChassisType,
        tmnxSysLicenseMaxNumCPMs,
        tmnxSysLicenseMaxNumIOMs,
        tmnxSysCpmCardLicStatus,
        tmnxSysCpmCardLicName,
        tmnxSysCpmCardLicUuid,
        tmnxSysCpmCardLicDescription,
        tmnxSysCpmCardLicProduct,
        tmnxSysCpmCardLicSwVersion,
        tmnxSysCpmCardLicIssueDateTime,
        tmnxSysCpmCardLicStartDateTime,
        tmnxSysCpmCardLicEndDateTime,
        tmnxSysCpmCardLicVChassisType,
        tmnxSysCpmCardLicMaxNumCPMs,
        tmnxSysCpmCardLicMaxNumIOMs,
        tmnxSysCpmCardLicFeatDescription
    }
    STATUS      current
    DESCRIPTION
        "The group of additional objects supporting license information on
         Nokia SROS series systems in release 13.0."
    ::= { tmnxSysGroups 68 }

tmnxSysLicenseNotifV13v0Group    NOTIFICATION-GROUP
    NOTIFICATIONS {   
        tmnxSysLicenseValid
    }
    STATUS      current
    DESCRIPTION
        "The group of additional notifications supporting license information
         on Nokia SROS series systems in release 13.0."
    ::= { tmnxSysGroups 69 }

tmnxSysSwReposV13v0Group         OBJECT-GROUP
    OBJECTS {
        tmnxSysSwReposTableLastChanged,
        tmnxSysSwReposRowStatus,
        tmnxSysSwReposLastChanged,
        tmnxSysSwReposDescription,
        tmnxSysSwReposPrimaryLocation,
        tmnxSysSwReposSecondaryLocation,
        tmnxSysSwReposTertiaryLocation
    }
    STATUS      current
    DESCRIPTION
        "The group of objects maintaining configuration for system software
         repositories on Nokia SROS series systems in Release 13.0."
    ::= { tmnxSysGroups 70 }

tmnxSysBofV13v0Group             OBJECT-GROUP
    OBJECTS {
        sbiFips1402Level1,
        sbiEssSystemType
    }
    STATUS      current
    DESCRIPTION
        "The group of additional objects supporting bof configuration on 
         Nokia SROS series systems in release 13.0."
    ::= { tmnxSysGroups 71 }

tmnxSysV14v0Groups               OBJECT IDENTIFIER ::= { tmnxSysGroups 72 }

tmnxSysBofV14v0Group             OBJECT-GROUP
    OBJECTS     {
        sbiSystemBaseMacAddress
    }
    STATUS      current
    DESCRIPTION
        "The group of additional objects supporting bof configuration on
         Nokia SROS series systems in release 14.0."
    ::= { tmnxSysV14v0Groups 1 }


tmnxSysNotificationV14v0Group NOTIFICATION-GROUP
    NOTIFICATIONS {
        tmnxSysBaseMacAddressNotSet,
        tmnxSmLaunchStartFailed,
        tmnxEhsHandlerInvoked,
        tmnxEhsDroppedByMinDelay,
        tmnxSysAppStats24HrsAvailable,
        tmnxSysAppStatsWeekAvailable
    }
    STATUS      current
    DESCRIPTION
        "The group of additional notifications supporting the general system
         capabilities on Nokia SROS series systems in release 14.0."
    ::= { tmnxSysV14v0Groups 2 }

tmnxPersistenceV14v0Group  OBJECT-GROUP
    OBJECTS {
                tmnxDhcpLeaseTimeModeThreshold
            }
    STATUS      current
    DESCRIPTION
        "The group of objects supporting management of persistency across
         system reboot added to Nokia SROS series systems release 14.0."
    ::= { tmnxSysV14v0Groups 3 }



tmnxSysNetconfV14v0Group     OBJECT-GROUP
    OBJECTS {
        tmnxSysNetconfFailedEditCfgReqs,
        tmnxSysNetconfFailedLockReqs,
        sgiSnmpFailedSets,
        tmnxSysNetconfLockRequests,
        tmnxSysNetconfUnlockRequests,
        tmnxSysNetconfCommitRequests,
        tmnxSysNetconfDiscardRequests,
        tmnxSysNetconfCapCandidateCfg,
        tmnxSysNetconfCapRunningCfg,
        tmnxSysNetconfYangBaseR13,
        tmnxSysNetconfYangNokia
    }
    STATUS      current
    DESCRIPTION
        "The group of objects supporting management of the NETCONF on
         Nokia SROS series system added in SROS release 14.0."
    ::= { tmnxSysV14v0Groups 4 }
tmnxSysEhsParameterGroup      OBJECT-GROUP
    OBJECTS {
        tmnxSmRunEventArgName,
        tmnxSmRunEventArgValue
    }
    STATUS current
    DESCRIPTION
        "The group of objects extending the support of the DISMAN-SCRIPT-MIB 
         for the Event Handling System (EHS) feature added in Nokia
         SROS release 14.0"
    ::= { tmnxSysV14v0Groups 5 }

tmnxSysLicenseApplicationGroup         OBJECT-GROUP
    OBJECTS {
        tmnxSysAppStats24HrsName,
        tmnxSysAppStats24HrsValue,
        tmnxSysAppStats24HrsTime,
        tmnxSysAppStatsWeekName,
        tmnxSysAppStatsWeekAverage,
        tmnxSysAppStatsWeekPeak,
        tmnxSysAppStatsWeekTime,
        tmnxSysAppStatsPeakName,
        tmnxSysAppStatsPeakValue,
        tmnxSysAppStatsPeakTime
    }
    STATUS      current
    DESCRIPTION
        "The group of additional objects supporting license information
         about a virtual machine implementation of an application
         on Nokia SROS series systems."
    ::= { tmnxSysV14v0Groups 6 }


tmnxSysNotifyObjsV14v0Group   OBJECT-GROUP
    OBJECTS {
        tmnxSysLicenseErrorAction,
        tmnxSysNotifAppStatsTime,
        tmnxSysNotifAppStatsApplication,
        tmnxSysNotifAppStatsType
    }
    STATUS      current
    DESCRIPTION
        "The group of objects supporting notifications for general system
         capabilities, added in Nokia SROS release 14.0."
    ::= { tmnxSysV14v0Groups 7 }

tmnxSysTimeV14v0Group   OBJECT-GROUP
    OBJECTS {
        stiPreferLocalTime
    }
    STATUS current
    DESCRIPTION
        "The group of objects enhancing time output on Nokia SROS
         series systems for 14.0 Release."
    ::= {tmnxSysV14v0Groups 8}

tmnxSysLoginControlV15v0Group   OBJECT-GROUP
    OBJECTS {
        slcIdleTimeout,
        slcLoginScriptGlobal,
        slcLoginScriptPerUserDirectory,
        slcLoginScriptPerUserFilename
    }
    STATUS current
    DESCRIPTION
        "The group of objects enhancing system login control on Nokia SROS
         series systems for 15.0 Release."
    ::= {tmnxSysGroups 73}


tmnxSysGrpcV15v0Group            OBJECT-GROUP
    OBJECTS     {
        tmnxSysGrpcAdminState,
        tmnxSysGrpcOperState,
        tmnxSysGrpcTlsServerProfile,
        tmnxSysGrpcMaxMsgSize
    }
    STATUS      current
    DESCRIPTION
        "The group of objects supporting gRPC server on Nokia SROS series
         systems for 15.0 Release."
    ::= { tmnxSysGroups 74 }

tmnxSysXmppMgmtGroup OBJECT-GROUP
    OBJECTS     {
        tmnxSysXmppServServiceId,
        tmnxSysXmppServRouterId
    }
    STATUS      current
    DESCRIPTION
        "The group of objects supporting management of XMPP server on Nokia
         SROS series systems for 15.0 Release."
    ::= { tmnxSysGroups 75 }

tmnxSysV15v0Groups               OBJECT IDENTIFIER ::= { tmnxSysGroups 76 }


END
