TIMETRA-RIP-NG-MIB DEFINITIONS ::= BEGIN

IMPORTS
    InterfaceIndex
                                                         FROM IF-MIB
    InetAddress, InetAddressPrefixLength,
    InetAddressType
                                                         FROM INET-ADDRESS-MIB
    RouteTag
                                                         FROM RIPv2-MIB
    MODULE-COMPLIANCE, NOTIFICATION-GROUP,
    OBJECT-GROUP
                                                         FROM SNMPv2-CONF
    Counter32, Gauge32, Integer32,
    MODULE-IDENTITY, NOTIFICATION-TYPE,
    OBJECT-TYPE, Unsigned32
                                                         FROM SNMPv2-SMI
    DisplayString, RowStatus,
    TEXTUAL-CONVENTION, TimeStamp,
    TruthValue
                                                         FROM SNMPv2-TC
    timetraSRMIBModules, tmnxSRConfs,
    tmnxSRNotifyPrefix, tmnxSRObjs
                                                         FROM TIMETRA-GLOBAL-MIB
    TItemDescription, TNamedItem,
    TNamedItemOrEmpty,
    TPolicyStatementNameOrEmpty,
    TPriorityOrUndefined, TmnxAdminState,
    TmnxOperState, TmnxRipNgAuthKey,
    TmnxRipNgAuthType
                                                         FROM TIMETRA-TC-MIB
    vRtrID, vRtrIfIndex
                                                         FROM TIMETRA-VRTR-MIB
    ;

timetraRipNgMIBModule            MODULE-IDENTITY
    LAST-UPDATED "201304220000Z"
    ORGANIZATION "Nokia"
    CONTACT-INFO
        "Nokia SROS Support
         Web: http://www.nokia.com"
    DESCRIPTION
        "This document is the SNMP MIB module for the Nokia SROS implementation
         of RIP/RIP-NG.

         Copyright 2003-2017 Nokia. All rights reserved. Reproduction of this
         document is authorized on the condition that the foregoing copyright
         notice is included.

         This SNMP MIB module (Specification) embodies Nokia's
         proprietary intellectual property.  Nokia retains all
         title and ownership in the Specification, including any
         revisions.

         Nokia grants all interested parties a non-exclusive license to use and
         distribute an unmodified copy of this Specification in connection with
         management of Nokia products, and without fee, provided this copyright
         notice and license appear on all copies.

         This Specification is supplied `as is', and Nokia makes no warranty,
         either express or implied, as to the use, operation, condition, or
         performance of the Specification.

         There is one RIP instance per virtual router.  Each RIP instance
         can have a number of interface groups.

         The value of most RIP configuration objects can be defaulted at
         three levels: at the per-interface level, at the interface group
         level, and at the RIP instance level.  The per-interface object
         values are determined by the following: - if the interface
         object is set, by that value. - else if its corresponding group
         object is set, by that value - else by the corresponding rip
         instance object value. "

    REVISION    "201304220000Z"
    DESCRIPTION
        "Rev 12.0              22 Apr 2013 00:00
         12.0 release of the TIMETRA-RIP-NG-MIB."

    REVISION    "201304220000Z"
    DESCRIPTION
        "Rev 0.1               22 Apr 2013 00:00
         Initial version of the TIMETRA-RIP-NG-MIB."

    ::= { timetraSRMIBModules 89 }

TmnxRipNgInstVersion             ::= TEXTUAL-CONVENTION
    STATUS      current
    DESCRIPTION
        "The TmnxRipNgInstVersion TC defines the RIP/RIP-NG version applicable."
    SYNTAX      INTEGER {
        none  (0),
        rip   (1),
        ripNg (2)
    }

TmnxRipNgPeerVersion             ::= TEXTUAL-CONVENTION
    STATUS      current
    DESCRIPTION
        "The TmnxRipNgPeerVersion TC defines the RIP/RIP-NG version applicable
         to the peer."
    SYNTAX      INTEGER {
        none     (0),
        rip-v1   (1),
        rip-v2   (2),
        ripNg-v1 (3)
    }

TmnxRipNgMessageSize             ::= TEXTUAL-CONVENTION
    STATUS      current
    DESCRIPTION
        "The TmnxRipNgMessageSize TC defines the maximum number of routes that
         can be sent out per RIP/RIP-NG update message."
    SYNTAX      Unsigned32 (25..255)

TmnxRipNgMetric                  ::= TEXTUAL-CONVENTION
    STATUS      current
    DESCRIPTION
        "The TmnxRipNgMetric TC defines the range for RIP/RIP-NG route metric."
    SYNTAX      Unsigned32 (1..16)

TmnxRipNgPreference              ::= TEXTUAL-CONVENTION
    STATUS      current
    DESCRIPTION
        "The TmnxRipNgPreference TC defines the preference to be assigned to
         RIP/RIP-NG routes."
    SYNTAX      Unsigned32 (1..255)

TmnxRipNgReceive                 ::= TEXTUAL-CONVENTION
    STATUS      current
    DESCRIPTION
        "The TmnxRipNgReceive TC defines the which version of RIP/RIP-NG updates
         are to be accepted. Allowed values are :
           rip1(1)         - Only RIPv1 packets are accepted
           rip2(2)         - Only RIPv2 packets are accepted
           rip1OrRip2(3)   - RIPv1 and v2 packets are accepted
           doNotReceive(4) - No packets are accepted
           ripNg1(5)       - RIP-NGv1 packets are accepted

         Note that rip2 and rip1OrRip2 implies reception of multicast packets.

         For RIP only rip1(1), rip2(2), rip1OrRip2(3) and doNotReceive(4) are
         allowed.

         For RIP-NG only doNotReceive(4) and ripNg1(5) are allowed."
    REFERENCE
        "RIP2-MIB.rip2IfConfReceive"
    SYNTAX      INTEGER {
        rip1         (1),
        rip2         (2),
        rip1OrRip2   (3),
        doNotReceive (4),
        ripNg1       (5)
    }

TmnxRipNgSend                    ::= TEXTUAL-CONVENTION
    STATUS      current
    DESCRIPTION
        "The TmnxRipNgSend TC indicates how the router sends RIP/RIP-NG updates
         on an interface. Allowed values are :
           doNotSend(1)      - No RIP updates sent
           ripVersion1(2)    - RIPv1 updates are broadcast
           rip1Compatible(3) - RIPv2 updates are broadcast
           ripVersion2(4)    - RIPv2 updates are multicast
           ripNgVersion1(5)  - RIP-NGv1 updates are multicast
           ripUnicast(6)     - RIP/RIP-NG updates are unicast

         RIP2-MIB (RFC 1724) also defines ripV1Demand(5) and ripV2Demand(6)
         which are not supported by the Nokia SROS series.

         For RIP only doNotSend(1), ripVersion1(2), rip1Compatible(3),
         ripVersion2(4) and ripUnicast(6) are allowed.

         For RIP-NG only doNotSend(1), ripNgVersion1(5) and ripUnicast(6) are
         allowed.

         ripUnicast(6) is only allowed at neighbor level."
    REFERENCE
        "RIP2-MIB.rip2IfConfSend"
    SYNTAX      INTEGER {
        doNotSend      (1),
        ripVersion1    (2),
        rip1Compatible (3),
        ripVersion2    (4),
        ripNgVersion1  (5),
        ripUnicast     (6)
    }

TmnxRipNgTimerFlush              ::= TEXTUAL-CONVENTION
    STATUS      current
    DESCRIPTION
        "The TmnxRipTimerFlush TC defines the range for the Flush Timer (or
         Garbage Collection timer). The flush timer counts the number of
         seconds since the route was declared invalid. When the timer expires
         the invalid route will be flushed out from the route database."
    SYNTAX      Unsigned32 (1..1200)

TmnxRipNgTimerTimeout            ::= TEXTUAL-CONVENTION
    STATUS      current
    DESCRIPTION
        "The TmnxRipNgTimerTimeout TC defines the range for the Timeout Timer.
         The Timeout timer counts the number of seconds since the last update
         was received. When the timer expires the route will be declared
         invalid in the route database."
    SYNTAX      Unsigned32 (1..1200)

TmnxRipNgTimerUpdate             ::= TEXTUAL-CONVENTION
    STATUS      current
    DESCRIPTION
        "The TmnxRipNgTimerUpdate TC defines the range for the Update Timer.
         The Update timer determines how often updates are sent."
    SYNTAX      Unsigned32 (1..600)

tmnxRipNgObjs                    OBJECT IDENTIFIER ::= { tmnxSRObjs 89 }

tmnxRipNgGlobals                 OBJECT IDENTIFIER ::= { tmnxRipNgObjs 1 }

tmnxRipNgGlobalLearnedRoutes     OBJECT-TYPE
    SYNTAX      Counter32
    MAX-ACCESS  read-only
    STATUS      current
    DESCRIPTION
        "tmnxRipNgGlobalLearnedRoutes is the number of routes learned by
         RIP/RIP-NG."
    ::= { tmnxRipNgGlobals 1 }

tmnxRipNgGlobalTimedoutRoutes    OBJECT-TYPE
    SYNTAX      Counter32
    MAX-ACCESS  read-only
    STATUS      current
    DESCRIPTION
        "tmnxRipNgGlobalTimedoutRoutes is the number of invalid RIP/RIP-NG
         routes."
    ::= { tmnxRipNgGlobals 2 }

tmnxRipNgGlobalCurrentMemory     OBJECT-TYPE
    SYNTAX      Counter32
    MAX-ACCESS  read-only
    STATUS      current
    DESCRIPTION
        "tmnxRipNgGlobalCurrentMemory is the amount of memory used by this
         RIP/RIP-NG router instance."
    ::= { tmnxRipNgGlobals 3 }

tmnxRipNgGlobalMaximumMemory     OBJECT-TYPE
    SYNTAX      Counter32
    MAX-ACCESS  read-only
    STATUS      current
    DESCRIPTION
        "tmnxRipNgGlobalMaximumMemory is the amount of memory allocated for
         this RIP/RIP-NG router instance."
    ::= { tmnxRipNgGlobals 4 }

tmnxRipNgTableObjs               OBJECT IDENTIFIER ::= { tmnxRipNgObjs 2 }

tmnxRipNgInstTable               OBJECT-TYPE
    SYNTAX      SEQUENCE OF TmnxRipNgInstEntry
    MAX-ACCESS  not-accessible
    STATUS      current
    DESCRIPTION
        "tmnxRipNgInstTable contains configuration information for the
         RIP/RIP-NG instance on a virtual router."
    ::= { tmnxRipNgTableObjs 1 }

tmnxRipNgInstEntry               OBJECT-TYPE
    SYNTAX      TmnxRipNgInstEntry
    MAX-ACCESS  not-accessible
    STATUS      current
    DESCRIPTION
        "tmnxRipNgInstEntry is an entry (conceptual row) in the
         tmnxRipNgInstTable. Each entry represents the configuration for a
         RIP/RIP-NG instance.

         Entries in this table cannot be created and deleted via SNMP SET
         operations.  An entry in this table is created by the agent when
         vRtrRipStatus in the vRtrConfTable is set to 'create(1)'. The entry
         is destroyed when vRtrRipStatus is set to 'delete(2)'."
    INDEX       {
        vRtrID,
        tmnxRipNgInstVersion
    }
    ::= { tmnxRipNgInstTable 1 }

TmnxRipNgInstEntry               ::= SEQUENCE
{
    tmnxRipNgInstVersion             TmnxRipNgInstVersion,
    tmnxRipNgInstAuthType            TmnxRipNgAuthType,
    tmnxRipNgInstAuthKey             TmnxRipNgAuthKey,
    tmnxRipNgInstCheckZero           TruthValue,
    tmnxRipNgInstMessageSize         TmnxRipNgMessageSize,
    tmnxRipNgInstMetricIn            TmnxRipNgMetric,
    tmnxRipNgInstMetricOut           TmnxRipNgMetric,
    tmnxRipNgInstPreference          TmnxRipNgPreference,
    tmnxRipNgInstReceive             TmnxRipNgReceive,
    tmnxRipNgInstSend                TmnxRipNgSend,
    tmnxRipNgInstSplitHorizon        TruthValue,
    tmnxRipNgInstTimerFlush          TmnxRipNgTimerFlush,
    tmnxRipNgInstTimerTimeout        TmnxRipNgTimerTimeout,
    tmnxRipNgInstTimerUpdate         TmnxRipNgTimerUpdate,
    tmnxRipNgInstImportPolicy1       TPolicyStatementNameOrEmpty,
    tmnxRipNgInstImportPolicy2       TPolicyStatementNameOrEmpty,
    tmnxRipNgInstImportPolicy3       TPolicyStatementNameOrEmpty,
    tmnxRipNgInstImportPolicy4       TPolicyStatementNameOrEmpty,
    tmnxRipNgInstImportPolicy5       TPolicyStatementNameOrEmpty,
    tmnxRipNgInstExportPolicy1       TPolicyStatementNameOrEmpty,
    tmnxRipNgInstExportPolicy2       TPolicyStatementNameOrEmpty,
    tmnxRipNgInstExportPolicy3       TPolicyStatementNameOrEmpty,
    tmnxRipNgInstExportPolicy4       TPolicyStatementNameOrEmpty,
    tmnxRipNgInstExportPolicy5       TPolicyStatementNameOrEmpty,
    tmnxRipNgInstDescription         TItemDescription,
    tmnxRipNgInstAdminStatus         TmnxAdminState,
    tmnxRipNgInstOperStatus          TmnxOperState,
    tmnxRipNgInstPropagateMetric     TruthValue,
    tmnxRipNgInstExportLimit         Unsigned32,
    tmnxRipNgInstExpLmtLogPct        Unsigned32,
    tmnxRipNgInstTotalExpRoutes      Gauge32
}

tmnxRipNgInstVersion             OBJECT-TYPE
    SYNTAX      TmnxRipNgInstVersion
    MAX-ACCESS  not-accessible
    STATUS      current
    DESCRIPTION
        "The value of tmnxRipNgInstVersion specifies the RIP/RIP-NG version
         supported by this instance."
    ::= { tmnxRipNgInstEntry 1 }

tmnxRipNgInstAuthType            OBJECT-TYPE
    SYNTAX      TmnxRipNgAuthType
    MAX-ACCESS  read-create
    STATUS      current
    DESCRIPTION
        "tmnxRipNgInstAuthType defines the type of authentication to be used
         for the RIP/RIP-NG instance."
    DEFVAL      { noAuthentication }
    ::= { tmnxRipNgInstEntry 2 }

tmnxRipNgInstAuthKey             OBJECT-TYPE
    SYNTAX      TmnxRipNgAuthKey
    MAX-ACCESS  read-create
    STATUS      current
    DESCRIPTION
        "tmnxRipNgInstAuthKey is the authentication key that should be used for
         the RIP/RIP-NG instance when tmnxRipNgInstAuthType has a value other
         than noAuthentication(1). Modifying the value of tmnxRipNgInstAuthType
         does not modify the tmnxRipNgInstAuthKey value. If a string shorter
         than 16 octets is supplied, it will be left-justified and padded to 16
         octets, on the right, with nulls (0x00).

         Reading this object always results in an  OCTET STRING of
         length zero; authentication may not be bypassed by reading
         the MIB object."
    DEFVAL      { ''H }
    ::= { tmnxRipNgInstEntry 3 }

tmnxRipNgInstCheckZero           OBJECT-TYPE
    SYNTAX      TruthValue
    MAX-ACCESS  read-create
    STATUS      current
    DESCRIPTION
        "tmnxRipNgInstCheckZero specifies whether RIP updates are checked for
         for zero values in fields defined as Must-Be-Zero by the RIPv1 and v2
         specifications."
    DEFVAL      { false }
    ::= { tmnxRipNgInstEntry 4 }

tmnxRipNgInstMessageSize         OBJECT-TYPE
    SYNTAX      TmnxRipNgMessageSize
    MAX-ACCESS  read-create
    STATUS      current
    DESCRIPTION
        "tmnxRipNgInstMessageSize is the maximum number of routes that can be
         sent out per RIP/RIP-NG update message."
    DEFVAL      { 25 }
    ::= { tmnxRipNgInstEntry 5 }

tmnxRipNgInstMetricIn            OBJECT-TYPE
    SYNTAX      TmnxRipNgMetric
    MAX-ACCESS  read-create
    STATUS      current
    DESCRIPTION
        "tmnxRipNgInstMetricIn is the value added to the metric of routes
         received from a RIP/RIP-NG neighbor."
    DEFVAL      { 1 }
    ::= { tmnxRipNgInstEntry 6 }

tmnxRipNgInstMetricOut           OBJECT-TYPE
    SYNTAX      TmnxRipNgMetric
    MAX-ACCESS  read-create
    STATUS      current
    DESCRIPTION
        "tmnxRipNgInstMetricOut is the value added to the metric of routes
         exported into RIP/RIP-NG and advertised to RIP/RIP-NG neighbors."
    DEFVAL      { 1 }
    ::= { tmnxRipNgInstEntry 7 }

tmnxRipNgInstPreference          OBJECT-TYPE
    SYNTAX      TmnxRipNgPreference
    MAX-ACCESS  read-create
    STATUS      current
    DESCRIPTION
        "tmnxRipNgInstPreference is the route preference to be assigned to
         RIP/RIP-NG routes. This value may be overridden via route policies."
    DEFVAL      { 100 }
    ::= { tmnxRipNgInstEntry 8 }

tmnxRipNgInstReceive             OBJECT-TYPE
    SYNTAX      TmnxRipNgReceive
    MAX-ACCESS  read-create
    STATUS      current
    DESCRIPTION
        "tmnxRipNgInstReceive specifies which version of RIP/RIP-NG updates are
         to be accepted."
    DEFVAL      { ripNg1 }
    ::= { tmnxRipNgInstEntry 9 }

tmnxRipNgInstSend                OBJECT-TYPE
    SYNTAX      TmnxRipNgSend
    MAX-ACCESS  read-create
    STATUS      current
    DESCRIPTION
        "tmnxRipNgInstSend specifies the version to be used for sending
         RIP/RIP-NG updates."
    DEFVAL      { ripNgVersion1 }
    ::= { tmnxRipNgInstEntry 10 }

tmnxRipNgInstSplitHorizon        OBJECT-TYPE
    SYNTAX      TruthValue
    MAX-ACCESS  read-create
    STATUS      current
    DESCRIPTION
        "tmnxRipNgInstSplitHorizon specifies whether split horizon scheme is to
         be used when sending updates to RIP/RIP-NG neighbors."
    DEFVAL      { true }
    ::= { tmnxRipNgInstEntry 11 }

tmnxRipNgInstTimerFlush          OBJECT-TYPE
    SYNTAX      TmnxRipNgTimerFlush
    UNITS       "seconds"
    MAX-ACCESS  read-create
    STATUS      current
    DESCRIPTION
        "tmnxRipNgInstTimerFlush is the number of seconds after a route has
         been declared invalid that it is flushed from the route database."
    DEFVAL      { 120 }
    ::= { tmnxRipNgInstEntry 12 }

tmnxRipNgInstTimerTimeout        OBJECT-TYPE
    SYNTAX      TmnxRipNgTimerTimeout
    UNITS       "seconds"
    MAX-ACCESS  read-create
    STATUS      current
    DESCRIPTION
        "tmnxRipNgInstTimerTimeout is the number of seconds after a route has
         been discovered or last updated that it is declared invalid in the
         route database."
    DEFVAL      { 180 }
    ::= { tmnxRipNgInstEntry 13 }

tmnxRipNgInstTimerUpdate         OBJECT-TYPE
    SYNTAX      TmnxRipNgTimerUpdate
    UNITS       "seconds"
    MAX-ACCESS  read-create
    STATUS      current
    DESCRIPTION
        "tmnxRipNgInstTimerUpdate determines how often updates are sent."
    DEFVAL      { 30 }
    ::= { tmnxRipNgInstEntry 14 }

tmnxRipNgInstImportPolicy1       OBJECT-TYPE
    SYNTAX      TPolicyStatementNameOrEmpty
    MAX-ACCESS  read-create
    STATUS      current
    DESCRIPTION
        "tmnxRipNgInstImportPolicy1 is import policy number 1 for the instance
         level."
    DEFVAL      { ''H }
    ::= { tmnxRipNgInstEntry 15 }

tmnxRipNgInstImportPolicy2       OBJECT-TYPE
    SYNTAX      TPolicyStatementNameOrEmpty
    MAX-ACCESS  read-create
    STATUS      current
    DESCRIPTION
        "tmnxRipNgInstImportPolicy2 is import policy number 2 for the instance
         level."
    DEFVAL      { ''H }
    ::= { tmnxRipNgInstEntry 16 }

tmnxRipNgInstImportPolicy3       OBJECT-TYPE
    SYNTAX      TPolicyStatementNameOrEmpty
    MAX-ACCESS  read-create
    STATUS      current
    DESCRIPTION
        "tmnxRipNgInstImportPolicy3 is import policy number 3 for the instance
         level."
    DEFVAL      { ''H }
    ::= { tmnxRipNgInstEntry 17 }

tmnxRipNgInstImportPolicy4       OBJECT-TYPE
    SYNTAX      TPolicyStatementNameOrEmpty
    MAX-ACCESS  read-create
    STATUS      current
    DESCRIPTION
        "tmnxRipNgInstImportPolicy4 is import policy number 4 for the instance
         level."
    DEFVAL      { ''H }
    ::= { tmnxRipNgInstEntry 18 }

tmnxRipNgInstImportPolicy5       OBJECT-TYPE
    SYNTAX      TPolicyStatementNameOrEmpty
    MAX-ACCESS  read-create
    STATUS      current
    DESCRIPTION
        "tmnxRipNgInstImportPolicy5 is import policy number 5 for the instance
         level."
    DEFVAL      { ''H }
    ::= { tmnxRipNgInstEntry 19 }

tmnxRipNgInstExportPolicy1       OBJECT-TYPE
    SYNTAX      TPolicyStatementNameOrEmpty
    MAX-ACCESS  read-create
    STATUS      current
    DESCRIPTION
        "tmnxRipNgInstExportPolicy1 is export policy number 1 for the instance
         level."
    DEFVAL      { ''H }
    ::= { tmnxRipNgInstEntry 20 }

tmnxRipNgInstExportPolicy2       OBJECT-TYPE
    SYNTAX      TPolicyStatementNameOrEmpty
    MAX-ACCESS  read-create
    STATUS      current
    DESCRIPTION
        "tmnxRipNgInstExportPolicy2 is export policy number 2 for the instance
         level."
    DEFVAL      { ''H }
    ::= { tmnxRipNgInstEntry 21 }

tmnxRipNgInstExportPolicy3       OBJECT-TYPE
    SYNTAX      TPolicyStatementNameOrEmpty
    MAX-ACCESS  read-create
    STATUS      current
    DESCRIPTION
        "tmnxRipNgInstExportPolicy3 is export policy number 3 for the instance
         level."
    DEFVAL      { ''H }
    ::= { tmnxRipNgInstEntry 22 }

tmnxRipNgInstExportPolicy4       OBJECT-TYPE
    SYNTAX      TPolicyStatementNameOrEmpty
    MAX-ACCESS  read-create
    STATUS      current
    DESCRIPTION
        "tmnxRipNgInstExportPolicy4 is export policy number 4 for the instance
         level."
    DEFVAL      { ''H }
    ::= { tmnxRipNgInstEntry 23 }

tmnxRipNgInstExportPolicy5       OBJECT-TYPE
    SYNTAX      TPolicyStatementNameOrEmpty
    MAX-ACCESS  read-create
    STATUS      current
    DESCRIPTION
        "tmnxRipNgInstExportPolicy5 is export policy number 5 for the instance
         level."
    DEFVAL      { ''H }
    ::= { tmnxRipNgInstEntry 24 }

tmnxRipNgInstDescription         OBJECT-TYPE
    SYNTAX      TItemDescription
    MAX-ACCESS  read-create
    STATUS      current
    DESCRIPTION
        "tmnxRipNgInstDescription specifies a textual description for the RIP
         instance."
    DEFVAL      { ''H }
    ::= { tmnxRipNgInstEntry 25 }

tmnxRipNgInstAdminStatus         OBJECT-TYPE
    SYNTAX      TmnxAdminState
    MAX-ACCESS  read-create
    STATUS      current
    DESCRIPTION
        "The value of tmnxRipNgInstAdminStatus specifies the desired
         administrative state for this RIP/RIP-NG group or instance.

         If the RIP/RIP-NG instance entry object is set to outOfService, then
         all RIP groups and interfaces are shutdown operationally.

         If set to inService, the entity and all groups and interfaces below it
         are re-enabled operationally unless they have been administratively
         shutdown at the group or interface level."
    DEFVAL      { inService }
    ::= { tmnxRipNgInstEntry 26 }

tmnxRipNgInstOperStatus          OBJECT-TYPE
    SYNTAX      TmnxOperState
    MAX-ACCESS  read-only
    STATUS      current
    DESCRIPTION
        "The value of tmnxRipNgInstOperStatus indicates the current operational
         status of this RIP/RIP-NG instance"
    ::= { tmnxRipNgInstEntry 27 }

tmnxRipNgInstPropagateMetric     OBJECT-TYPE
    SYNTAX      TruthValue
    MAX-ACCESS  read-create
    STATUS      current
    DESCRIPTION
        "The value of tmnxRipNgInstPropagateMetric specifies whether the metric
         used by RIP/RIP-NG or OSPF protocol should be propagated to the Provider
         Edge (PE) routers as well, in addition to the Customer Equipment
         (CE) routers.  tmnxRipNgInstPropagateMetric only applies to VPRN
         RIP/RIP-NG instance and not the base router RIP/RIP-NG instance."
    DEFVAL      { false }
    ::= { tmnxRipNgInstEntry 28 }

tmnxRipNgInstExportLimit         OBJECT-TYPE
    SYNTAX      Unsigned32
    MAX-ACCESS  read-create
    STATUS      current
    DESCRIPTION
        "The value of tmnxRipNgInstExportLimit specifies the maximum number of
         routes or prefixes that can be exported into RIP/RIP-NG from the route
         table.

         A value of 0 indicates that the export limit for routes or prefixes
         has been disabled."
    DEFVAL      { 0 }
    ::= { tmnxRipNgInstEntry 29 }

tmnxRipNgInstExpLmtLogPct        OBJECT-TYPE
    SYNTAX      Unsigned32 (0..100)
    UNITS       "percentage"
    MAX-ACCESS  read-create
    STATUS      current
    DESCRIPTION
        "The value of tmnxRipNgInstExpLmtLogPct specifies the percentage of the
         export-limit, at which a warning log message and SNMP notification
         would be sent. This would only be a warning and additional routes will
         be learned up to 100% of tmnxRipNgInstExportLimit.

         A value of 0 indicates that tmnxRipNgInstExpLmtLogPct is disabled and
         no log message or SNMP notification would be sent."
    DEFVAL      { 0 }
    ::= { tmnxRipNgInstEntry 30 }

tmnxRipNgInstTotalExpRoutes      OBJECT-TYPE
    SYNTAX      Gauge32
    MAX-ACCESS  read-only
    STATUS      current
    DESCRIPTION
        "The value of tmnxRipNgInstTotalExpRoutes indicates the total number of
         routes exported into RIP/RIP-NG from the route table manager when an
         export policy is configured.

         Value of tmnxRipNgInstTotalExpRoutes would be 0 when no export policy
         is configured."
    ::= { tmnxRipNgInstEntry 31 }

tmnxRipNgGroupTable              OBJECT-TYPE
    SYNTAX      SEQUENCE OF TmnxRipNgGroupEntry
    MAX-ACCESS  not-accessible
    STATUS      current
    DESCRIPTION
        "tmnxRipNgGroupTable contains configuration information for each group
         of interfaces running RIP/RIP-NG."
    ::= { tmnxRipNgTableObjs 2 }

tmnxRipNgGroupEntry              OBJECT-TYPE
    SYNTAX      TmnxRipNgGroupEntry
    MAX-ACCESS  not-accessible
    STATUS      current
    DESCRIPTION
        "tmnxRipNgGroupEntry is an entry (conceptual row) in the
         tmnxRipNgGroupTable. Each entry represents the RIP/RIP-NG
         configuration of a group of interfaces on the router.

         Entries in this table can be created and deleted via SNMP SET
         operations to tmnxRipNgGroupRowStatus."
    INDEX       {
        vRtrID,
        tmnxRipNgInstVersion,
        tmnxRipNgGroupName
    }
    ::= { tmnxRipNgGroupTable 1 }

TmnxRipNgGroupEntry              ::= SEQUENCE
{
    tmnxRipNgGroupName               TNamedItem,
    tmnxRipNgGroupAuthType           TmnxRipNgAuthType,
    tmnxRipNgGroupAuthKey            TmnxRipNgAuthKey,
    tmnxRipNgGroupCheckZero          TruthValue,
    tmnxRipNgGroupMessageSize        TmnxRipNgMessageSize,
    tmnxRipNgGroupMetricIn           TmnxRipNgMetric,
    tmnxRipNgGroupMetricOut          TmnxRipNgMetric,
    tmnxRipNgGroupPreference         TmnxRipNgPreference,
    tmnxRipNgGroupReceive            TmnxRipNgReceive,
    tmnxRipNgGroupSend               TmnxRipNgSend,
    tmnxRipNgGroupSplitHorizon       TruthValue,
    tmnxRipNgGroupTimerFlush         TmnxRipNgTimerFlush,
    tmnxRipNgGroupTimerTimeout       TmnxRipNgTimerTimeout,
    tmnxRipNgGroupTimerUpdate        TmnxRipNgTimerUpdate,
    tmnxRipNgGroupImportPolicy1      TPolicyStatementNameOrEmpty,
    tmnxRipNgGroupImportPolicy2      TPolicyStatementNameOrEmpty,
    tmnxRipNgGroupImportPolicy3      TPolicyStatementNameOrEmpty,
    tmnxRipNgGroupImportPolicy4      TPolicyStatementNameOrEmpty,
    tmnxRipNgGroupImportPolicy5      TPolicyStatementNameOrEmpty,
    tmnxRipNgGroupExportPolicy1      TPolicyStatementNameOrEmpty,
    tmnxRipNgGroupExportPolicy2      TPolicyStatementNameOrEmpty,
    tmnxRipNgGroupExportPolicy3      TPolicyStatementNameOrEmpty,
    tmnxRipNgGroupExportPolicy4      TPolicyStatementNameOrEmpty,
    tmnxRipNgGroupExportPolicy5      TPolicyStatementNameOrEmpty,
    tmnxRipNgGroupDescription        TItemDescription,
    tmnxRipNgGroupInheritance        Unsigned32,
    tmnxRipNgGroupAdminStatus        TmnxAdminState,
    tmnxRipNgGroupOperStatus         TmnxOperState,
    tmnxRipNgGroupRowStatus          RowStatus
}

tmnxRipNgGroupName               OBJECT-TYPE
    SYNTAX      TNamedItem
    MAX-ACCESS  not-accessible
    STATUS      current
    DESCRIPTION
        "tmnxRipNgGroupName uniquely identifies a RIP/RIP-NG group for the
         router instance."
    ::= { tmnxRipNgGroupEntry 1 }

tmnxRipNgGroupAuthType           OBJECT-TYPE
    SYNTAX      TmnxRipNgAuthType
    MAX-ACCESS  read-create
    STATUS      current
    DESCRIPTION
        "tmnxRipNgGroupAuthType defines the type of authentication to be used
         for all the interfaces in this group."
    DEFVAL      { noAuthentication }
    ::= { tmnxRipNgGroupEntry 2 }

tmnxRipNgGroupAuthKey            OBJECT-TYPE
    SYNTAX      TmnxRipNgAuthKey
    MAX-ACCESS  read-create
    STATUS      current
    DESCRIPTION
        "tmnxRipNgGroupAuthKey is the authentication key that should be used
         for the interfaces in this group when tmnxRipNgInstAuthType has a
         value other than noAuthentication(1). Modifying the value of
         tmnxRipNgGroupAuthType does not modify the tmnxRipNgGroupAuthKey
         value. If a string shorter than 16 octets is supplied, it will be
         left-justified and padded to 16 octets, on the right, with nulls
         (0x00).

         Reading this object always results in an  OCTET STRING of
         length zero; authentication may not be bypassed by reading
         the MIB object."
    DEFVAL      { ''H }
    ::= { tmnxRipNgGroupEntry 3 }

tmnxRipNgGroupCheckZero          OBJECT-TYPE
    SYNTAX      TruthValue
    MAX-ACCESS  read-create
    STATUS      current
    DESCRIPTION
        "tmnxRipNgGroupCheckZero specifies whether RIP/RIP-NG updates received
         on interfaces in this group are checked for zero values in fields
         defined as Must-Be-Zero by the RIPv1 and v2 specifications."
    DEFVAL      { false }
    ::= { tmnxRipNgGroupEntry 4 }

tmnxRipNgGroupMessageSize        OBJECT-TYPE
    SYNTAX      TmnxRipNgMessageSize
    MAX-ACCESS  read-create
    STATUS      current
    DESCRIPTION
        "tmnxRipNgGroupMessageSize is the maximum number of routes that can be
         sent out per RIP/RIP-NG update message."
    DEFVAL      { 25 }
    ::= { tmnxRipNgGroupEntry 5 }

tmnxRipNgGroupMetricIn           OBJECT-TYPE
    SYNTAX      TmnxRipNgMetric
    MAX-ACCESS  read-create
    STATUS      current
    DESCRIPTION
        "tmnxRipNgGroupMetricIn is the value added to the metric of routes
         received on a RIP/RIP-NG interface which is a part of this group."
    DEFVAL      { 1 }
    ::= { tmnxRipNgGroupEntry 6 }

tmnxRipNgGroupMetricOut          OBJECT-TYPE
    SYNTAX      TmnxRipNgMetric
    MAX-ACCESS  read-create
    STATUS      current
    DESCRIPTION
        "tmnxRipNgGroupMetricOut is the value added to the metric of routes
         exported into RIP/RIP-NG and advertised out on RIP/RIP-NG interfaces
         in this group."
    DEFVAL      { 1 }
    ::= { tmnxRipNgGroupEntry 7 }

tmnxRipNgGroupPreference         OBJECT-TYPE
    SYNTAX      TmnxRipNgPreference
    MAX-ACCESS  read-create
    STATUS      current
    DESCRIPTION
        "tmnxRipNgGroupPreference is the route preference to be assigned to
         RIP/RIP-NG routes received on interfaces that are a part of this
         group. This value may be overridden via route policies."
    DEFVAL      { 100 }
    ::= { tmnxRipNgGroupEntry 8 }

tmnxRipNgGroupReceive            OBJECT-TYPE
    SYNTAX      TmnxRipNgReceive
    MAX-ACCESS  read-create
    STATUS      current
    DESCRIPTION
        "tmnxRipNgGroupReceive specifies which version of RIP/RIP-NG updates
         are to be accepted for the group of interfaces."
    DEFVAL      { ripNg1 }
    ::= { tmnxRipNgGroupEntry 9 }

tmnxRipNgGroupSend               OBJECT-TYPE
    SYNTAX      TmnxRipNgSend
    MAX-ACCESS  read-create
    STATUS      current
    DESCRIPTION
        "tmnxRipNgGroupSend specifies the version to be used for sending
         RIP/RIP-NG updates on interfaces within the group."
    DEFVAL      { ripNgVersion1 }
    ::= { tmnxRipNgGroupEntry 10 }

tmnxRipNgGroupSplitHorizon       OBJECT-TYPE
    SYNTAX      TruthValue
    MAX-ACCESS  read-create
    STATUS      current
    DESCRIPTION
        "tmnxRipNgGroupSplitHorizon specifies whether split horizon scheme is
         to be used when sending updates on interfaces which are a part of the
         group."
    DEFVAL      { true }
    ::= { tmnxRipNgGroupEntry 11 }

tmnxRipNgGroupTimerFlush         OBJECT-TYPE
    SYNTAX      TmnxRipNgTimerFlush
    UNITS       "seconds"
    MAX-ACCESS  read-create
    STATUS      current
    DESCRIPTION
        "tmnxRipNgGroupTimerFlush is the number of seconds after a route has
         been declared invalid that it is flushed from the route database."
    DEFVAL      { 120 }
    ::= { tmnxRipNgGroupEntry 12 }

tmnxRipNgGroupTimerTimeout       OBJECT-TYPE
    SYNTAX      TmnxRipNgTimerTimeout
    UNITS       "seconds"
    MAX-ACCESS  read-create
    STATUS      current
    DESCRIPTION
        "tmnxRipNgGroupTimerTimeout is the number of seconds after a route has
         been discovered or last updated that it is declared invalid in the
         route database."
    DEFVAL      { 180 }
    ::= { tmnxRipNgGroupEntry 13 }

tmnxRipNgGroupTimerUpdate        OBJECT-TYPE
    SYNTAX      TmnxRipNgTimerUpdate
    UNITS       "seconds"
    MAX-ACCESS  read-create
    STATUS      current
    DESCRIPTION
        "tmnxRipNgGroupTimerUpdate determines how often updates are sent."
    DEFVAL      { 30 }
    ::= { tmnxRipNgGroupEntry 14 }

tmnxRipNgGroupImportPolicy1      OBJECT-TYPE
    SYNTAX      TPolicyStatementNameOrEmpty
    MAX-ACCESS  read-create
    STATUS      current
    DESCRIPTION
        "tmnxRipNgGroupImportPolicy1 is import policy number 1 for the group
         level."
    DEFVAL      { ''H }
    ::= { tmnxRipNgGroupEntry 15 }

tmnxRipNgGroupImportPolicy2      OBJECT-TYPE
    SYNTAX      TPolicyStatementNameOrEmpty
    MAX-ACCESS  read-create
    STATUS      current
    DESCRIPTION
        "tmnxRipNgGroupImportPolicy2 is import policy number 2 for the group
         level."
    DEFVAL      { ''H }
    ::= { tmnxRipNgGroupEntry 16 }

tmnxRipNgGroupImportPolicy3      OBJECT-TYPE
    SYNTAX      TPolicyStatementNameOrEmpty
    MAX-ACCESS  read-create
    STATUS      current
    DESCRIPTION
        "tmnxRipNgGroupImportPolicy3 is import policy number 3 for the group
         level."
    DEFVAL      { ''H }
    ::= { tmnxRipNgGroupEntry 17 }

tmnxRipNgGroupImportPolicy4      OBJECT-TYPE
    SYNTAX      TPolicyStatementNameOrEmpty
    MAX-ACCESS  read-create
    STATUS      current
    DESCRIPTION
        "tmnxRipNgGroupImportPolicy4 is import policy number 4 for the group
         level."
    DEFVAL      { ''H }
    ::= { tmnxRipNgGroupEntry 18 }

tmnxRipNgGroupImportPolicy5      OBJECT-TYPE
    SYNTAX      TPolicyStatementNameOrEmpty
    MAX-ACCESS  read-create
    STATUS      current
    DESCRIPTION
        "tmnxRipNgGroupImportPolicy5 is import policy number 5 for the group
         level."
    DEFVAL      { ''H }
    ::= { tmnxRipNgGroupEntry 19 }

tmnxRipNgGroupExportPolicy1      OBJECT-TYPE
    SYNTAX      TPolicyStatementNameOrEmpty
    MAX-ACCESS  read-create
    STATUS      current
    DESCRIPTION
        "tmnxRipNgGroupExportPolicy1 is export policy number 1 for the group
         level."
    DEFVAL      { ''H }
    ::= { tmnxRipNgGroupEntry 20 }

tmnxRipNgGroupExportPolicy2      OBJECT-TYPE
    SYNTAX      TPolicyStatementNameOrEmpty
    MAX-ACCESS  read-create
    STATUS      current
    DESCRIPTION
        "tmnxRipNgGroupExportPolicy2 is export policy number 2 for the group
         level."
    DEFVAL      { ''H }
    ::= { tmnxRipNgGroupEntry 21 }

tmnxRipNgGroupExportPolicy3      OBJECT-TYPE
    SYNTAX      TPolicyStatementNameOrEmpty
    MAX-ACCESS  read-create
    STATUS      current
    DESCRIPTION
        "tmnxRipNgGroupExportPolicy3 is export policy number 3 for the group
         level."
    DEFVAL      { ''H }
    ::= { tmnxRipNgGroupEntry 22 }

tmnxRipNgGroupExportPolicy4      OBJECT-TYPE
    SYNTAX      TPolicyStatementNameOrEmpty
    MAX-ACCESS  read-create
    STATUS      current
    DESCRIPTION
        "tmnxRipNgGroupExportPolicy4 is export policy number 4 for the group
         level."
    DEFVAL      { ''H }
    ::= { tmnxRipNgGroupEntry 23 }

tmnxRipNgGroupExportPolicy5      OBJECT-TYPE
    SYNTAX      TPolicyStatementNameOrEmpty
    MAX-ACCESS  read-create
    STATUS      current
    DESCRIPTION
        "tmnxRipNgGroupExportPolicy5 is export policy number 5 for the group
         level."
    DEFVAL      { ''H }
    ::= { tmnxRipNgGroupEntry 24 }

tmnxRipNgGroupDescription        OBJECT-TYPE
    SYNTAX      TItemDescription
    MAX-ACCESS  read-create
    STATUS      current
    DESCRIPTION
        "tmnxRipNgGroupDescription specifies a textual description for the
         group."
    DEFVAL      { ''H }
    ::= { tmnxRipNgGroupEntry 25 }

tmnxRipNgGroupInheritance        OBJECT-TYPE
    SYNTAX      Unsigned32
    MAX-ACCESS  read-create
    STATUS      current
    DESCRIPTION
        "tmnxRipNgGroupInheritance controls, for the objects listed below,
         whether to use the administratively set value for that object or
         objects, or to use the corresponding value or values from the
         tmnxRipNgInstTable entry that represents the RIP/RIP-NG instance for
         this router.

         This object is a bit-mask, and the bits correspond to the following
         objects:

         tmnxRipNgGroupAuthType            0x00000001
         tmnxRipNgGroupAuthKey             0x00000002
         tmnxRipNgGroupSend                0x00000004
         tmnxRipNgGroupReceive             0x00000008
         tmnxRipNgGroupCheckZero           0x00000010
         tmnxRipNgGroupMessageSize         0x00000020
         tmnxRipNgGroupMetricIn            0x00000040
         tmnxRipNgGroupMetricOut           0x00000080
         tmnxRipNgGroupPreference          0x00000100
         tmnxRipNgGroupSplitHorizon        0x00000200

         tmnxRipNgGroupTimerFlush          0x00000400
         tmnxRipNgGroupTimerTimeout
         tmnxRipNgGroupTimerUpdate

         tmnxRipNgGroupImportPolicy1       0x00000800
         tmnxRipNgGroupImportPolicy2
         tmnxRipNgGroupImportPolicy3
         tmnxRipNgGroupImportPolicy4
         tmnxRipNgGroupImportPolicy5

         tmnxRipNgGroupExportPolicy1       0x00001000
         tmnxRipNgGroupExportPolicy2
         tmnxRipNgGroupExportPolicy3
         tmnxRipNgGroupExportPolicy4
         tmnxRipNgGroupExportPolicy5

         When the bit for an object is set to one, then the object's
         value is whatever the DEFVAL or most recently SET value is.
         The corresponding mask bit will be changed to one when SNMP
         SET is performed on any of the inherited objects ( tmnxRipNgGroupSend,
         tmnxRipNgGroupAuthType,  etc ).

         When the bit for an object is set to zero, then the object's value is
         inherited from the tmnxRipNgInstEntry that represents the RIP instance
         for this router.

         Non mask bits will always have value of zero, and any attempt to
         change the value will be silently discarded.

         The bit, timer (10), applies this rule to all of the following
         objects:
             tmnxRipNgGroupTimerFlush
             tmnxRipNgGroupTimerTimeout
             tmnxRipNgGroupTimerUpdate

         The bit, importPolicy (11), applies this rule to all of the
         following objects:
             tmnxRipNgGroupImportPolicy1,
             tmnxRipNgGroupImportPolicy2,
             tmnxRipNgGroupImportPolicy3,
             tmnxRipNgGroupImportPolicy4,
             tmnxRipNgGroupImportPolicy5

         The bit, exportPolicy (12), applies this rule to all of the
         following objects:
             tmnxRipNgGroupExportPolicy1,
             tmnxRipNgGroupExportPolicy2,
             tmnxRipNgGroupExportPolicy3,
             tmnxRipNgGroupExportPolicy4,
             tmnxRipNgGroupExportPolicy5"
    DEFVAL      { 0 }
    ::= { tmnxRipNgGroupEntry 26 }

tmnxRipNgGroupAdminStatus        OBJECT-TYPE
    SYNTAX      TmnxAdminState
    MAX-ACCESS  read-create
    STATUS      current
    DESCRIPTION
        "The value of tmnxRipNgGroupAdminStatus specifies the desired
         administrative state for this RIP/RIP-NG group or instance.

         If a RIP group entry object is set to outOfService, then all
         interfaces in the group are shutdown operationally.

         If set to inService, all interfaces within the group are re-enabled
         operationally unless they have been administratively shutdown at the
         interface level."
    DEFVAL      { inService }
    ::= { tmnxRipNgGroupEntry 27 }

tmnxRipNgGroupOperStatus         OBJECT-TYPE
    SYNTAX      TmnxOperState
    MAX-ACCESS  read-only
    STATUS      current
    DESCRIPTION
        "The value of tmnxRipNgGroupOperStatus indicates the current
         operational status of this RIP group."
    ::= { tmnxRipNgGroupEntry 28 }

tmnxRipNgGroupRowStatus          OBJECT-TYPE
    SYNTAX      RowStatus
    MAX-ACCESS  read-create
    STATUS      current
    DESCRIPTION
        "tmnxRipNgGroupRowStatus controls the creation and deletion of rows in
         this table.

         To create a row in the tmnxRipNgGroupTable, set
         tmnxRipNgGroupRowStatus to createAndGo(4). All objects will take on
         default values and the agent will change tmnxRipNgGroupRowStatus to
         active(1).

         To delete a row in the tmnxRipNgGroupTable, set
         tmnxRipNgGroupRowStatus to delete(6). However the row can only be
         deleted the group has been shutdown (i.e. value of
         tmnxRipNgGroupAdminStatus is outOfService)."
    ::= { tmnxRipNgGroupEntry 29 }

tmnxRipNgIfTable                 OBJECT-TYPE
    SYNTAX      SEQUENCE OF TmnxRipNgIfEntry
    MAX-ACCESS  not-accessible
    STATUS      current
    DESCRIPTION
        "tmnxRipNgIfTable contains configuration information for each interface
         running RIP/RIP-NG."
    ::= { tmnxRipNgTableObjs 3 }

tmnxRipNgIfEntry                 OBJECT-TYPE
    SYNTAX      TmnxRipNgIfEntry
    MAX-ACCESS  not-accessible
    STATUS      current
    DESCRIPTION
        "tmnxRipNgIfEntry is an entry (conceptual row) in the tmnxRipNgIfTable.
         Each row entry represents an interface on the router that participates
         in the RIP/RIP-NG protocol.

         Entries in this table can be created and deleted via SNMP SET
         operations to tmnxRipNgIfRowStatus."
    INDEX       {
        vRtrID,
        tmnxRipNgInstVersion,
        vRtrIfIndex
    }
    ::= { tmnxRipNgIfTable 1 }

TmnxRipNgIfEntry                 ::= SEQUENCE
{
    tmnxRipNgIfGroupName             TNamedItem,
    tmnxRipNgIfAuthType              TmnxRipNgAuthType,
    tmnxRipNgIfAuthKey               TmnxRipNgAuthKey,
    tmnxRipNgIfCheckZero             TruthValue,
    tmnxRipNgIfMessageSize           TmnxRipNgMessageSize,
    tmnxRipNgIfMetricIn              TmnxRipNgMetric,
    tmnxRipNgIfMetricOut             TmnxRipNgMetric,
    tmnxRipNgIfPreference            TmnxRipNgPreference,
    tmnxRipNgIfReceive               TmnxRipNgReceive,
    tmnxRipNgIfSend                  TmnxRipNgSend,
    tmnxRipNgIfSplitHorizon          TruthValue,
    tmnxRipNgIfTimerFlush            TmnxRipNgTimerFlush,
    tmnxRipNgIfTimerTimeout          TmnxRipNgTimerTimeout,
    tmnxRipNgIfTimerUpdate           TmnxRipNgTimerUpdate,
    tmnxRipNgIfImportPolicy1         TPolicyStatementNameOrEmpty,
    tmnxRipNgIfImportPolicy2         TPolicyStatementNameOrEmpty,
    tmnxRipNgIfImportPolicy3         TPolicyStatementNameOrEmpty,
    tmnxRipNgIfImportPolicy4         TPolicyStatementNameOrEmpty,
    tmnxRipNgIfImportPolicy5         TPolicyStatementNameOrEmpty,
    tmnxRipNgIfExportPolicy1         TPolicyStatementNameOrEmpty,
    tmnxRipNgIfExportPolicy2         TPolicyStatementNameOrEmpty,
    tmnxRipNgIfExportPolicy3         TPolicyStatementNameOrEmpty,
    tmnxRipNgIfExportPolicy4         TPolicyStatementNameOrEmpty,
    tmnxRipNgIfExportPolicy5         TPolicyStatementNameOrEmpty,
    tmnxRipNgIfDescription           TItemDescription,
    tmnxRipNgIfInheritance           Unsigned32,
    tmnxRipNgIfAdminStatus           TmnxAdminState,
    tmnxRipNgIfOperStatus            TmnxOperState,
    tmnxRipNgIfRowStatus             RowStatus
}

tmnxRipNgIfGroupName             OBJECT-TYPE
    SYNTAX      TNamedItem
    MAX-ACCESS  read-create
    STATUS      current
    DESCRIPTION
        "tmnxRipNgIfGroupName is an index into the tmnxRipNgGroupTable. It
         identifies the RIP/RIP-NG group to which this interface belongs. This
         object must be set to an existing group name before the row status can
         be changed to 'active'."
    ::= { tmnxRipNgIfEntry 1 }

tmnxRipNgIfAuthType              OBJECT-TYPE
    SYNTAX      TmnxRipNgAuthType
    MAX-ACCESS  read-create
    STATUS      current
    DESCRIPTION
        "tmnxRipNgIfAuthType defines the type of authentication to be used for
         this interface."
    DEFVAL      { noAuthentication }
    ::= { tmnxRipNgIfEntry 2 }

tmnxRipNgIfAuthKey               OBJECT-TYPE
    SYNTAX      TmnxRipNgAuthKey
    MAX-ACCESS  read-create
    STATUS      current
    DESCRIPTION
        "tmnxRipNgIfAuthKey is the authentication key that should be used for
         this interface when tmnxRipNgInstAuthType has a value other than
         noAuthentication(1). Modifying the value of tmnxRipNgIfAuthType does
         not modify the tmnxRipNgIfAuthKey value. If a string shorter than 16
         octets is supplied, it will be left-justified and padded to 16 octets,
         on the right, with nulls (0x00).

         Reading this object always results in an  OCTET STRING of
         length zero; authentication may not be bypassed by reading
         the MIB object."
    DEFVAL      { ''H }
    ::= { tmnxRipNgIfEntry 3 }

tmnxRipNgIfCheckZero             OBJECT-TYPE
    SYNTAX      TruthValue
    MAX-ACCESS  read-create
    STATUS      current
    DESCRIPTION
        "tmnxRipNgIfCheckZero specifies whether RIP updates received on this
         interface are checked for zero values in fields defined as
         Must-Be-Zero by the RIPv1 and v2 specifications."
    DEFVAL      { false }
    ::= { tmnxRipNgIfEntry 4 }

tmnxRipNgIfMessageSize           OBJECT-TYPE
    SYNTAX      TmnxRipNgMessageSize
    MAX-ACCESS  read-create
    STATUS      current
    DESCRIPTION
        "tmnxRipNgIfMessageSize is the maximum number of routes that can be
         sent out per RIP/RIP-NG update message."
    DEFVAL      { 25 }
    ::= { tmnxRipNgIfEntry 5 }

tmnxRipNgIfMetricIn              OBJECT-TYPE
    SYNTAX      TmnxRipNgMetric
    MAX-ACCESS  read-create
    STATUS      current
    DESCRIPTION
        "tmnxRipNgIfMetricIn is the value added to the metric of routes
         received on this RIP/RIP-NG interface."
    DEFVAL      { 1 }
    ::= { tmnxRipNgIfEntry 6 }

tmnxRipNgIfMetricOut             OBJECT-TYPE
    SYNTAX      TmnxRipNgMetric
    MAX-ACCESS  read-create
    STATUS      current
    DESCRIPTION
        "tmnxRipNgIfMetricOut is the value added to the metric of routes
         exported into RIP/RIP-NG and advertised out on this RIP/RIP-NG
         interface."
    DEFVAL      { 1 }
    ::= { tmnxRipNgIfEntry 7 }

tmnxRipNgIfPreference            OBJECT-TYPE
    SYNTAX      TmnxRipNgPreference
    MAX-ACCESS  read-create
    STATUS      current
    DESCRIPTION
        "tmnxRipNgIfPreference is the route preference to be assigned to routes
         received on this interface. This value may be overridden via route
         policies."
    DEFVAL      { 100 }
    ::= { tmnxRipNgIfEntry 8 }

tmnxRipNgIfReceive               OBJECT-TYPE
    SYNTAX      TmnxRipNgReceive
    MAX-ACCESS  read-create
    STATUS      current
    DESCRIPTION
        "tmnxRipNgIfReceive specifies which version of RIP/RIP-NG updates are
         to be accepted on the interface."
    DEFVAL      { ripNg1 }
    ::= { tmnxRipNgIfEntry 9 }

tmnxRipNgIfSend                  OBJECT-TYPE
    SYNTAX      TmnxRipNgSend
    MAX-ACCESS  read-create
    STATUS      current
    DESCRIPTION
        "tmnxRipNgIfSend specifies the version to be used for sending
         RIP/RIP-NG updates on the interface."
    DEFVAL      { ripNgVersion1 }
    ::= { tmnxRipNgIfEntry 10 }

tmnxRipNgIfSplitHorizon          OBJECT-TYPE
    SYNTAX      TruthValue
    MAX-ACCESS  read-create
    STATUS      current
    DESCRIPTION
        "tmnxRipNgIfSplitHorizon specifies whether split horizon scheme is is
         to be used when sending updates on the interface."
    DEFVAL      { true }
    ::= { tmnxRipNgIfEntry 11 }

tmnxRipNgIfTimerFlush            OBJECT-TYPE
    SYNTAX      TmnxRipNgTimerFlush
    UNITS       "seconds"
    MAX-ACCESS  read-create
    STATUS      current
    DESCRIPTION
        "tmnxRipNgIfTimerFlush specifies the number of seconds after a route
         has been declared invalid that it is flushed from the route database."
    DEFVAL      { 120 }
    ::= { tmnxRipNgIfEntry 12 }

tmnxRipNgIfTimerTimeout          OBJECT-TYPE
    SYNTAX      TmnxRipNgTimerTimeout
    UNITS       "seconds"
    MAX-ACCESS  read-create
    STATUS      current
    DESCRIPTION
        "tmnxRipNgIfTimerTimeout specifies the number of seconds after a route
         has been discovered or last updated that it is declared invalid in the
         route database."
    DEFVAL      { 180 }
    ::= { tmnxRipNgIfEntry 13 }

tmnxRipNgIfTimerUpdate           OBJECT-TYPE
    SYNTAX      TmnxRipNgTimerUpdate
    UNITS       "seconds"
    MAX-ACCESS  read-create
    STATUS      current
    DESCRIPTION
        "tmnxRipNgIfTimerUpdate specifies how often updates are sent."
    DEFVAL      { 30 }
    ::= { tmnxRipNgIfEntry 14 }

tmnxRipNgIfImportPolicy1         OBJECT-TYPE
    SYNTAX      TPolicyStatementNameOrEmpty
    MAX-ACCESS  read-create
    STATUS      current
    DESCRIPTION
        "tmnxRipNgIfImportPolicy1 is import policy number 1 for the interface."
    DEFVAL      { ''H }
    ::= { tmnxRipNgIfEntry 15 }

tmnxRipNgIfImportPolicy2         OBJECT-TYPE
    SYNTAX      TPolicyStatementNameOrEmpty
    MAX-ACCESS  read-create
    STATUS      current
    DESCRIPTION
        "tmnxRipNgIfImportPolicy2 is import policy number 2 for the interface."
    DEFVAL      { ''H }
    ::= { tmnxRipNgIfEntry 16 }

tmnxRipNgIfImportPolicy3         OBJECT-TYPE
    SYNTAX      TPolicyStatementNameOrEmpty
    MAX-ACCESS  read-create
    STATUS      current
    DESCRIPTION
        "tmnxRipNgIfImportPolicy3 is import policy number 3 for the interface."
    DEFVAL      { ''H }
    ::= { tmnxRipNgIfEntry 17 }

tmnxRipNgIfImportPolicy4         OBJECT-TYPE
    SYNTAX      TPolicyStatementNameOrEmpty
    MAX-ACCESS  read-create
    STATUS      current
    DESCRIPTION
        "tmnxRipNgIfImportPolicy4 is import policy number 4 for the interface."
    DEFVAL      { ''H }
    ::= { tmnxRipNgIfEntry 18 }

tmnxRipNgIfImportPolicy5         OBJECT-TYPE
    SYNTAX      TPolicyStatementNameOrEmpty
    MAX-ACCESS  read-create
    STATUS      current
    DESCRIPTION
        "tmnxRipNgIfImportPolicy5 is import policy number 5 for the interface."
    DEFVAL      { ''H }
    ::= { tmnxRipNgIfEntry 19 }

tmnxRipNgIfExportPolicy1         OBJECT-TYPE
    SYNTAX      TPolicyStatementNameOrEmpty
    MAX-ACCESS  read-create
    STATUS      current
    DESCRIPTION
        "tmnxRipNgIfExportPolicy1 is export policy number 1 for the interface."
    DEFVAL      { ''H }
    ::= { tmnxRipNgIfEntry 20 }

tmnxRipNgIfExportPolicy2         OBJECT-TYPE
    SYNTAX      TPolicyStatementNameOrEmpty
    MAX-ACCESS  read-create
    STATUS      current
    DESCRIPTION
        "tmnxRipNgIfExportPolicy2 is export policy number 2 for the interface."
    DEFVAL      { ''H }
    ::= { tmnxRipNgIfEntry 21 }

tmnxRipNgIfExportPolicy3         OBJECT-TYPE
    SYNTAX      TPolicyStatementNameOrEmpty
    MAX-ACCESS  read-create
    STATUS      current
    DESCRIPTION
        "tmnxRipNgIfExportPolicy3 is export policy number 3 for the interface."
    DEFVAL      { ''H }
    ::= { tmnxRipNgIfEntry 22 }

tmnxRipNgIfExportPolicy4         OBJECT-TYPE
    SYNTAX      TPolicyStatementNameOrEmpty
    MAX-ACCESS  read-create
    STATUS      current
    DESCRIPTION
        "tmnxRipNgIfExportPolicy4 is export policy number 4 for the interface."
    DEFVAL      { ''H }
    ::= { tmnxRipNgIfEntry 23 }

tmnxRipNgIfExportPolicy5         OBJECT-TYPE
    SYNTAX      TPolicyStatementNameOrEmpty
    MAX-ACCESS  read-create
    STATUS      current
    DESCRIPTION
        "tmnxRipNgIfExportPolicy5 is export policy number 5 for the interface."
    DEFVAL      { ''H }
    ::= { tmnxRipNgIfEntry 24 }

tmnxRipNgIfDescription           OBJECT-TYPE
    SYNTAX      TItemDescription
    MAX-ACCESS  read-create
    STATUS      current
    DESCRIPTION
        "tmnxRipNgIfDescription specifies a textual description for the
         interface."
    DEFVAL      { ''H }
    ::= { tmnxRipNgIfEntry 25 }

tmnxRipNgIfInheritance           OBJECT-TYPE
    SYNTAX      Unsigned32
    MAX-ACCESS  read-create
    STATUS      current
    DESCRIPTION
        "tmnxRipNgIfInheritance controls, for the objects listed below, whether
         to use the administratively set value for that object or objects or to
         use the corresponding value or values from the tmnxRipNgGroupTable
         entry that represents the RIP/RIP-NG group to which this interface
         belongs.

         This object is a bit-mask, and the bits correspond to the following
         objects:

         tmnxRipNgIfAuthType       0x00000001
         tmnxRipNgIfAuthKey        0x00000002
         tmnxRipNgIfSend           0x00000004
         tmnxRipNgIfReceive        0x00000008
         tmnxRipNgIfCheckZero      0x00000010
         tmnxRipNgIfMessageSize    0x00000020
         tmnxRipNgIfMetricIn       0x00000040
         tmnxRipNgIfMetricOut      0x00000080
         tmnxRipNgIfPreference     0x00000100
         tmnxRipNgIfSplitHorizon   0x00000200

         tmnxRipNgIfTimerFlush     0x00000400
         tmnxRipNgIfTimerTimeout
         tmnxRipNgIfTimerUpdate

         tmnxRipNgIfImportPolicy1  0x00000800
         tmnxRipNgIfImportPolicy2
         tmnxRipNgIfImportPolicy3
         tmnxRipNgIfImportPolicy4
         tmnxRipNgIfImportPolicy5

         tmnxRipNgIfExportPolicy1  0x00001000
         tmnxRipNgIfExportPolicy2
         tmnxRipNgIfExportPolicy3
         tmnxRipNgIfExportPolicy4
         tmnxRipNgIfExportPolicy5

         When the bit for an object is set to one, then the object's
         value is whatever the DEFVAL or most recently SET value is.
         The corresponding mask bit will be changed to one when SNMP
         SET is performed on any of the inherited objects ( tmnxRipNgIfSend,
         tmnxRipNgIfAuthType,  etc ).

         When the bit for an object is set to zero, then the object's value is
         inherited from the corresponding object in tmnxRipNgGroupTable whose
         index is the value of tmnxRipNgIfGroupName.

         Non mask bits will always have value of zero, and any attempt to
         change the value will be silently discarded.

         The bit, 'timer(10)', applies this rule to all of the following
         objects:
             tmnxRipNgIfTimerFlush
             tmnxRipNgIfTimerTimeout
             tmnxRipNgIfTimerUpdate

         The bit, 'importPolicy(11)', applies this rule to all of the
         following objects:
             tmnxRipNgIfImportPolicy1,
             tmnxRipNgIfImportPolicy2,
             tmnxRipNgIfImportPolicy3,
             tmnxRipNgIfImportPolicy4,
             tmnxRipNgIfImportPolicy5

         The bit, 'exportPolicy(12)', applies this rule to all of the
         following objects:
             tmnxRipNgIfExportPolicy1,
             tmnxRipNgIfExportPolicy2,
             tmnxRipNgIfExportPolicy3,
             tmnxRipNgIfExportPolicy4,
             tmnxRipNgIfExportPolicy5"
    DEFVAL      { 0 }
    ::= { tmnxRipNgIfEntry 26 }

tmnxRipNgIfAdminStatus           OBJECT-TYPE
    SYNTAX      TmnxAdminState
    MAX-ACCESS  read-create
    STATUS      current
    DESCRIPTION
        "The value of tmnxRipNgIfAdminStatus specifies the desired
         administrative state for this RIP/RIP-NG interface."
    DEFVAL      { inService }
    ::= { tmnxRipNgIfEntry 27 }

tmnxRipNgIfOperStatus            OBJECT-TYPE
    SYNTAX      TmnxOperState
    MAX-ACCESS  read-only
    STATUS      current
    DESCRIPTION
        "The value of tmnxRipNgIfOperStatus indicates the current operational
         status of this RIP/RIP-NG interface."
    DEFVAL      { inService }
    ::= { tmnxRipNgIfEntry 28 }

tmnxRipNgIfRowStatus             OBJECT-TYPE
    SYNTAX      RowStatus
    MAX-ACCESS  read-create
    STATUS      current
    DESCRIPTION
        "tmnxRipNgIfRowStatus controls the creation and deletion of rows in
         this table.

         To create a row in the tmnxRipNgIfTable, set tmnxRipNgIfRowStatus to
         createAndGo(4). tmnxRipNgIfGroupName for the interface must be set to
         the name of an existing group in the tmnxRipNgGroupTable before the
         row status can be set to active(1).

         To delete a row in the tmnxRipNgIfTable, set tmnxRipNgIfRowStatus to
         delete(6). However the row can only be deleted the group has been
         shutdown (i.e. value of tmnxRipNgIfAdminStatus is outOfService)."
    ::= { tmnxRipNgIfEntry 29 }

tmnxRipNgRouteTable              OBJECT-TYPE
    SYNTAX      SEQUENCE OF TmnxRipNgRouteEntry
    MAX-ACCESS  not-accessible
    STATUS      current
    DESCRIPTION
        "The tmnxRipNgRouteTable has an entry for each route in the RIP/RIP-NG
         database."
    ::= { tmnxRipNgTableObjs 4 }

tmnxRipNgRouteEntry              OBJECT-TYPE
    SYNTAX      TmnxRipNgRouteEntry
    MAX-ACCESS  not-accessible
    STATUS      current
    DESCRIPTION
        "tmnxRipNgRouteEntry is an entry (conceptual row) in the
         tmnxRipNgRouteTable.  Each entry represents information for
         a RIP/RIP-NG route received from a peer."
    INDEX       {
        vRtrID,
        tmnxRipNgInstVersion,
        tmnxRipNgRouteDestAddrType,
        tmnxRipNgRouteDestAddress,
        tmnxRipNgRouteMaskLength,
        tmnxRipNgRouteIfIndex,
        tmnxRipNgRoutePeerAddrType,
        tmnxRipNgRoutePeerAddress
    }
    ::= { tmnxRipNgRouteTable 1 }

TmnxRipNgRouteEntry              ::= SEQUENCE
{
    tmnxRipNgRouteDestAddrType       InetAddressType,
    tmnxRipNgRouteDestAddress        InetAddress,
    tmnxRipNgRouteMaskLength         InetAddressPrefixLength,
    tmnxRipNgRouteIfIndex            InterfaceIndex,
    tmnxRipNgRoutePeerAddrType       InetAddressType,
    tmnxRipNgRoutePeerAddress        InetAddress,
    tmnxRipNgRouteNHAddrType         InetAddressType,
    tmnxRipNgRouteNHAddress          InetAddress,
    tmnxRipNgRouteMetric             TmnxRipNgMetric,
    tmnxRipNgRouteTag                RouteTag,
    tmnxRipNgRouteStatus             INTEGER,
    tmnxRipNgRouteTimerRemaining     Unsigned32,
    tmnxRipNgRouteFC                 TNamedItemOrEmpty,
    tmnxRipNgRouteFCPriority         TPriorityOrUndefined
}

tmnxRipNgRouteDestAddrType       OBJECT-TYPE
    SYNTAX      InetAddressType
    MAX-ACCESS  not-accessible
    STATUS      current
    DESCRIPTION
        "The value of tmnxRipNgRouteDestAddrType indicates the type of address
         specified by tmnxRipNgRouteDestAddress"
    ::= { tmnxRipNgRouteEntry 1 }

tmnxRipNgRouteDestAddress        OBJECT-TYPE
    SYNTAX      InetAddress (SIZE (4|16))
    MAX-ACCESS  not-accessible
    STATUS      current
    DESCRIPTION
        "tmnxRipNgRouteDestAddress is the destination IP address of the
         RIP/RIP-NG route."
    ::= { tmnxRipNgRouteEntry 2 }

tmnxRipNgRouteMaskLength         OBJECT-TYPE
    SYNTAX      InetAddressPrefixLength (0..128)
    MAX-ACCESS  not-accessible
    STATUS      current
    DESCRIPTION
        "tmnxRipNgRouteMaskLength contains the subnet/prefix masking length
         which is applied to tmnxRipNgRouteDestAddress to yield the non-host
         portion of the destination address.

         If this field is zero, then no masking length has been included."
    ::= { tmnxRipNgRouteEntry 3 }

tmnxRipNgRouteIfIndex            OBJECT-TYPE
    SYNTAX      InterfaceIndex
    MAX-ACCESS  not-accessible
    STATUS      current
    DESCRIPTION
        "tmnxRipNgRouteIfIndex specifies the index of the interface on which
         this route was received."
    ::= { tmnxRipNgRouteEntry 4 }

tmnxRipNgRoutePeerAddrType       OBJECT-TYPE
    SYNTAX      InetAddressType
    MAX-ACCESS  not-accessible
    STATUS      current
    DESCRIPTION
        "The value of tmnxRipNgRoutePeerAddrType indicates the type of address
         specified by tmnxRipNgRoutePeerAddress"
    ::= { tmnxRipNgRouteEntry 5 }

tmnxRipNgRoutePeerAddress        OBJECT-TYPE
    SYNTAX      InetAddress (SIZE (4|16))
    MAX-ACCESS  not-accessible
    STATUS      current
    DESCRIPTION
        "tmnxRipNgRoutePeerAddress specifies the IP address of the peer from
         whom this route was received."
    ::= { tmnxRipNgRouteEntry 6 }

tmnxRipNgRouteNHAddrType         OBJECT-TYPE
    SYNTAX      InetAddressType
    MAX-ACCESS  read-only
    STATUS      current
    DESCRIPTION
        "The value of tmnxRipNgRouteNHAddrType indicates the type of address
         specified by tmnxRipNgRouteNHAddress"
    ::= { tmnxRipNgRouteEntry 7 }

tmnxRipNgRouteNHAddress          OBJECT-TYPE
    SYNTAX      InetAddress (SIZE (0|4|16))
    MAX-ACCESS  read-only
    STATUS      current
    DESCRIPTION
        "tmnxRipNgRouteNHAddress indicates the IP address in the Next Hop field
         of the RIPv2 update received for this route. The Next Hop field is the
         immediate next hop IP address to which packets to the destination
         specified by this route entry should be forwarded. Specifying a value
         of 0.0.0.0 in this field indicates that routing should be via the
         originator of the RIP advertisement. An address specified as a next
         hop must, per force, be directly reachable on the logical subnet over
         which the advertisement is made."
    ::= { tmnxRipNgRouteEntry 8 }

tmnxRipNgRouteMetric             OBJECT-TYPE
    SYNTAX      TmnxRipNgMetric
    MAX-ACCESS  read-only
    STATUS      current
    DESCRIPTION
        "tmnxRipNgRouteMetric gives the distance to the destination as
         advertised by the peer that sent this route."
    ::= { tmnxRipNgRouteEntry 9 }

tmnxRipNgRouteTag                OBJECT-TYPE
    SYNTAX      RouteTag
    MAX-ACCESS  read-only
    STATUS      current
    DESCRIPTION
        "tmnxRipNgRouteTag gives the value in the Route Tag field of the update
         received for this route,"
    ::= { tmnxRipNgRouteEntry 10 }

tmnxRipNgRouteStatus             OBJECT-TYPE
    SYNTAX      INTEGER {
        active   (1),
        inactive (2)
    }
    MAX-ACCESS  read-only
    STATUS      current
    DESCRIPTION
        "The value of tmnxRipNgRouteStatus indicates whether or not the route
         entry is active in the system. tmnxRipNgRouteStatus will be active(1)
         if the route entry has been added to the Route Table Manager(RTM)."
    ::= { tmnxRipNgRouteEntry 11 }

tmnxRipNgRouteTimerRemaining     OBJECT-TYPE
    SYNTAX      Unsigned32
    MAX-ACCESS  read-only
    STATUS      current
    DESCRIPTION
        "The value of tmnxRipNgRouteTimerRemaining is the number of seconds
         till the timeout timer expires."
    ::= { tmnxRipNgRouteEntry 12 }

tmnxRipNgRouteFC                 OBJECT-TYPE
    SYNTAX      TNamedItemOrEmpty
    MAX-ACCESS  read-only
    STATUS      current
    DESCRIPTION
        "The value of tmnxRipNgRouteFC indicates the forwarding class
         associated with the rip route.

         This object takes one of the following eight values - 'be', 'l2',
         'af', 'l1', 'h2', 'ef', 'h1', 'nc' - when the forwarding class is
         valid. If the forwarding class is not valid the object is a null
         string."
    ::= { tmnxRipNgRouteEntry 13 }

tmnxRipNgRouteFCPriority         OBJECT-TYPE
    SYNTAX      TPriorityOrUndefined
    MAX-ACCESS  read-only
    STATUS      current
    DESCRIPTION
        "The value of tmnxRipNgRouteFCPriority indicates the priority that is
         assigned to the rip routes."
    ::= { tmnxRipNgRouteEntry 14 }

tmnxRipNgIfStatTable             OBJECT-TYPE
    SYNTAX      SEQUENCE OF TmnxRipNgIfStatEntry
    MAX-ACCESS  not-accessible
    STATUS      current
    DESCRIPTION
        "tmnxRipNgIfStatTable is a read-only table which keeps statistical
         information about the interfaces monitoring RIP/RIP-NG."
    ::= { tmnxRipNgTableObjs 5 }

tmnxRipNgIfStatEntry             OBJECT-TYPE
    SYNTAX      TmnxRipNgIfStatEntry
    MAX-ACCESS  not-accessible
    STATUS      current
    DESCRIPTION
        "tmnxRipNgIfStatEntry is an entry (conceptual row) in the
         tmnxRipNgIfStatTable. Each entry represents statistical information
         for a RIP/RIP-NG interface."
    INDEX       {
        vRtrID,
        tmnxRipNgInstVersion,
        vRtrIfIndex
    }
    ::= { tmnxRipNgIfStatTable 1 }

TmnxRipNgIfStatEntry             ::= SEQUENCE
{
    tmnxRipNgIfStatAllSentUpdates    Counter32,
    tmnxRipNgIfStatAllTrigUpdates    Counter32,
    tmnxRipNgIfStatAllRcvBadPkts     Counter32,
    tmnxRipNgIfStatV1RcvUpdates      Counter32,
    tmnxRipNgIfStatV1RcvRequests     Counter32,
    tmnxRipNgIfStatV1BadUpdates      Counter32,
    tmnxRipNgIfStatV1BadRequests     Counter32,
    tmnxRipNgIfStatV1BadRoutes       Counter32,
    tmnxRipNgIfStatV2RcvUpdates      Counter32,
    tmnxRipNgIfStatV2RcvRequests     Counter32,
    tmnxRipNgIfStatV2BadUpdates      Counter32,
    tmnxRipNgIfStatV2BadRequests     Counter32,
    tmnxRipNgIfStatV2BadRoutes       Counter32,
    tmnxRipNgIfStatAuthErrors        Counter32,
    tmnxRipNgIfStatAllSentUpdts5Min  Counter32,
    tmnxRipNgIfStatAllTrigUpdts5Min  Counter32,
    tmnxRipNgIfStatAllRcvBadPkts5Min Counter32,
    tmnxRipNgIfStatV1RcvUpdates5Min  Counter32,
    tmnxRipNgIfStatV1RcvRequests5Min Counter32,
    tmnxRipNgIfStatV1BadUpdates5Min  Counter32,
    tmnxRipNgIfStatV1BadRequests5Min Counter32,
    tmnxRipNgIfStatV1BadRoutes5Min   Counter32,
    tmnxRipNgIfStatV2RcvUpdates5Min  Counter32,
    tmnxRipNgIfStatV2RcvRequests5Min Counter32,
    tmnxRipNgIfStatV2BadUpdates5Min  Counter32,
    tmnxRipNgIfStatV2BadRequests5Min Counter32,
    tmnxRipNgIfStatV2BadRoutes5Min   Counter32,
    tmnxRipNgIfStatAuthErrors5Min    Counter32,
    tmnxRipNgIfStatAllSentUpdts1Min  Counter32,
    tmnxRipNgIfStatAllTrigUpdts1Min  Counter32,
    tmnxRipNgIfStatAllRcvBadPkts1Min Counter32,
    tmnxRipNgIfStatV1RcvUpdates1Min  Counter32,
    tmnxRipNgIfStatV1RcvRequests1Min Counter32,
    tmnxRipNgIfStatV1BadUpdates1Min  Counter32,
    tmnxRipNgIfStatV1BadRequests1Min Counter32,
    tmnxRipNgIfStatV1BadRoutes1Min   Counter32,
    tmnxRipNgIfStatV2RcvUpdates1Min  Counter32,
    tmnxRipNgIfStatV2RcvRequests1Min Counter32,
    tmnxRipNgIfStatV2BadUpdates1Min  Counter32,
    tmnxRipNgIfStatV2BadRequests1Min Counter32,
    tmnxRipNgIfStatV2BadRoutes1Min   Counter32,
    tmnxRipNgIfStatAuthErrors1Min    Counter32
}

tmnxRipNgIfStatAllSentUpdates    OBJECT-TYPE
    SYNTAX      Counter32
    MAX-ACCESS  read-only
    STATUS      current
    DESCRIPTION
        "tmnxRipNgIfStatAllSentUpdates is the number of all RIPv1/RIP-NG
         updates actually sent on this interface. This explicitly does include
         full updates sent containing new information."
    ::= { tmnxRipNgIfStatEntry 1 }

tmnxRipNgIfStatAllTrigUpdates    OBJECT-TYPE
    SYNTAX      Counter32
    MAX-ACCESS  read-only
    STATUS      current
    DESCRIPTION
        "tmnxRipNgIfStatAllTrigUpdates is the number of triggered
         RIPv1/RIP-NG updates actually sent on this interface.  This explicitly
         does include full updates sent containing new information."
    ::= { tmnxRipNgIfStatEntry 2 }

tmnxRipNgIfStatAllRcvBadPkts     OBJECT-TYPE
    SYNTAX      Counter32
    MAX-ACCESS  read-only
    STATUS      current
    DESCRIPTION
        "tmnxRipNgIfStatAllRcvBadPkts is the number of RIPv1/RIP-NG updates
         received on this interface that were discarded as invalid."
    ::= { tmnxRipNgIfStatEntry 3 }

tmnxRipNgIfStatV1RcvUpdates      OBJECT-TYPE
    SYNTAX      Counter32
    MAX-ACCESS  read-only
    STATUS      current
    DESCRIPTION
        "tmnxRipNgIfStatV1RcvUpdates is the number of RIPv1/RIP-NG response
         packets received."
    ::= { tmnxRipNgIfStatEntry 4 }

tmnxRipNgIfStatV1RcvRequests     OBJECT-TYPE
    SYNTAX      Counter32
    MAX-ACCESS  read-only
    STATUS      current
    DESCRIPTION
        "tmnxRipNgIfStatV1RcvRequests is the number of RIPv1/RIP-NG request
         packets received."
    ::= { tmnxRipNgIfStatEntry 5 }

tmnxRipNgIfStatV1BadUpdates      OBJECT-TYPE
    SYNTAX      Counter32
    MAX-ACCESS  read-only
    STATUS      current
    DESCRIPTION
        "tmnxRipNgIfStatV1BadUpdates is the number of RIPv1/RIP-NG response
         packets received which were subsequently discarded for any reason."
    ::= { tmnxRipNgIfStatEntry 6 }

tmnxRipNgIfStatV1BadRequests     OBJECT-TYPE
    SYNTAX      Counter32
    MAX-ACCESS  read-only
    STATUS      current
    DESCRIPTION
        "tmnxRipNgIfStatV1BadRequests is the number of RIPv1/RIP-NG request
         packets received that were subsequently discarded for any reason."
    ::= { tmnxRipNgIfStatEntry 7 }

tmnxRipNgIfStatV1BadRoutes       OBJECT-TYPE
    SYNTAX      Counter32
    MAX-ACCESS  read-only
    STATUS      current
    DESCRIPTION
        "tmnxRipNgIfStatV1BadRoutes is the number of routes, in valid
         RIPv1/RIP-NG packets, which were ignored for any reason (e.g. unknown
         address family, or invalid metric)."
    ::= { tmnxRipNgIfStatEntry 8 }

tmnxRipNgIfStatV2RcvUpdates      OBJECT-TYPE
    SYNTAX      Counter32
    MAX-ACCESS  read-only
    STATUS      current
    DESCRIPTION
        "tmnxRipNgIfStatV2RcvUpdates is the number of RIPv2 response packets
         received."
    ::= { tmnxRipNgIfStatEntry 9 }

tmnxRipNgIfStatV2RcvRequests     OBJECT-TYPE
    SYNTAX      Counter32
    MAX-ACCESS  read-only
    STATUS      current
    DESCRIPTION
        "tmnxRipNgIfStatV2RcvRequests is the number of RIPv2 request packets
         received."
    ::= { tmnxRipNgIfStatEntry 10 }

tmnxRipNgIfStatV2BadUpdates      OBJECT-TYPE
    SYNTAX      Counter32
    MAX-ACCESS  read-only
    STATUS      current
    DESCRIPTION
        "tmnxRipNgIfStatV2BadUpdates is the number of RIPv2 response packets
         received which were subsequently discarded for any reason."
    ::= { tmnxRipNgIfStatEntry 11 }

tmnxRipNgIfStatV2BadRequests     OBJECT-TYPE
    SYNTAX      Counter32
    MAX-ACCESS  read-only
    STATUS      current
    DESCRIPTION
        "tmnxRipNgIfStatV2BadRequests is the number of RIPv2 request packets
         received that were subsequently discarded for any reason."
    ::= { tmnxRipNgIfStatEntry 12 }

tmnxRipNgIfStatV2BadRoutes       OBJECT-TYPE
    SYNTAX      Counter32
    MAX-ACCESS  read-only
    STATUS      current
    DESCRIPTION
        "tmnxRipNgIfStatV2BadRoutes is the number of routes, in valid RIPv2
         packets, which were ignored for any reason (e.g. unknown address
         family, or invalid metric)."
    ::= { tmnxRipNgIfStatEntry 13 }

tmnxRipNgIfStatAuthErrors        OBJECT-TYPE
    SYNTAX      Counter32
    MAX-ACCESS  read-only
    STATUS      current
    DESCRIPTION
        "tmnxRipNgIfStatAuthErrors is the  number of RIPv2 packets received
         which were subsequently discarded because of an error authenticating
         the packet."
    ::= { tmnxRipNgIfStatEntry 14 }

tmnxRipNgIfStatAllSentUpdts5Min  OBJECT-TYPE
    SYNTAX      Counter32
    MAX-ACCESS  read-only
    STATUS      current
    DESCRIPTION
        "tmnxRipNgIfStatAllSentUpdts5Min is the number of all RIPv1/RIP-NG
         updates actually sent on this interface in the last 5 minutes. This
         explicitly does include full updates sent containing new information."
    ::= { tmnxRipNgIfStatEntry 15 }

tmnxRipNgIfStatAllTrigUpdts5Min  OBJECT-TYPE
    SYNTAX      Counter32
    MAX-ACCESS  read-only
    STATUS      current
    DESCRIPTION
        "tmnxRipNgIfStatAllTrigUpdts5Min is the number of triggered
         RIPv1/RIP-NG updates actually sent on this interface in the last 5
         minutes. This explicitly does NOT include full updates sent containing
         new information."
    ::= { tmnxRipNgIfStatEntry 16 }

tmnxRipNgIfStatAllRcvBadPkts5Min OBJECT-TYPE
    SYNTAX      Counter32
    MAX-ACCESS  read-only
    STATUS      current
    DESCRIPTION
        "tmnxRipNgIfStatAllRcvBadPkts5Min is the number of RIPv1/RIP-NG
         response packets discarded (for any reason e.g. a version 0 packet, or
         an unknown command type) in the last 5 minutes."
    ::= { tmnxRipNgIfStatEntry 17 }

tmnxRipNgIfStatV1RcvUpdates5Min  OBJECT-TYPE
    SYNTAX      Counter32
    MAX-ACCESS  read-only
    STATUS      current
    DESCRIPTION
        "tmnxRipNgIfStatV1RcvUpdates5Min is the number of RIPv1/RIP-NG response
         packets received in the last 5 minutes."
    ::= { tmnxRipNgIfStatEntry 18 }

tmnxRipNgIfStatV1RcvRequests5Min OBJECT-TYPE
    SYNTAX      Counter32
    MAX-ACCESS  read-only
    STATUS      current
    DESCRIPTION
        "tmnxRipNgIfStatV1RcvRequests5Min is the number of RIPv1/RIP-NG request
         packets received in the last 5 minutes."
    ::= { tmnxRipNgIfStatEntry 19 }

tmnxRipNgIfStatV1BadUpdates5Min  OBJECT-TYPE
    SYNTAX      Counter32
    MAX-ACCESS  read-only
    STATUS      current
    DESCRIPTION
        "tmnxRipNgIfStatV1BadUpdates5Min is the number of RIPv1/RIP-NG response
         packets received in the last 5 minutes which were subsequently
         discarded for any reason."
    ::= { tmnxRipNgIfStatEntry 20 }

tmnxRipNgIfStatV1BadRequests5Min OBJECT-TYPE
    SYNTAX      Counter32
    MAX-ACCESS  read-only
    STATUS      current
    DESCRIPTION
        "tmnxRipNgIfStatV1BadRequests5Min is the number of RIPv1/RIP-NG request
         packets received in the last 5 minutes that were subsequently
         discarded for any reason."
    ::= { tmnxRipNgIfStatEntry 21 }

tmnxRipNgIfStatV1BadRoutes5Min   OBJECT-TYPE
    SYNTAX      Counter32
    MAX-ACCESS  read-only
    STATUS      current
    DESCRIPTION
        "tmnxRipNgIfStatV1BadRoutes5Min is the number of routes, in valid
         RIPv1/RIP-NG packets, which were ignored for any reason (e.g. unknown
         address family, or invalid metric) in the last 5 minutes."
    ::= { tmnxRipNgIfStatEntry 22 }

tmnxRipNgIfStatV2RcvUpdates5Min  OBJECT-TYPE
    SYNTAX      Counter32
    MAX-ACCESS  read-only
    STATUS      current
    DESCRIPTION
        "tmnxRipNgIfStatV2RcvUpdates5Min is the number of RIPv2 response
         packets received in the last 5 minutes."
    ::= { tmnxRipNgIfStatEntry 23 }

tmnxRipNgIfStatV2RcvRequests5Min OBJECT-TYPE
    SYNTAX      Counter32
    MAX-ACCESS  read-only
    STATUS      current
    DESCRIPTION
        "tmnxRipNgIfStatV2RcvRequests5Min is the number of RIPv2 request
         packets received in the last 5 minutes."
    ::= { tmnxRipNgIfStatEntry 24 }

tmnxRipNgIfStatV2BadUpdates5Min  OBJECT-TYPE
    SYNTAX      Counter32
    MAX-ACCESS  read-only
    STATUS      current
    DESCRIPTION
        "tmnxRipNgIfStatV2BadUpdates5Min is the number of RIPv2 response
         packets received which were subsequently discarded for any reason in
         the last 5 minutes."
    ::= { tmnxRipNgIfStatEntry 25 }

tmnxRipNgIfStatV2BadRequests5Min OBJECT-TYPE
    SYNTAX      Counter32
    MAX-ACCESS  read-only
    STATUS      current
    DESCRIPTION
        "tmnxRipNgIfStatV2BadRequests5Min is the number of RIPv2 request
         packets received that were subsequently discarded for any reason in
         the last 5 minutes."
    ::= { tmnxRipNgIfStatEntry 26 }

tmnxRipNgIfStatV2BadRoutes5Min   OBJECT-TYPE
    SYNTAX      Counter32
    MAX-ACCESS  read-only
    STATUS      current
    DESCRIPTION
        "tmnxRipNgIfStatV2BadRoutes5Min is the number of routes, in valid RIPv2
         packets, which were ignored for any reason (e.g. unknown address
         family, or invalid metric) in the last 5 minutes."
    ::= { tmnxRipNgIfStatEntry 27 }

tmnxRipNgIfStatAuthErrors5Min    OBJECT-TYPE
    SYNTAX      Counter32
    MAX-ACCESS  read-only
    STATUS      current
    DESCRIPTION
        "tmnxRipNgIfStatAuthErrors5Min is the  number of RIPv2 packets
         received which were subsequently discarded because of an error
         authenticating the packet in the last 5 minutes."
    ::= { tmnxRipNgIfStatEntry 28 }

tmnxRipNgIfStatAllSentUpdts1Min  OBJECT-TYPE
    SYNTAX      Counter32
    MAX-ACCESS  read-only
    STATUS      current
    DESCRIPTION
        "tmnxRipNgIfStatAllSentUpdts1Min is the number of all RIPv1/RIP-NG
         updates actually sent on this interface in the last minute. This
         explicitly does include full updates sent containing new information."
    ::= { tmnxRipNgIfStatEntry 29 }

tmnxRipNgIfStatAllTrigUpdts1Min  OBJECT-TYPE
    SYNTAX      Counter32
    MAX-ACCESS  read-only
    STATUS      current
    DESCRIPTION
        "tmnxRipNgIfStatAllTrigUpdts1Min is the number of triggered
         RIPv1/RIP-NG updates actually sent on this interface in the last
         minute. This explicitly does NOT include full updates sent containing
         new information."
    ::= { tmnxRipNgIfStatEntry 30 }

tmnxRipNgIfStatAllRcvBadPkts1Min OBJECT-TYPE
    SYNTAX      Counter32
    MAX-ACCESS  read-only
    STATUS      current
    DESCRIPTION
        "tmnxRipNgIfStatAllRcvBadPkts1Min is the number of RIPv1/RIP-NG
         response packets discarded (for any reason e.g. a version 0 packet, or
         an unknown command type) in the last minute."
    ::= { tmnxRipNgIfStatEntry 31 }

tmnxRipNgIfStatV1RcvUpdates1Min  OBJECT-TYPE
    SYNTAX      Counter32
    MAX-ACCESS  read-only
    STATUS      current
    DESCRIPTION
        "tmnxRipNgIfStatV1RcvUpdates1Min is the number of RIPv1/RIP-NG response
         packets received in the last minute."
    ::= { tmnxRipNgIfStatEntry 32 }

tmnxRipNgIfStatV1RcvRequests1Min OBJECT-TYPE
    SYNTAX      Counter32
    MAX-ACCESS  read-only
    STATUS      current
    DESCRIPTION
        "tmnxRipNgIfStatV1RcvRequests1Min is the number of RIPv1/RIP-NG request
         packets received in the last minute."
    ::= { tmnxRipNgIfStatEntry 33 }

tmnxRipNgIfStatV1BadUpdates1Min  OBJECT-TYPE
    SYNTAX      Counter32
    MAX-ACCESS  read-only
    STATUS      current
    DESCRIPTION
        "tmnxRipNgIfStatV1BadUpdates1Min is the number of RIPv1/RIP-NG response
         packets received in the last minute which were subsequently discarded
         for any reason."
    ::= { tmnxRipNgIfStatEntry 34 }

tmnxRipNgIfStatV1BadRequests1Min OBJECT-TYPE
    SYNTAX      Counter32
    MAX-ACCESS  read-only
    STATUS      current
    DESCRIPTION
        "tmnxRipNgIfStatV1BadRequests1Min is the number of RIPv1/RIP-NG request
         packets received in the last minute that were subsequently discarded
         for any reason."
    ::= { tmnxRipNgIfStatEntry 35 }

tmnxRipNgIfStatV1BadRoutes1Min   OBJECT-TYPE
    SYNTAX      Counter32
    MAX-ACCESS  read-only
    STATUS      current
    DESCRIPTION
        "tmnxRipNgIfStatV1BadRoutes1Min is the number of routes, in valid
         RIPv1/RIP-NG packets, which were ignored for any reason (e.g. unknown
         address family, or invalid metric) in the last minute."
    ::= { tmnxRipNgIfStatEntry 36 }

tmnxRipNgIfStatV2RcvUpdates1Min  OBJECT-TYPE
    SYNTAX      Counter32
    MAX-ACCESS  read-only
    STATUS      current
    DESCRIPTION
        "tmnxRipNgIfStatV2RcvUpdates1Min is the number of RIPv2 response
         packets received in the last minute."
    ::= { tmnxRipNgIfStatEntry 37 }

tmnxRipNgIfStatV2RcvRequests1Min OBJECT-TYPE
    SYNTAX      Counter32
    MAX-ACCESS  read-only
    STATUS      current
    DESCRIPTION
        "tmnxRipNgIfStatV2RcvRequests1Min is the number of RIPv2 request
         packets received by the RIP/RIP-NG process in the last minute."
    ::= { tmnxRipNgIfStatEntry 38 }

tmnxRipNgIfStatV2BadUpdates1Min  OBJECT-TYPE
    SYNTAX      Counter32
    MAX-ACCESS  read-only
    STATUS      current
    DESCRIPTION
        "tmnxRipNgIfStatV2BadUpdates1Min is the number of RIPv2 response
         packets received which were subsequently discarded for any reason in
         the last minute."
    ::= { tmnxRipNgIfStatEntry 39 }

tmnxRipNgIfStatV2BadRequests1Min OBJECT-TYPE
    SYNTAX      Counter32
    MAX-ACCESS  read-only
    STATUS      current
    DESCRIPTION
        "tmnxRipNgIfStatV2BadRequests1Min is the number of RIPv2 request
         packets received that were subsequently discarded for any reason in
         the last 1 minute."
    ::= { tmnxRipNgIfStatEntry 40 }

tmnxRipNgIfStatV2BadRoutes1Min   OBJECT-TYPE
    SYNTAX      Counter32
    MAX-ACCESS  read-only
    STATUS      current
    DESCRIPTION
        "tmnxRipNgIfStatV2BadRoutes1Min is the number of routes, in valid RIPv2
         packets, which were ignored for any reason (e.g. unknown address
         family, or invalid metric) in the last minute."
    ::= { tmnxRipNgIfStatEntry 41 }

tmnxRipNgIfStatAuthErrors1Min    OBJECT-TYPE
    SYNTAX      Counter32
    MAX-ACCESS  read-only
    STATUS      current
    DESCRIPTION
        "tmnxRipNgIfStatAuthErrors1Min is the number of RIPv2 packets received
         which were subsequently discarded because of an error authenticating
         the packet in the last minute."
    ::= { tmnxRipNgIfStatEntry 42 }

tmnxRipNgPeerTable               OBJECT-TYPE
    SYNTAX      SEQUENCE OF TmnxRipNgPeerEntry
    MAX-ACCESS  not-accessible
    STATUS      current
    DESCRIPTION
        "tmnxRipNgPeerTable is a read-only table which keeps information about
         RIP/RIP-NG peers."
    ::= { tmnxRipNgTableObjs 6 }

tmnxRipNgPeerEntry               OBJECT-TYPE
    SYNTAX      TmnxRipNgPeerEntry
    MAX-ACCESS  not-accessible
    STATUS      current
    DESCRIPTION
        "tmnxRipNgPeerEntry is an entry (conceptual row) in the
         tmnxRipNgPeerTable. Each entry represents information for a RIP/RIP-NG
         peer."
    INDEX       {
        vRtrID,
        tmnxRipNgInstVersion,
        tmnxRipNgPeerIfIndex,
        tmnxRipNgPeerAddrType,
        tmnxRipNgPeerAddress
    }
    ::= { tmnxRipNgPeerTable 1 }

TmnxRipNgPeerEntry               ::= SEQUENCE
{
    tmnxRipNgPeerIfIndex             InterfaceIndex,
    tmnxRipNgPeerAddrType            InetAddressType,
    tmnxRipNgPeerAddress             InetAddress,
    tmnxRipNgPeerLastUpdate          TimeStamp,
    tmnxRipNgPeerVersion             TmnxRipNgPeerVersion,
    tmnxRipNgPeerRcvBadPackets       Counter32,
    tmnxRipNgPeerRcvBadRoutes        Counter32
}

tmnxRipNgPeerIfIndex             OBJECT-TYPE
    SYNTAX      InterfaceIndex
    MAX-ACCESS  not-accessible
    STATUS      current
    DESCRIPTION
        "tmnxRipNgPeerIfIndex specifies the index of the interface on which
         this peer was discovered."
    ::= { tmnxRipNgPeerEntry 1 }

tmnxRipNgPeerAddrType            OBJECT-TYPE
    SYNTAX      InetAddressType
    MAX-ACCESS  not-accessible
    STATUS      current
    DESCRIPTION
        "The value of tmnxRipNgPeerAddrType indicates the type of address
         specified by tmnxRipNgPeerAddress"
    ::= { tmnxRipNgPeerEntry 2 }

tmnxRipNgPeerAddress             OBJECT-TYPE
    SYNTAX      InetAddress (SIZE (4|16))
    MAX-ACCESS  not-accessible
    STATUS      current
    DESCRIPTION
        "tmnxRipNgPeerAddress specifies the IP address that the peer is using
         as its source address."
    ::= { tmnxRipNgPeerEntry 3 }

tmnxRipNgPeerLastUpdate          OBJECT-TYPE
    SYNTAX      TimeStamp
    MAX-ACCESS  read-only
    STATUS      current
    DESCRIPTION
        "tmnxRipNgPeerLastUpdate indicates the value of sysUpTime when the most
         recent RIP/RIP-NG update was received from this peer."
    ::= { tmnxRipNgPeerEntry 4 }

tmnxRipNgPeerVersion             OBJECT-TYPE
    SYNTAX      TmnxRipNgPeerVersion
    MAX-ACCESS  read-only
    STATUS      current
    DESCRIPTION
        "tmnxRipNgPeerVersion indicates the RIP/RIP-NG version in the header of
         the last packet received from this peer."
    ::= { tmnxRipNgPeerEntry 5 }

tmnxRipNgPeerRcvBadPackets       OBJECT-TYPE
    SYNTAX      Counter32
    MAX-ACCESS  read-only
    STATUS      current
    DESCRIPTION
        "tmnxRipNgPeerRcvBadPackets is the number of RIP/RIP-NG updates
         received from this peer that were discarded as invalid."
    ::= { tmnxRipNgPeerEntry 6 }

tmnxRipNgPeerRcvBadRoutes        OBJECT-TYPE
    SYNTAX      Counter32
    MAX-ACCESS  read-only
    STATUS      current
    DESCRIPTION
        "tmnxRipNgPeerRcvBadRoutes is the number of routes received from this
         peer that were discarded as invalid."
    ::= { tmnxRipNgPeerEntry 7 }

tmnxRipNgAdvRouteTable           OBJECT-TYPE
    SYNTAX      SEQUENCE OF TmnxRipNgAdvRouteEntry
    MAX-ACCESS  not-accessible
    STATUS      current
    DESCRIPTION
        "tmnxRipNgAdvRouteTable is a read-only table which gives the routes
         that are advertised by RIP/RIP-NG to its neighbors."
    ::= { tmnxRipNgTableObjs 7 }

tmnxRipNgAdvRouteEntry           OBJECT-TYPE
    SYNTAX      TmnxRipNgAdvRouteEntry
    MAX-ACCESS  not-accessible
    STATUS      current
    DESCRIPTION
        "tmnxRipNgAdvRouteEntry is an entry (conceptual row) in the
         tmnxRipNgAdvRouteTable. Each entry represents information about a
         route that is advertised by RIP/RIP-NG on a particular interface."
    INDEX       {
        vRtrID,
        tmnxRipNgInstVersion,
        tmnxRipNgAdvRouteDestAddrType,
        tmnxRipNgAdvRouteDestAddress,
        tmnxRipNgAdvRouteMaskLength,
        tmnxRipNgAdvRouteIfIndex,
        tmnxRipNgAdvRouteIfAddrType,
        tmnxRipNgAdvRouteIfAddress
    }
    ::= { tmnxRipNgAdvRouteTable 1 }

TmnxRipNgAdvRouteEntry           ::= SEQUENCE
{
    tmnxRipNgAdvRouteDestAddrType    InetAddressType,
    tmnxRipNgAdvRouteDestAddress     InetAddress,
    tmnxRipNgAdvRouteMaskLength      InetAddressPrefixLength,
    tmnxRipNgAdvRouteIfIndex         InterfaceIndex,
    tmnxRipNgAdvRouteIfAddrType      InetAddressType,
    tmnxRipNgAdvRouteIfAddress       InetAddress,
    tmnxRipNgAdvRouteNHAddrType      InetAddressType,
    tmnxRipNgAdvRouteNHAddress       InetAddress,
    tmnxRipNgAdvRouteMetric          Unsigned32,
    tmnxRipNgAdvRouteTag             RouteTag,
    tmnxRipNgAdvRouteTimerRem        Integer32
}

tmnxRipNgAdvRouteDestAddrType    OBJECT-TYPE
    SYNTAX      InetAddressType
    MAX-ACCESS  not-accessible
    STATUS      current
    DESCRIPTION
        "The value of tmnxRipNgAdvRouteDestAddrType indicates the type of
         address specified by tmnxRipNgAdvRouteDestAddress"
    ::= { tmnxRipNgAdvRouteEntry 1 }

tmnxRipNgAdvRouteDestAddress     OBJECT-TYPE
    SYNTAX      InetAddress (SIZE (4|16))
    MAX-ACCESS  not-accessible
    STATUS      current
    DESCRIPTION
        "tmnxRipNgAdvRouteDestAddress is the destination IP address of the
         advertised route."
    ::= { tmnxRipNgAdvRouteEntry 2 }

tmnxRipNgAdvRouteMaskLength      OBJECT-TYPE
    SYNTAX      InetAddressPrefixLength (0..128)
    MAX-ACCESS  not-accessible
    STATUS      current
    DESCRIPTION
        "tmnxRipNgAdvRouteMaskLength contains the subnet/prefix masking length
         which is applied to tmnxRipNgAdvRouteDestAddress to yield the non-host
         portion of the destination address.

         If this field is zero, then no masking length has been included."
    ::= { tmnxRipNgAdvRouteEntry 3 }

tmnxRipNgAdvRouteIfIndex         OBJECT-TYPE
    SYNTAX      InterfaceIndex
    MAX-ACCESS  not-accessible
    STATUS      current
    DESCRIPTION
        "tmnxRipNgAdvRouteIfIndex specifies the index of the interface on which
         the route is advertised."
    ::= { tmnxRipNgAdvRouteEntry 4 }

tmnxRipNgAdvRouteIfAddrType      OBJECT-TYPE
    SYNTAX      InetAddressType
    MAX-ACCESS  not-accessible
    STATUS      current
    DESCRIPTION
        "The value of tmnxRipNgAdvRouteIfAddrType indicates the type of address
         specified by tmnxRipNgAdvRouteIfAddress"
    ::= { tmnxRipNgAdvRouteEntry 5 }

tmnxRipNgAdvRouteIfAddress       OBJECT-TYPE
    SYNTAX      InetAddress (SIZE (4|16))
    MAX-ACCESS  not-accessible
    STATUS      current
    DESCRIPTION
        "tmnxRipNgAdvRouteIfAddress specifies the IP address of the
         subnet/prefix to which the route is advertised."
    ::= { tmnxRipNgAdvRouteEntry 6 }

tmnxRipNgAdvRouteNHAddrType      OBJECT-TYPE
    SYNTAX      InetAddressType
    MAX-ACCESS  read-only
    STATUS      current
    DESCRIPTION
        "The value of tmnxRipNgAdvRouteNHAddrType indicates the type of address
         specified by tmnxRipNgAdvRouteNHAddress"
    ::= { tmnxRipNgAdvRouteEntry 7 }

tmnxRipNgAdvRouteNHAddress       OBJECT-TYPE
    SYNTAX      InetAddress (SIZE (0|4|16))
    MAX-ACCESS  read-only
    STATUS      current
    DESCRIPTION
        "tmnxRipNgAdvRouteNHAddress indicates the IP address which is
         advertised in the Next Hop field of the RIPv2 updates."
    ::= { tmnxRipNgAdvRouteEntry 8 }

tmnxRipNgAdvRouteMetric          OBJECT-TYPE
    SYNTAX      Unsigned32 (1..16)
    MAX-ACCESS  read-only
    STATUS      current
    DESCRIPTION
        "tmnxRipNgAdvRouteMetric gives the metric with which the route is
         advertised."
    ::= { tmnxRipNgAdvRouteEntry 9 }

tmnxRipNgAdvRouteTag             OBJECT-TYPE
    SYNTAX      RouteTag
    MAX-ACCESS  read-only
    STATUS      current
    DESCRIPTION
        "tmnxRipNgAdvRouteTag gives the value which is advertised in the Route
         Tag field for the route."
    ::= { tmnxRipNgAdvRouteEntry 10 }

tmnxRipNgAdvRouteTimerRem        OBJECT-TYPE
    SYNTAX      Integer32
    MAX-ACCESS  read-only
    STATUS      current
    DESCRIPTION
        "The value of tmnxRipNgAdvRouteTimerRem gives the number of seconds
         till the flush timer expires. The flush timer is active for only those
         routes which are no longer valid. Such routes will be advertised with
         a metric of 16 till the flush timer expires after which they will be
         removed from the database.

         tmnxRipNgAdvRouteTimerRem will have a value of -1 for valid routes for
         which the flush timer is not active."
    ::= { tmnxRipNgAdvRouteEntry 11 }

tmnxRipNgIfUcastTable            OBJECT-TYPE
    SYNTAX      SEQUENCE OF TmnxRipNgIfUcastEntry
    MAX-ACCESS  not-accessible
    STATUS      current
    DESCRIPTION
        "tmnxRipNgIfUcastTable contains configuration information for each
         unicast-address on an interface running RIP/RIP-NG."
    ::= { tmnxRipNgTableObjs 8 }

tmnxRipNgIfUcastEntry            OBJECT-TYPE
    SYNTAX      TmnxRipNgIfUcastEntry
    MAX-ACCESS  not-accessible
    STATUS      current
    DESCRIPTION
        "tmnxRipNgIfUcastEntry is an entry in the tmnxRipNgIfUcastTable. Each
         row entry represents a unicast address for an interface on the router
         that participates in the RIP/RIP-NG protocol.

         Entries in this table can be created and deleted via SNMP SET
         operations to tmnxRipNgIfUcastRowStatus."
    INDEX       {
        vRtrID,
        tmnxRipNgInstVersion,
        vRtrIfIndex,
        tmnxRipNgIfUcastAddrType,
        tmnxRipNgIfUcastAddress
    }
    ::= { tmnxRipNgIfUcastTable 1 }

TmnxRipNgIfUcastEntry            ::= SEQUENCE
{
    tmnxRipNgIfUcastAddrType         InetAddressType,
    tmnxRipNgIfUcastAddress          InetAddress,
    tmnxRipNgIfUcastRowStatus        RowStatus
}

tmnxRipNgIfUcastAddrType         OBJECT-TYPE
    SYNTAX      InetAddressType
    MAX-ACCESS  not-accessible
    STATUS      current
    DESCRIPTION
        "The value of tmnxRipNgIfUcastAddrType indicates the type of address
         specified by tmnxRipNgIfUcastAddress"
    ::= { tmnxRipNgIfUcastEntry 1 }

tmnxRipNgIfUcastAddress          OBJECT-TYPE
    SYNTAX      InetAddress (SIZE (4|16))
    MAX-ACCESS  not-accessible
    STATUS      current
    DESCRIPTION
        "tmnxRipNgIfUcastAddress is a unicast destination IP-address for this
         RIP/RIP-NG interface."
    ::= { tmnxRipNgIfUcastEntry 2 }

tmnxRipNgIfUcastRowStatus        OBJECT-TYPE
    SYNTAX      RowStatus
    MAX-ACCESS  read-create
    STATUS      current
    DESCRIPTION
        "tmnxRipNgIfUcastRowStatus controls the creation and deletion of rows
         in this table.

         To create a row in the tmnxRipNgIfUcastTable, set
         tmnxRipNgIfUcastRowStatus to createAndGo(4).

         To delete a row in the tmnxRipNgIfUcastTable, set
         tmnxRipNgIfUcastRowStatus to delete(6)."
    ::= { tmnxRipNgIfUcastEntry 3 }

tmnxRipNgNotificationObjs        OBJECT IDENTIFIER ::= { tmnxRipNgObjs 3 }

tmnxRipNgNotifySrcAddrType       OBJECT-TYPE
    SYNTAX      InetAddressType
    MAX-ACCESS  accessible-for-notify
    STATUS      current
    DESCRIPTION
        "The value of the object tmnxRipNgNotifySrcAddrType indicates the type
         of tmnxRipNgNotifySrcAddr."
    ::= { tmnxRipNgNotificationObjs 1 }

tmnxRipNgNotifySrcAddr           OBJECT-TYPE
    SYNTAX      InetAddress
    MAX-ACCESS  accessible-for-notify
    STATUS      current
    DESCRIPTION
        "The value of the object tmnxRipNgNotifySrcAddr indicates source
         address of the RIP/RIP-NG packet."
    ::= { tmnxRipNgNotificationObjs 2 }

tmnxRipNgNotifyReason            OBJECT-TYPE
    SYNTAX      DisplayString (SIZE (0..200))
    MAX-ACCESS  accessible-for-notify
    STATUS      current
    DESCRIPTION
        "The object tmnxRipNgNotifyReason is a printable character string."
    ::= { tmnxRipNgNotificationObjs 3 }

tmnxRipNgConformance             OBJECT IDENTIFIER ::= { tmnxSRConfs 89 }

tmnxRipNgCompliances             OBJECT IDENTIFIER ::= { tmnxRipNgConformance 1 }

tmnxRipNgV12v0Compliance         MODULE-COMPLIANCE
    STATUS      current
    DESCRIPTION
        "The compliance statement for management of RIP/RIP-NG features on
         release 12.0 Nokia SROS series systems."
    MODULE
        MANDATORY-GROUPS {
            tmnxRipNgGlobalV12v0Group,
            tmnxRipNgInstanceV12v0Group,
            tmnxRipNgGroupV12v0Group,
            tmnxRipNgInterfaceV12v0Group,
            tmnxRipNgRoutesV12v0Group,
            tmnxRipNgPeerV12v0Group,
            tmnxRipNgNotificationV12v0Group
        }
    ::= { tmnxRipNgCompliances 1 }

tmnxRipNgGroups                  OBJECT IDENTIFIER ::= { tmnxRipNgConformance 2 }

tmnxRipNgGlobalV12v0Group        OBJECT-GROUP
    OBJECTS     {
        tmnxRipNgGlobalLearnedRoutes,
        tmnxRipNgGlobalTimedoutRoutes,
        tmnxRipNgGlobalCurrentMemory,
        tmnxRipNgGlobalMaximumMemory
    }
    STATUS      current
    DESCRIPTION
        "The group of objects supporting general management of RIP/RIP-NG
         features on release 12.0 Nokia SROS series systems."
    ::= { tmnxRipNgGroups 1 }

tmnxRipNgInstanceV12v0Group      OBJECT-GROUP
    OBJECTS     {
        tmnxRipNgInstAuthType,
        tmnxRipNgInstAuthKey,
        tmnxRipNgInstCheckZero,
        tmnxRipNgInstMessageSize,
        tmnxRipNgInstMetricIn,
        tmnxRipNgInstMetricOut,
        tmnxRipNgInstPreference,
        tmnxRipNgInstReceive,
        tmnxRipNgInstSend,
        tmnxRipNgInstSplitHorizon,
        tmnxRipNgInstTimerFlush,
        tmnxRipNgInstTimerTimeout,
        tmnxRipNgInstTimerUpdate,
        tmnxRipNgInstImportPolicy1,
        tmnxRipNgInstImportPolicy2,
        tmnxRipNgInstImportPolicy3,
        tmnxRipNgInstImportPolicy4,
        tmnxRipNgInstImportPolicy5,
        tmnxRipNgInstExportPolicy1,
        tmnxRipNgInstExportPolicy2,
        tmnxRipNgInstExportPolicy3,
        tmnxRipNgInstExportPolicy4,
        tmnxRipNgInstExportPolicy5,
        tmnxRipNgInstDescription,
        tmnxRipNgInstAdminStatus,
        tmnxRipNgInstOperStatus,
        tmnxRipNgInstPropagateMetric,
        tmnxRipNgInstExportLimit,
        tmnxRipNgInstExpLmtLogPct,
        tmnxRipNgInstTotalExpRoutes
    }
    STATUS      current
    DESCRIPTION
        "The group of objects supporting management of RIP/RIP-NG instances on
         release 12.0 Nokia SROS series systems."
    ::= { tmnxRipNgGroups 2 }

tmnxRipNgGroupV12v0Group         OBJECT-GROUP
    OBJECTS     {
        tmnxRipNgGroupAuthType,
        tmnxRipNgGroupAuthKey,
        tmnxRipNgGroupCheckZero,
        tmnxRipNgGroupMessageSize,
        tmnxRipNgGroupMetricIn,
        tmnxRipNgGroupMetricOut,
        tmnxRipNgGroupPreference,
        tmnxRipNgGroupReceive,
        tmnxRipNgGroupSend,
        tmnxRipNgGroupSplitHorizon,
        tmnxRipNgGroupTimerFlush,
        tmnxRipNgGroupTimerTimeout,
        tmnxRipNgGroupTimerUpdate,
        tmnxRipNgGroupImportPolicy1,
        tmnxRipNgGroupImportPolicy2,
        tmnxRipNgGroupImportPolicy3,
        tmnxRipNgGroupImportPolicy4,
        tmnxRipNgGroupImportPolicy5,
        tmnxRipNgGroupExportPolicy1,
        tmnxRipNgGroupExportPolicy2,
        tmnxRipNgGroupExportPolicy3,
        tmnxRipNgGroupExportPolicy4,
        tmnxRipNgGroupExportPolicy5,
        tmnxRipNgGroupDescription,
        tmnxRipNgGroupInheritance,
        tmnxRipNgGroupAdminStatus,
        tmnxRipNgGroupOperStatus,
        tmnxRipNgGroupRowStatus
    }
    STATUS      current
    DESCRIPTION
        "The group of objects supporting management of RIP/RIP-NG Groups on
         release 12.0 Nokia SROS series systems."
    ::= { tmnxRipNgGroups 3 }

tmnxRipNgInterfaceV12v0Group     OBJECT-GROUP
    OBJECTS     {
        tmnxRipNgIfGroupName,
        tmnxRipNgIfAuthType,
        tmnxRipNgIfAuthKey,
        tmnxRipNgIfCheckZero,
        tmnxRipNgIfMessageSize,
        tmnxRipNgIfMetricIn,
        tmnxRipNgIfMetricOut,
        tmnxRipNgIfPreference,
        tmnxRipNgIfReceive,
        tmnxRipNgIfSend,
        tmnxRipNgIfSplitHorizon,
        tmnxRipNgIfTimerFlush,
        tmnxRipNgIfTimerTimeout,
        tmnxRipNgIfTimerUpdate,
        tmnxRipNgIfImportPolicy1,
        tmnxRipNgIfImportPolicy2,
        tmnxRipNgIfImportPolicy3,
        tmnxRipNgIfImportPolicy4,
        tmnxRipNgIfImportPolicy5,
        tmnxRipNgIfExportPolicy1,
        tmnxRipNgIfExportPolicy2,
        tmnxRipNgIfExportPolicy3,
        tmnxRipNgIfExportPolicy4,
        tmnxRipNgIfExportPolicy5,
        tmnxRipNgIfDescription,
        tmnxRipNgIfInheritance,
        tmnxRipNgIfAdminStatus,
        tmnxRipNgIfOperStatus,
        tmnxRipNgIfRowStatus,
        tmnxRipNgIfStatAllSentUpdates,
        tmnxRipNgIfStatAllTrigUpdates,
        tmnxRipNgIfStatAllRcvBadPkts,
        tmnxRipNgIfStatV1RcvUpdates,
        tmnxRipNgIfStatV1RcvRequests,
        tmnxRipNgIfStatV1BadUpdates,
        tmnxRipNgIfStatV1BadRequests,
        tmnxRipNgIfStatV1BadRoutes,
        tmnxRipNgIfStatV2RcvUpdates,
        tmnxRipNgIfStatV2RcvRequests,
        tmnxRipNgIfStatV2BadUpdates,
        tmnxRipNgIfStatV2BadRequests,
        tmnxRipNgIfStatV2BadRoutes,
        tmnxRipNgIfStatAuthErrors,
        tmnxRipNgIfStatAllSentUpdts5Min,
        tmnxRipNgIfStatAllTrigUpdts5Min,
        tmnxRipNgIfStatAllRcvBadPkts5Min,
        tmnxRipNgIfStatV1RcvUpdates5Min,
        tmnxRipNgIfStatV1RcvRequests5Min,
        tmnxRipNgIfStatV1BadUpdates5Min,
        tmnxRipNgIfStatV1BadRequests5Min,
        tmnxRipNgIfStatV1BadRoutes5Min,
        tmnxRipNgIfStatV2RcvUpdates5Min,
        tmnxRipNgIfStatV2RcvRequests5Min,
        tmnxRipNgIfStatV2BadUpdates5Min,
        tmnxRipNgIfStatV2BadRequests5Min,
        tmnxRipNgIfStatV2BadRoutes5Min,
        tmnxRipNgIfStatAuthErrors5Min,
        tmnxRipNgIfStatAllSentUpdts1Min,
        tmnxRipNgIfStatAllTrigUpdts1Min,
        tmnxRipNgIfStatAllRcvBadPkts1Min,
        tmnxRipNgIfStatV1RcvUpdates1Min,
        tmnxRipNgIfStatV1RcvRequests1Min,
        tmnxRipNgIfStatV1BadUpdates1Min,
        tmnxRipNgIfStatV1BadRequests1Min,
        tmnxRipNgIfStatV1BadRoutes1Min,
        tmnxRipNgIfStatV2RcvUpdates1Min,
        tmnxRipNgIfStatV2RcvRequests1Min,
        tmnxRipNgIfStatV2BadUpdates1Min,
        tmnxRipNgIfStatV2BadRequests1Min,
        tmnxRipNgIfStatV2BadRoutes1Min,
        tmnxRipNgIfStatAuthErrors1Min,
        tmnxRipNgIfUcastRowStatus
    }
    STATUS      current
    DESCRIPTION
        "The group of objects supporting management of RIP/RIP-NG interfaces on
         release 12.0 Nokia SROS series systems."
    ::= { tmnxRipNgGroups 4 }

tmnxRipNgRoutesV12v0Group        OBJECT-GROUP
    OBJECTS     {
        tmnxRipNgRouteNHAddrType,
        tmnxRipNgRouteNHAddress,
        tmnxRipNgRouteMetric,
        tmnxRipNgRouteTag,
        tmnxRipNgRouteStatus,
        tmnxRipNgRouteTimerRemaining,
        tmnxRipNgRouteFC,
        tmnxRipNgRouteFCPriority,
        tmnxRipNgAdvRouteNHAddrType,
        tmnxRipNgAdvRouteNHAddress,
        tmnxRipNgAdvRouteMetric,
        tmnxRipNgAdvRouteTag,
        tmnxRipNgAdvRouteTimerRem
    }
    STATUS      current
    DESCRIPTION
        "The group of objects supporting RIP/RIP-NG Routes on release 12.0
         Nokia SROS series systems."
    ::= { tmnxRipNgGroups 5 }

tmnxRipNgPeerV12v0Group          OBJECT-GROUP
    OBJECTS     {
        tmnxRipNgPeerLastUpdate,
        tmnxRipNgPeerVersion,
        tmnxRipNgPeerRcvBadPackets,
        tmnxRipNgPeerRcvBadRoutes
    }
    STATUS      current
    DESCRIPTION
        "The group of objects supporting RIP/RIP-NG Peers on release 12.0 Nokia
         SROS series systems."
    ::= { tmnxRipNgGroups 6 }

tmnxRipNgNotifyObjsV12v0Group    OBJECT-GROUP
    OBJECTS     {
        tmnxRipNgNotifySrcAddrType,
        tmnxRipNgNotifySrcAddr,
        tmnxRipNgNotifyReason
    }
    STATUS      current
    DESCRIPTION
        "The group of objects supporting the RIP/RIP-NG notifications on
         release 12.0 Nokia SROS series systems."
    ::= { tmnxRipNgGroups 7 }

tmnxRipNgNotificationV12v0Group  NOTIFICATION-GROUP
    NOTIFICATIONS {
        tmnxRipNgAuthTypeMismatch,
        tmnxRipNgAuthFailure,
        tmnxRipNgInstShuttingDown,
        tmnxRipNgInstRestarted,
        tmnxRipNgInstExpLmtReached,
        tmnxRipNgInstExpLmtWarning,
        tmnxRipNgInstRtsExpLmtDropped,
        tmnxRipNgIfUcastAddrNotUsed
    }
    STATUS      current
    DESCRIPTION
        "The group of notifications supporting the RIP/RIP-NG feature on
         release 12.0 Nokia SROS series systems."
    ::= { tmnxRipNgGroups 8 }

tmnxRipNgNotifyPrefix            OBJECT IDENTIFIER ::= { tmnxSRNotifyPrefix 89 }

tmnxRipNgNotifications           OBJECT IDENTIFIER ::= { tmnxRipNgNotifyPrefix 0 }

tmnxRipNgAuthTypeMismatch        NOTIFICATION-TYPE
    OBJECTS     {
        tmnxRipNgPeerLastUpdate
    }
    STATUS      current
    DESCRIPTION
        "A tmnxRipNgAuthTypeMismatch trap is generated when the authentication
         type field in a received RIPv2 packet conflicts with the
         authentication type configured for this router."
    ::= { tmnxRipNgNotifications 1 }

tmnxRipNgAuthFailure             NOTIFICATION-TYPE
    OBJECTS     {
        tmnxRipNgPeerLastUpdate
    }
    STATUS      current
    DESCRIPTION
        "A tmnxRipNgAuthFailure trap is generated when the authentication key
         in a received RIPv2 packet conflicts with the authentication key
         configured for this router."
    ::= { tmnxRipNgNotifications 2 }

tmnxRipNgInstShuttingDown        NOTIFICATION-TYPE
    OBJECTS     {
        tmnxRipNgInstOperStatus,
        tmnxRipNgNotifyReason
    }
    STATUS      current
    DESCRIPTION
        "A tmnxRipNgInstShuttingDown trap is generated when the RIP/RIP-NG
         instance shuts down on its own accord when the protocol runs out of
         resources such as memory. The instance will attempt to restart within
         30 seconds of shutting down."
    ::= { tmnxRipNgNotifications 3 }

tmnxRipNgInstRestarted           NOTIFICATION-TYPE
    OBJECTS     {
        tmnxRipNgInstOperStatus
    }
    STATUS      current
    DESCRIPTION
        "When a RIP/RIP-NG protocol instance runs out of resources, the
         instance will shut down and then attempt to restart within 30 seconds.
         A tmnxRipNgInstRestarted trap is generated when the RIP instance has
         restarted."
    ::= { tmnxRipNgNotifications 4 }

tmnxRipNgInstExpLmtReached       NOTIFICATION-TYPE
    OBJECTS     {
        tmnxRipNgInstExportLimit
    }
    STATUS      current
    DESCRIPTION
        "A tmnxRipNgInstExpLmtReached notification is generated when the
         configured value of exported routes, tmnxRipNgInstExportLimit is
         reached. Additional routes would not be exported into RIP/RIP-NG from
         the route table."
    ::= { tmnxRipNgNotifications 5 }

tmnxRipNgInstExpLmtWarning       NOTIFICATION-TYPE
    OBJECTS     {
        tmnxRipNgInstExportLimit,
        tmnxRipNgInstExpLmtLogPct
    }
    STATUS      current
    DESCRIPTION
        "A tmnxRipNgInstExpLmtWarning notification is generated when the number
         of exported routes is equal to the configured percent,
         tmnxRipNgInstExpLmtLogPct of the export limit,
         tmnxRipNgInstExportLimit. Additional routes will continue to be
         exported into RIP/RIP-NG from the route table till the export limit is
         reached."
    ::= { tmnxRipNgNotifications 6 }

tmnxRipNgInstRtsExpLmtDropped    NOTIFICATION-TYPE
    OBJECTS     {
        tmnxRipNgInstExportLimit
    }
    STATUS      current
    DESCRIPTION
        "A tmnxRipNgInstRtsExpLmtDropped notification is generated when the
         number of exported routes drops below the export limit,
         tmnxRipNgInstExportLimit."
    ::= { tmnxRipNgNotifications 7 }

tmnxRipNgIfUcastAddrNotUsed      NOTIFICATION-TYPE
    OBJECTS     {
        tmnxRipNgIfRowStatus
    }
    STATUS      current
    DESCRIPTION
        "A tmnxRipNgIfUcastAddrNotUsed notification is generated when a
         neighbor has one or more unicast-addresses configured but it's send
         mode is not set to 'unicast'."
    ::= { tmnxRipNgNotifications 8 }

END
