TIMETRA-VRRP-MIB DEFINITIONS ::= BEGIN

IMPORTS
    MODULE-IDENTITY, OBJECT-TYPE, NOTIFICATION-TYPE,
    Integer32, Unsigned32, IpAddress, Counter32
        FROM SNMPv2-SMI

    MODULE-COMPLIANCE, OBJECT-GROUP, NOTIFICATION-GROUP
        FROM SNMPv2-CONF

    TEXTUAL-CONVENTION, RowStatus, TruthValue, 
    TimeStamp, TimeInterval, MacAddress         
        FROM SNMPv2-TC

    TItemDescription, TmnxPortID, TmnxServId, TNamedItem,
    TNamedItemOrEmpty, TmnxTunnelGroupId, TmnxAdminState
        FROM TIMETRA-TC-MIB

    timetraSRMIBModules, tmnxSRObjs, tmnxSRNotifyPrefix,
    tmnxSRConfs
        FROM TIMETRA-GLOBAL-MIB

    LAGInterfaceNumber
        FROM TIMETRA-TC-MIB

    ifIndex                             
        FROM IF-MIB
        
    vrrpOperVrId, vrrpOperMasterIpAddr, 
    vrrpOperEntry, vrrpRouterStatsEntry 
        FROM VRRP-MIB

    vrrpOperationsVrId, vrrpOperationsMasterIpAddr,
    vrrpOperationsEntry, vrrpRouterStatisticsEntry,
    vrrpNewMasterReason
        FROM TIMETRA-VRRP-V3-MIB

    InetAddress, InetAddressType, InetAddressPrefixLength
        FROM INET-ADDRESS-MIB

    ipv6RouterAdvertEntry
        FROM IP-MIB
    ;

timetraVrrpMIBModule   MODULE-IDENTITY
        LAST-UPDATED "201701010000Z"
        ORGANIZATION "Nokia"
        CONTACT-INFO
            "Nokia SROS Support
             Web: http://www.nokia.com"
        DESCRIPTION
        "This document is the SNMP MIB module to manage and provision 
        Virtual Router Redundancy Protocol (VRRP) in the Nokia
        SROS system.

        Copyright 2003-2017 Nokia. All rights reserved.
        Reproduction of this document is authorized on the condition 
        that the foregoing copyright notice is included.

        This SNMP MIB module (Specification) embodies Nokia's
        proprietary intellectual property.  Nokia retains 
        all title and ownership in the Specification, including any 
        revisions.

        Nokia grants all interested parties a non-exclusive 
        license to use and distribute an unmodified copy of this 
        Specification in connection with management of Nokia  
        products, and without fee, provided this copyright notice and 
        license appear on all copies.

        This Specification is supplied `as is', and Nokia
        makes no warranty, either express or implied, as to the use, 
        operation, condition, or performance of the Specification."

--
--  Revision History
--
        REVISION        "201701010000Z"
        DESCRIPTION     "Rev 15.0               1 Jan 2017 00:00
                         15.0 release of the TIMETRA-VRRP-MIB."

        REVISION        "201501010000Z"
        DESCRIPTION     "Rev 13.0               1 Jan 2015 00:00
                         13.0 release of the TIMETRA-VRRP-MIB."

        REVISION        "201401010000Z"
        DESCRIPTION     "Rev 12.0               1 Jan 2014 00:00
                         12.0 release of the TIMETRA-VRRP-MIB."

        REVISION        "201102010000Z"
        DESCRIPTION     "Rev 9.0                1 Feb 2011 00:00
                         9.0 release of the TIMETRA-VRRP-MIB."

        REVISION        "200902280000Z"
        DESCRIPTION     "Rev 7.0                28 Feb 2009 00:00
                         7.0 release of the TIMETRA-VRRP-MIB."

        REVISION        "200807010000Z"
        DESCRIPTION     "Rev 6.1                01 Jul 2008 00:00
                         6.1 release of the TIMETRA-VRRP-MIB."

        REVISION        "200701010000Z"
        DESCRIPTION     "Rev 5.0                01 Jan 2007 00:00
                         5.0 release of the TIMETRA-VRRP-MIB."

        REVISION        "200508310000Z"   
        DESCRIPTION     "Rev 3.0                31 Aug 2005 00:00
                         3.0 release of the TIMETRA-VRRP-MIB."

        REVISION        "200501240000Z"   
        DESCRIPTION     "Rev 2.1                24 Jan 2005 00:00
                         2.1 release of the TIMETRA-VRRP-MIB."

        REVISION        "200401150000Z"
        DESCRIPTION     "Rev 2.0                15 Jan 2004 00:00
                         2.0 release of the TIMETRA-VRRP-MIB."

        REVISION        "200308150000Z"
        DESCRIPTION     "Rev 1.2                15 Aug 2003 00:00
                         1.2 release of the TIMETRA-VRRP-MIB."

        REVISION        "200301200000Z"
        DESCRIPTION     "Rev 1.0                20 Jan 2003 00:00
                         1.0 Release of the TIMETRA-VRRP-MIB."

        REVISION        "200205130000Z"
        DESCRIPTION     "Rev 0.1                13 May 2002 00:00
                         Initial version of the TIMETRA-VRRP-MIB."
        
        ::= { timetraSRMIBModules 20 }

tmnxVrrpMibObjects          OBJECT IDENTIFIER ::= { tmnxSRObjs 20 }
tmnxVrrpNotifyPrefix        OBJECT IDENTIFIER ::= { tmnxSRNotifyPrefix 20 }
    tmnxVrrpNotifications       OBJECT IDENTIFIER ::= { tmnxVrrpNotifyPrefix 0 }
tmnxVrrpConformance         OBJECT IDENTIFIER ::= { tmnxSRConfs 20 }

tmnxVrrpObjects             OBJECT IDENTIFIER ::= { tmnxVrrpMibObjects 1 }
tmnxVrrpPolicyObjects       OBJECT IDENTIFIER ::= { tmnxVrrpMibObjects 2 }
tmnxVrrpNotificationObjects OBJECT IDENTIFIER ::= { tmnxVrrpMibObjects 3 }

-- ***************************************************************************
-- TIMETRA-VRRP-MIB Textual Conventions
-- ***************************************************************************
TmnxVrrpPolicyID ::= TEXTUAL-CONVENTION
    STATUS       current
    DESCRIPTION  
        "The TmnxVrrpPolicyID textual convention is used to uniquely identify 
         a Priority Control Policy."
    SYNTAX Unsigned32 (1..9999)

TmnxVrrpPriority ::= TEXTUAL-CONVENTION
    STATUS       current
    DESCRIPTION  
        "The TmnxVrrpPriority textual convention specifies either the 
         configured delta-in-use-limit priority for a VRRP Priority 
         Control Policy or the configured delta or explicit priority 
         for a Priority Control Event."
    SYNTAX Unsigned32 (0..254)

TmnxEventType ::= TEXTUAL-CONVENTION
    STATUS       current
    DESCRIPTION  
        "The TmnxEventType textual convention is an enumerated
         integer that specifies whether the priority event is a delta(1) 
         or an explicit(2) event. 
         A Delta priority event is a conditional event defined in a Priority 
         Control policy that subtracts a given amount from the base priority
         to give the current in-use priority for the VRRP virtual router 
         instances to which the policy is applied. 
         An Explicit priority event is a conditional event defined in a 
         Priority Control policy that explicitly defines the in-use 
         priority for the VRRP virtual router instances to which the policy
         is applied.
         Explicit events override all Delta Events. When multiple explicit 
         events occur simultaneously, the event with the lowest priority 
         value defines the in-use priority."
    SYNTAX INTEGER {
                delta(1), 
                explicit(2) 
           }

TmnxEventHoldSet ::= TEXTUAL-CONVENTION
    STATUS       current
    DESCRIPTION  
        "The TmnxEventHoldSet textual convention specifies the hold-set 
         time i.e. the amount of time in seconds that must transpire 
         before an event which is in a 'set' state can transition to 
         the 'cleared' state. 
         The hold-set time is used to dampen the effect of a flapping 
         event. Each time an event transitions between 'cleared' and 
         'set', the hold-set timer is loaded with the configured hold-set 
         time and begins to count down to zero. If the timer reaches zero, 
         the event will be allowed to enter the 'cleared' state depending 
         on whether the object controlling the event conforms to the 
         requirements defined in the event itself. It is possible, on
         some event types, to have a further 'set' action reload the 
         hold-set timer. This extends the amount of time that must 
         expire before entering the cleared state."
    SYNTAX Unsigned32 (0..86400)

TmnxEventHoldClear ::= TEXTUAL-CONVENTION
    STATUS       current
    DESCRIPTION  
        "The TmnxEventHoldClear textual convention specifies the 
         hold-clear time i.e. the amount of time in seconds by which 
         the effect of a cleared event on the associated virtual
         router instance is delayed.
         The hold-clear time is used to prevent black hole conditions 
         when a virtual router instance advertises itself as a master 
         before other conditions associated with the cleared event 
         have had a chance to enter a forwarding state." 
    SYNTAX Unsigned32 (0..86400)

TmnxPortDownEventOperState ::= TEXTUAL-CONVENTION
    STATUS       current
    DESCRIPTION  
        "The TmnxPortDownEventOperState textual convention is an 
         enumerated integer that specifies the operational state 
         of a Port Down Priority Event. The event state corresponds 
         to the state of the port or the channel with which it is
         associated." 
    SYNTAX INTEGER {
        cleared(0),           -- port or channel is operationally up 
        setNotProvisioned(1), -- port or channel is not provisioned
        setNotPopulated(2),   -- port or channel is not populated
        setDown(3)            -- port or channel is operationally down
    }

TmnxLagPortDownEventOperState ::= TEXTUAL-CONVENTION
    STATUS       current
    DESCRIPTION  
        "The TmnxLagPortDownEventOperState textual convention is an 
         enumerated integer that specifies the operational state 
         of a LAG Port Down Priority Event. The event state depends on
         the state of each port in the LAG (Link Aggregation Group) 
         with which it is associated." 
    SYNTAX INTEGER {
        cleared(0),              -- all ports are operationally up 
        setNonExistant(1),       -- LAG does not exist in the system
        setOnePortDown(2),       -- 1 port is down
        setTwoPortDown(3),       -- 2 ports are down 
        setThreePortDown(4),     -- 3 ports are down 
        setFourPortDown(5),      -- 4 ports are down 
        setFivePortDown(6),      -- 5 ports are down 
        setSixPortDown(7),       -- 6 ports are down 
        setSevenPortDown(8),     -- 7 ports are down 
        setEightPortDown(9),     -- 8 ports are down 
        setNinePortDown(10),     -- 9 ports are down 
        setTenPortDown(11),      -- 10 ports are down 
        setElevenPortDown(12),   -- 11 ports are down 
        setTwelvePortDown(13),   -- 12 ports are down 
        setThirteenPortDown(14), -- 13 ports are down 
        setFourteenPortDown(15), -- 14 ports are down 
        setFifteenPortDown(16),  -- 15 ports are down 
        setSixteenPortDown(17)   -- 16 ports are down 
    }

TmnxHostUnreachableEventOperState ::= TEXTUAL-CONVENTION
    STATUS       current
    DESCRIPTION  
        "The TmnxHostUnreachableEventOperState textual convention is an 
         enumerated integer that specifies the operational state 
         of a Host Unreachable Priority Event. The event state corresponds 
         to the ability to receive ICMP Echo Reply packets from the
         IP host address associated with the event" 
    SYNTAX INTEGER {
        clearedNoArp(0),           -- not enough failed attempts to be set
        clearedNoRoute(1),         -- not enough failed attempts to be set
        clearedHostUnreachable(2), -- not enough failed attempts to be set
        clearedNoReply(3),         -- not enough failed attempts to be set
        clearedReplyReceived(4),   -- last attempt received
        setNoArp(5),               -- local IP address is unreachable 
        setNoRoute(6),             -- remote IP address is unreachable
        setHostUnreachable(7),     -- ICMP Host Unreachable is received
        setNoReply(8),             -- ICMP Echo request times out
        setReplyReceived(9)        -- last attempt received but 
                                   -- historically not able to clear
    }

TmnxRouteUnknownEventOperState ::= TEXTUAL-CONVENTION
    STATUS       current
    DESCRIPTION  
        "The TmnxRouteUnknownEventOperState textual convention is an 
         enumerated integer that specifies the operational state 
         of a Route Unknown Priority Event. The event state corresponds 
         to the existence in the routing table of an active route to the 
         IP route prefix corresponding to the event." 
    SYNTAX INTEGER {
        clearedLessSpecificFound(0), -- found less specific prefix and
                                     -- meets other criteria
        clearedFound(1),             -- found and meets criteria
        setNonExistent(2),           -- not found
        setInActive(3),              -- found but not used
        setWrongNextHop(4),          -- found but does not meet next  
                                     -- hop criteria
        setWrongProtocol(5),         -- found but does not meet 
                                     -- protocol criteria
        setLessSpecificFound(6),     -- found but less-specific not
                                     -- defined for prefix
        setDefaultBestMatch(7)       -- found but allow-default not
                                     -- defined for prefix
    }

TmnxVrrpAssoBfdIntfSessOperState ::= TEXTUAL-CONVENTION
    STATUS  current
    DESCRIPTION
        "The TmnxVrrpAssoBfdIntfSessOperState data type is an enumerated integer 
         that describes the values used to identify the operational state of 
         a BFD session the VRRP virtual router instance is relying upon for its
         fast triggering mechanism."
    SYNTAX  INTEGER {
        unknown       (1),         
        connected     (2), -- the BFD connection with the peer is operational
        broken        (3), -- the BFD connection with the peer has timed out
        peerDetectsDown(4),-- the peer detects that the BFD connection is down
        notConfigured  (5),-- the BFD connection with the peer is not configured
        noResources    (6) -- resource not available
    }    
    
TmnxMcIPsecNoFwdEventOperState ::= TEXTUAL-CONVENTION
    STATUS       current
    DESCRIPTION  
        "The TmnxMcIPsecNoFwdEventOperState textual convention is an 
         enumerated integer that specifies the operational state 
         of a multi-chassis IPsec non-forwarding Priority Event.

         The event state corresponds to the state of the tunnel-group with
         which it is associated." 
    SYNTAX INTEGER {
        cleared(0),           -- Multi-chassis IPsec tunnel-group is forwarding
        setNotForwarding(1)   -- MC IPsec tunnel-group is not forwarding
    }


-- ***************************************************************************
-- TIMETRA-VRRP-MIB objects
-- ***************************************************************************

-- ***************************************************************************
-- Augmentation of the vrrpOperTable defined in the VRRP-MIB
-- ***************************************************************************

tmnxVrrpOperTable OBJECT-TYPE
    SYNTAX       SEQUENCE OF TmnxVrrpOperEntry
    MAX-ACCESS   not-accessible
    STATUS       current
    DESCRIPTION  
        "The tmnxVrrpOperTable provides an extension of the vrrpOperTable 
         in the VRRP-MIB.

         Use of AUGMENTS clause implies a one-to-one dependent relationship 
         between the base table, vrrpOperTable, and the augmenting table, 
         tmnxVrrpOperTable. This in effect extends the vrrpOperTable with 
         additional columns. Creation (or deletion) of a row in the 
         vrrpOperTable results in the same fate for the row in the 
         tmnxVrrpOperTable."
    ::= { tmnxVrrpObjects 1 }

tmnxVrrpOperEntry OBJECT-TYPE
    SYNTAX       TmnxVrrpOperEntry
    MAX-ACCESS   not-accessible
    STATUS       current
    DESCRIPTION 
        "Each row entry in the tmnxVrrpOperTable represents additional 
         columns in the vrrpOperTable for attributes specific to the
         Nokia SROS series VRRP implementation."
    AUGMENTS { vrrpOperEntry }
    ::= { tmnxVrrpOperTable 1 }

TmnxVrrpOperEntry ::= 
    SEQUENCE {
        tmnxVrrpOperState                     INTEGER,
        tmnxVrrpOperVirtualMacAddr            MacAddress,
        tmnxVrrpOperMismatchDiscard           TruthValue,
        tmnxVrrpOperPingReply                 TruthValue,
        tmnxVrrpOperTelnetReply               TruthValue,
        tmnxVrrpOperSshReply                  TruthValue,
        tmnxVrrpOperPolicyId                  Unsigned32,
        tmnxVrrpOperInUsePriority             Unsigned32,
        tmnxVrrpOperMasterSince               TimeStamp,
        tmnxVrrpOperMasterPriority            Unsigned32,
        tmnxVrrpOperOwner                     TruthValue,
        tmnxVrrpOperMasterDownInterval        TimeInterval,
        tmnxVrrpOperMasterDownTimer           TimeInterval,
        tmnxVrrpOperAdvIntervalInherit        TruthValue,
        tmnxVrrpOperInUseAdvInterval          Integer32,
        tmnxVrrpOperTracerouteReply           TruthValue,
        tmnxVrrpOperStandbyFwding             TruthValue,
        tmnxVrrpOperAdvIntervalMilSec         Unsigned32,
        tmnxVrrpOperInUseAdvIntlMilSec        Unsigned32,
        tmnxVrrpOperInitDelay                 Unsigned32,
        tmnxVrrpOperInitTimer                 TimeInterval,
        tmnxVrrpOperDownReason                INTEGER,
        tmnxVrrpOperPassive TruthValue,
        tmnxVrrpOperRowStatus RowStatus,
        tmnxVrrpOperGroupName TNamedItemOrEmpty
      
    }

tmnxVrrpOperState  OBJECT-TYPE
    SYNTAX       INTEGER {
                     up(1),
                     down(2)
                 }
    MAX-ACCESS   read-only
    STATUS       current
    DESCRIPTION 
        "The value of tmnxVrrpOperState gives the operational state 
         of the VRRP virtual router instance."
    ::= { tmnxVrrpOperEntry 1 }

tmnxVrrpOperVirtualMacAddr  OBJECT-TYPE
    SYNTAX       MacAddress
    MAX-ACCESS   read-create
    STATUS       current
    DESCRIPTION 
        "The value of tmnxVrrpOperVirtualMacAddr specifies the configured
         virtual MAC address used in ARP responses when the VRRP virtual
         router instance is operating as a master."
    DEFVAL { '000000000000'H }
    ::= { tmnxVrrpOperEntry 2 }

tmnxVrrpOperMismatchDiscard  OBJECT-TYPE
    SYNTAX       TruthValue
    MAX-ACCESS   read-create
    STATUS       current
    DESCRIPTION 
        "The tmnxVrrpOperMismatchDiscard is valid only if the VRRP virtual 
         router instance associated with this entry is a non-owner.
         
         The value of tmnxVrrpOperMismatchDiscard specifies the action taken 
         when IP Address List within a received VRRP Advertisement message 
         does not match the configured virtual router IP addresses. If the 
         value is 'true', then such VRRP messages are discarded."
    DEFVAL { false }
    ::= { tmnxVrrpOperEntry 3 }

tmnxVrrpOperPingReply  OBJECT-TYPE
    SYNTAX       TruthValue
    MAX-ACCESS   read-create
    STATUS       current
    DESCRIPTION 
        "The tmnxVrrpOperPingReply is valid only if the VRRP virtual router
         instance associated with this entry is a non-owner.
         
         By setting tmnxVrrpOperPingReply to 'true', a non-owner master is 
         enabled to reply to ICMP Echo requests directed to the virtual 
         router instance IP addresses. 
 
         A non-owner backup virtual router never responds to such ICMP echo 
         requests irrespective of the value of tmnxVrrpOperPingReply."
    DEFVAL { false }
    ::= { tmnxVrrpOperEntry 4 }

tmnxVrrpOperTelnetReply  OBJECT-TYPE
    SYNTAX       TruthValue
    MAX-ACCESS   read-create
    STATUS       current
    DESCRIPTION 
        "The tmnxVrrpOperTelnetReply is valid only if the VRRP virtual router
         instance associated with this entry is a non-owner.
         
         By setting tmnxVrrpOperTelnetReply to 'true', a non-owner master is
         enabled to reply to TCP Port 23 Telnet Requests directed to the 
         virtual router instance IP addresses. 
         
         A non-owner backup virtual router never responds to such Telnet  
         requests irrespective of the value of tmnxVrrpOperTelnetReply."
    DEFVAL { false }
    ::= { tmnxVrrpOperEntry 5 }

tmnxVrrpOperSshReply  OBJECT-TYPE
    SYNTAX       TruthValue
    MAX-ACCESS   read-create
    STATUS       current
    DESCRIPTION  
        "The tmnxVrrpOperSshReply is valid only if the VRRP virtual router
         instance associated with this entry is a non-owner.
         
         By setting tmnxVrrpOperSshReply to 'true', a non-owner master is
         enabled to reply to SSH Requests directed to the virtual router 
         instance IP addresses. 
         
         A non-owner backup virtual router never responds to such SSH  
         requests irrespective of the value of tmnxVrrpOperSshReply."
    DEFVAL { false }
    ::= { tmnxVrrpOperEntry 6 }

tmnxVrrpOperPolicyId  OBJECT-TYPE
    SYNTAX       Unsigned32 
    MAX-ACCESS   read-create
    STATUS       current
    DESCRIPTION 
        "The tmnxVrrpOperPolicyId identifies the VRRP Priority Control policy 
         associated with the VRRP virtual router instance. This policy must 
         be a valid policy in the tmnxVrrpPolicyTable. 
         A value of 0 indicates that no Priority Control policy is associated
         with the virtual router instance."
    DEFVAL { 0 }
    ::= { tmnxVrrpOperEntry 7 }

tmnxVrrpOperInUsePriority  OBJECT-TYPE
    SYNTAX       Unsigned32 (0..255)
    MAX-ACCESS   read-only
    STATUS       current
    DESCRIPTION 
        "The tmnxVrrpOperInUsePriority indicates the current in-use priority
         associated with the VRRP virtual router instance."
    ::= { tmnxVrrpOperEntry 8 }

tmnxVrrpOperMasterSince  OBJECT-TYPE
    SYNTAX       TimeStamp
    MAX-ACCESS   read-only
    STATUS       current
    DESCRIPTION 
        "The tmnxVrrpOperMasterSince, in case of a virtual router which 
         is the current master, is the sysUpTime when operational state 
         (vrrpOperState) of the virtual router changed to master(3).
         In case of a backup virtual router, this value specifies the
         sysUpTime when it received the first VRRP advertisement message
         from the virtual router which is the current master."
    ::= { tmnxVrrpOperEntry 9 }

tmnxVrrpOperMasterPriority  OBJECT-TYPE
    SYNTAX       Unsigned32 (0..255)
    MAX-ACCESS   read-only
    STATUS       current
    DESCRIPTION 
        "The value of tmnxVrrpOperMasterPriority indicates the priority of
         the virtual router instance which is the current master" 
    ::= { tmnxVrrpOperEntry 10 }

tmnxVrrpOperOwner  OBJECT-TYPE
    SYNTAX       TruthValue
    MAX-ACCESS   read-create
    STATUS       current
    DESCRIPTION 
        "The value of tmnxVrrpOperOwner specifies whether or not the virtual
         router instance has been configured as an owner. If 'true', then 
         the virtual router instance is an 'owner', if 'false' then the
         instance is a 'non-owner'."
    DEFVAL { false }
    ::= { tmnxVrrpOperEntry 11 }

tmnxVrrpOperMasterDownInterval  OBJECT-TYPE
    SYNTAX       TimeInterval
    UNITS        "milliseconds"
    MAX-ACCESS   read-only
    STATUS       current
    DESCRIPTION 
        "The value of tmnxVrrpOperMasterDownInterval indicates the time
         interval for the backup router to declare the master as down.  
         It is calculated as
                (3 * Advertisement_Interval) + Skew_time
         where Skew_Time is calculated as
                (256 - Priority) / 256
        " 
    REFERENCE 
        "www.ietf.org/internet-drafts/draft-ietf-vrrp-spec-v2-06.txt"  
    ::= { tmnxVrrpOperEntry 12 }

tmnxVrrpOperMasterDownTimer  OBJECT-TYPE
    SYNTAX       TimeInterval
    UNITS        "milliseconds"
    MAX-ACCESS   read-only
    STATUS       current
    DESCRIPTION 
        "The value of tmnxVrrpOperMasterDownTimer indicates the current
         value of the Master Down Timer. 

         When a backup router receives a VRRP advertisement from a master,
         it resets this timer to the value of the Master Down Interval 
         and begins to count down. If the backup router does not receive
         an advertisement till this timer times out, it will assume that
         the master is down and will declare itself to be the master." 
    REFERENCE    
        "www.ietf.org/internet-drafts/draft-ietf-vrrp-spec-v2-06.txt"
    ::= { tmnxVrrpOperEntry 13 }

tmnxVrrpOperAdvIntervalInherit  OBJECT-TYPE
    SYNTAX       TruthValue
    MAX-ACCESS   read-create
    STATUS       current
    DESCRIPTION 
        "The tmnxVrrpOperAdvIntervalInherit object is valid only if the VRRP
         virtual router instance associated with this entry is a non-owner.
         
         When the VRRP instance is operating as a backup and the value of
         tmnxVrrpOperAdvIntervalInherit is set to 'true', the master down 
         timer is indirectly derived from the value in the advertisement 
         interval field of the VRRP message received from the current master. 
         
         When the VRRP instance is operating as a backup and the value of
         tmnxVrrpOperAdvIntervalInherit is set to 'false', the configured 
         advertisement interval (vrrpOperAdvertisementInterval) is matched
         against the value in the advertisement interval field of the VRRP
         message received from the current master. If the two values do not 
         match then the VRRP advertisement is discarded

         When the VRRP instance is operating as a master, the value of 
         tmnxVrrpOperAdvIntervalInherit has no effect."
    DEFVAL { false }
    ::= { tmnxVrrpOperEntry 14 }

tmnxVrrpOperInUseAdvInterval  OBJECT-TYPE
    SYNTAX       Integer32
    MAX-ACCESS   read-only
    STATUS       current
    DESCRIPTION 
        "The tmnxVrrpOperInUseAdvInterval indicates the operational value
         for the advertisement interval. 

         When the VRRP instance is operating as a master, the value
         of tmnxVrrpOperInUseAdvInterval is the same as the value of 
         vrrpOperAdvertisementInterval.
         
         When the VRRP instance is operating as a backup and the value of
         tmnxVrrpOperAdvIntervalInherit is set to 'true', the total value of
         tmnxVrrpOperInUseAdvInterval and tmnxVrrpOperInUseAdvIntlMilSec 
         equals the value in the advertisement interval field of the VRRP 
         Advertisement message received from the current master.
         
         When the VRRP instance is operating as a backup and the value of
         tmnxVrrpOperAdvIntervalInherit is set to 'false', the value of
         tmnxVrrpOperInUseAdvInterval is the same as the value of 
         vrrpOperAdvertisementInterval.
         
         To get the total interval time, add the value for tmnxVrrpOperInUseAdvInterval 
         in seconds and tmnxVrrpOperInUseAdvIntlMilSec in milliseconds. 
         Only the master router sends VRRP advertisements."
    ::= { tmnxVrrpOperEntry 15 }
    
tmnxVrrpOperTracerouteReply  OBJECT-TYPE
    SYNTAX       TruthValue
    MAX-ACCESS   read-create
    STATUS       current
    DESCRIPTION 
        "The tmnxVrrpOperTracerouteReply is valid only if the VRRP virtual router
         instance associated with this entry is a non-owner.
         
         By setting tmnxVrrpOperTracerouteReply to 'true', a non-owner master is 
         enabled to reply to traceroute requests directed to the virtual 
         router instance IP addresses. 
 
         A non-owner backup virtual router never responds to such traceroute 
         requests irrespective of the value of tmnxVrrpOperTracerouteReply."
    DEFVAL { false }
    ::= { tmnxVrrpOperEntry 16 }

tmnxVrrpOperStandbyFwding OBJECT-TYPE
    SYNTAX       TruthValue
    MAX-ACCESS   read-create
    STATUS       current
    DESCRIPTION 
        "The value of tmnxVrrpOperStandbyFwding specifies
         whether this vrrp instance allows forwarding packets to
         standby router.
         
         The value 'false' specifies that a standby router should
         not forward traffic sent to virtual router's MAC address.
         However, the standby router should forward traffic sent
         to the standby routers real MAC address.
 
         The value 'true' specifies that a standby router should
         forward all traffic."
    DEFVAL { false }
    ::= { tmnxVrrpOperEntry 17 }   

tmnxVrrpOperAdvIntervalMilSec OBJECT-TYPE
    SYNTAX       Unsigned32 (0|100..900)
    UNITS        "milliseconds"
    MAX-ACCESS   read-create
    STATUS       current
    DESCRIPTION
        "The value of tmnxVrrpOperAdvIntervalMilSec specifies the milli seconds time 
         interval between sending advertisement messages. To get the total interval
         time, add the value for vrrpOperAdvertisementInterval in seconds and 
         tmnxVrrpOperAdvIntervalMilSec in milliseconds. Only the master router
         sends VRRP advertisements."
    DEFVAL { 0 }
    ::= { tmnxVrrpOperEntry 18 }

tmnxVrrpOperInUseAdvIntlMilSec  OBJECT-TYPE
    SYNTAX       Unsigned32 (0|100..900)
    MAX-ACCESS   read-only
    STATUS       current
    DESCRIPTION 
        "The tmnxVrrpOperInUseAdvIntlMilSec indicates the operational value
         for the advertisement milli second interval. 

         When the VRRP instance is operating as a master, the value
         of tmnxVrrpOperInUseAdvIntlMilSec is the same as the value of 
         tmnxVrrpOperAdvIntervalMilSec.
         
         When the VRRP instance is operating as a backup and the value of
         tmnxVrrpOperAdvIntervalInherit is set to 'true', the total value of
         tmnxVrrpOperInUseAdvInterval and tmnxVrrpOperInUseAdvIntlMilSec 
         equals the value in the advertisement interval field of the VRRP 
         Advertisement message received from the current master.

         When the VRRP instance is operating as a backup and the value of
         tmnxVrrpOperAdvIntervalInherit is set to 'false', the value of
         tmnxVrrpOperInUseAdvIntlMilSec is the same as the value of 
         tmnxVrrpOperAdvIntervalMilSec.

         To get the total interval time, add the value for tmnxVrrpOperInUseAdvInterval 
         in seconds and tmnxVrrpOperInUseAdvIntlMilSec in milliseconds. 
         Only the master router sends VRRP advertisements."
    ::= { tmnxVrrpOperEntry 19 }

tmnxVrrpOperInitDelay  OBJECT-TYPE
    SYNTAX       Unsigned32 (0..65535)
    UNITS        "seconds"
    MAX-ACCESS   read-create
    STATUS       current
    DESCRIPTION
        "The value of tmnxVrrpOperInitDelay specifies 
         the initialization delay timer for VRRP, in seconds."
    DEFVAL { 0 } 
    ::= { tmnxVrrpOperEntry 20 }

tmnxVrrpOperInitTimer  OBJECT-TYPE
    SYNTAX       TimeInterval
    UNITS        "milliseconds"
    MAX-ACCESS   read-only
    STATUS       current
    DESCRIPTION
        "The value of tmnxVrrpOperInitTimer indicates the current value of
         initialization delay timer for VRRP, in milli-seconds."
    ::= { tmnxVrrpOperEntry 21 }

tmnxVrrpOperDownReason  OBJECT-TYPE
    SYNTAX  INTEGER {
                     unknown (0),
                     notActive (1),       -- row-status not active
                     adminDown (2),
                     ifDown (3),
                     invalidMac (4)
                 }
    MAX-ACCESS   read-only
    STATUS       current
    DESCRIPTION 
        "The value of tmnxVrrpOperDownReason indicates the reason for the
         operational state to be 'down'."
    ::= { tmnxVrrpOperEntry 22 }

tmnxVrrpOperPassive OBJECT-TYPE
    SYNTAX       TruthValue
    MAX-ACCESS   read-create
    STATUS       current
    DESCRIPTION 
        "The tmnxVrrpOperPassive specifies whether to suppress the
         transmit/receive of keep-alive messages."
    DEFVAL { false }
    ::= { tmnxVrrpOperEntry 23 }

tmnxVrrpOperRowStatus OBJECT-TYPE
    SYNTAX       RowStatus
    MAX-ACCESS   read-create
    STATUS       current
    DESCRIPTION
        "The tmnxVrrpOperRowStatus is used for creation or deletion of entries
         in this table."
    ::= { tmnxVrrpOperEntry 24 }

tmnxVrrpOperGroupName OBJECT-TYPE
    SYNTAX      TNamedItemOrEmpty
    MAX-ACCESS  read-create
    STATUS      current
    DESCRIPTION
        "The tmnxVrrpOperGroupName specifies the operational group associated with
        the VRRP."
    DEFVAL { ''H}
    ::= { tmnxVrrpOperEntry 25 }
-- ***************************************************************************
-- Augmentation of the vrrpRouterStatsTable in VRRP-MIB
-- ***************************************************************************

tmnxVrrpRouterStatsTable OBJECT-TYPE
    SYNTAX       SEQUENCE OF TmnxVrrpRouterStatsEntry
    MAX-ACCESS   not-accessible
    STATUS       current
    DESCRIPTION  
        "The tmnxVrrpRouterStatsTable provides an extension of the 
         vrrpRouterStatsTable in the VRRP-MIB.

         Use of AUGMENTS clause implies a one-to-one dependent relationship 
         between the base table, vrrpRouterStatsTable, and the augmenting 
         table, tmnxVrrpRouterStatsTable. This in effect extends the 
         vrrpRouterStatsTable with additional columns."
    ::= { tmnxVrrpObjects 2 }

tmnxVrrpRouterStatsEntry OBJECT-TYPE
    SYNTAX       TmnxVrrpRouterStatsEntry
    MAX-ACCESS   not-accessible
    STATUS       current
    DESCRIPTION 
        "Each row entry in the tmnxVrrpRouterStatsTable represents additional 
         columns in the vrrpRouterStatsTable for statistics specific to the
         Nokia SROS series VRRP implementation."
    AUGMENTS { vrrpRouterStatsEntry }
    ::= { tmnxVrrpRouterStatsTable 1 }

TmnxVrrpRouterStatsEntry ::= 
    SEQUENCE {
        tmnxVrrpStatsAdvertiseSent                 Counter32,
        tmnxVrrpStatsPreemptEvents                 Counter32,
        tmnxVrrpStatsPreemptedEvents               Counter32,
        tmnxVrrpStatsMasterChanges                 Counter32,
        tmnxVrrpStatsAdvertiseIntervalDiscards     Counter32,
        tmnxVrrpStatsAddressListDiscards           Counter32,
        tmnxVrrpStatsTotalDiscards                 Counter32
    }

tmnxVrrpStatsAdvertiseSent  OBJECT-TYPE
    SYNTAX       Counter32
    MAX-ACCESS   read-only
    STATUS       current
    DESCRIPTION 
        "The total number of VRRP advertisements sent by this virtual 
         router."
    ::= { tmnxVrrpRouterStatsEntry 1 }    

tmnxVrrpStatsPreemptEvents  OBJECT-TYPE
    SYNTAX       Counter32
    MAX-ACCESS   read-only
    STATUS       current
    DESCRIPTION 
        "The value for tmnxVrrpStatsPreemptEvents indicates the total
         number of times the virtual router has preempted another
         non-owner master with lower priority."
    ::= { tmnxVrrpRouterStatsEntry 2 }    

tmnxVrrpStatsPreemptedEvents  OBJECT-TYPE
    SYNTAX       Counter32
    MAX-ACCESS   read-only
    STATUS       current
    DESCRIPTION 
        "The value for tmnxVrrpStatsPreemptedEvents indicates the total
         number of times the virtual router has been preempted by another
         non-owner master with higher priority."
    ::= { tmnxVrrpRouterStatsEntry 3 }    

tmnxVrrpStatsMasterChanges  OBJECT-TYPE
    SYNTAX       Counter32
    MAX-ACCESS   read-only
    STATUS       current
    DESCRIPTION 
        "The value for tmnxVrrpStatsMasterChanges indicates the total
         number of times the virtual router has seen the master virtual
         router change."
    ::= { tmnxVrrpRouterStatsEntry 4 }

tmnxVrrpStatsAdvertiseIntervalDiscards OBJECT-TYPE
    SYNTAX       Counter32
    MAX-ACCESS   read-only
    STATUS       current
    DESCRIPTION
        "The total number of VRRP advertisement packets discarded
         because the advertisement interval in the received packet 
         was different than the one configured for the local virtual 
         router."
    ::= { tmnxVrrpRouterStatsEntry 5 }

tmnxVrrpStatsAddressListDiscards OBJECT-TYPE
    SYNTAX       Counter32
    MAX-ACCESS   read-only
    STATUS       current
    DESCRIPTION
        "The total number of VRRP advertisement packets discarded
         because the address list did not match the locally configured 
         list for the virtual router."
    ::= { tmnxVrrpRouterStatsEntry 6 }

tmnxVrrpStatsTotalDiscards OBJECT-TYPE
    SYNTAX       Counter32
    MAX-ACCESS   read-only
    STATUS       current
    DESCRIPTION
        "The total number of VRRP advertisement packets discarded
         for any reason. This includes the packets discarded due to
         advertise interval mismatch and address list mismatch."
    ::= { tmnxVrrpRouterStatsEntry 7 }


-- ***************************************************************************
-- TIMETRA-VRRP-MIB Master Table
-- ***************************************************************************

tmnxVrrpRouterMasterTable OBJECT-TYPE
    SYNTAX       SEQUENCE OF TmnxVrrpRouterMasterEntry
    MAX-ACCESS   not-accessible
    STATUS       current
    DESCRIPTION  
        "The tmnxVrrpRouterMasterTable is a read-only table which provides
         a list of the master primary addresses that have been seen by the
         VRRP virtual router instance. Only the most recent 32 masters are 
         listed by this table."
    ::= { tmnxVrrpObjects 3 }

tmnxVrrpRouterMasterEntry OBJECT-TYPE
    SYNTAX       TmnxVrrpRouterMasterEntry
    MAX-ACCESS   not-accessible
    STATUS       current
    DESCRIPTION 
        "Each row entry in the tmnxVrrpRouterMasterTable represents the
         primary address of a VRRP virtual router instance that has 
         become the master as seen by the virtual router instance identified
         by ifIndex and vrrpOperVrId."
    INDEX { ifIndex, vrrpOperVrId, tmnxVrrpRouterMasterPrimaryAddr }
    ::= { tmnxVrrpRouterMasterTable 1 }

TmnxVrrpRouterMasterEntry ::= 
    SEQUENCE {
        tmnxVrrpRouterMasterPrimaryAddr            IpAddress,
        tmnxVrrpRouterMasterLastSeen               TimeStamp,
        tmnxVrrpRouterMasterMessageCount           Counter32,
        tmnxVrrpRouterMasterAuthSequence           Integer32,
        tmnxVrrpRouterMasterIPListMatch            TruthValue      
    }

tmnxVrrpRouterMasterPrimaryAddr  OBJECT-TYPE
    SYNTAX       IpAddress
    MAX-ACCESS   not-accessible
    STATUS       current
    DESCRIPTION 
        "The value of tmnxVrrpRouterMasterPrimaryAddr gives the primary 
         address of the virtual router that became a master as seen by the
         virtual router instance identified by ifIndex and vrrpOperVrId."
    ::= { tmnxVrrpRouterMasterEntry 1 }    

tmnxVrrpRouterMasterLastSeen  OBJECT-TYPE
    SYNTAX       TimeStamp
    MAX-ACCESS   read-only
    STATUS       current
    DESCRIPTION 
        "The value for tmnxVrrpRouterMasterLastSeen indicates the sysUpTime
         when the master was last seen by this virtual router instance. In 
         other words it is the timestamp of the last advertisement message 
         that was received from that master."
    ::= { tmnxVrrpRouterMasterEntry 2 }    

tmnxVrrpRouterMasterMessageCount  OBJECT-TYPE
    SYNTAX       Counter32
    MAX-ACCESS   read-only
    STATUS       current
    DESCRIPTION 
        "The value for tmnxVrrpRouterMasterMessageCount indicates the total
         number of VRRP advertisement messages that have been received 
         from the master."
    ::= { tmnxVrrpRouterMasterEntry 3 }    

tmnxVrrpRouterMasterAuthSequence  OBJECT-TYPE
    SYNTAX       Integer32
    MAX-ACCESS   read-only
    STATUS       current
    DESCRIPTION 
        "The value for tmnxVrrpRouterMasterAuthSequence indicates the last
         sequence number seen in the IP Authentication header of the 
         advertisement messages received from the master.
         A negative value implies that the master was not being 
         authenticated via IP authentication header."
    ::= { tmnxVrrpRouterMasterEntry 4 }   

tmnxVrrpRouterMasterIPListMatch  OBJECT-TYPE
    SYNTAX       TruthValue
    MAX-ACCESS   read-only
    STATUS       current
    DESCRIPTION 
        "The value for tmnxVrrpRouterMasterIPListMatch indicates whether or not
         the IP address list in the advertisement messages received from 
         the master matched the configured virtual router IP address list."
    ::= { tmnxVrrpRouterMasterEntry 5 }   


-- ***************************************************************************
-- TIMETRA-VRRP-MIB BFD Interface Table
-- ***************************************************************************

tmnxVrrpAssoBfdIntfTblLastChgd OBJECT-TYPE
    SYNTAX      TimeStamp
    MAX-ACCESS  read-only
    STATUS      obsolete
    DESCRIPTION
        "Timestamp of the last change to the tmnxVrrpAssoBfdIntfTable
         either from adding a row or removing a row."
    ::= { tmnxVrrpObjects 4 }

tmnxVrrpAssoBfdIntfTable OBJECT-TYPE
    SYNTAX       SEQUENCE OF TmnxVrrpAssoBfdIntfEntry
    MAX-ACCESS   not-accessible
    STATUS       obsolete
    DESCRIPTION  
        "The tmnxVrrpAssoBfdIntfTable is a read-only table which provides
         a list of the BFD interfaces associated with the corresponding
         VRRP virtual router instance.

         The BFD interface provides a fast mechanism for changing the state
         of an VRRP virtual router instance riding on the same subnet.
         
         The tmnxVrrpAssoBfdIntfTable is obsoleted and is replaced by
         tVrrpAssoBfdIntfTable."
    ::= { tmnxVrrpObjects 5 }

tmnxVrrpAssoBfdIntfEntry OBJECT-TYPE
    SYNTAX       TmnxVrrpAssoBfdIntfEntry
    MAX-ACCESS   not-accessible
    STATUS       obsolete
    DESCRIPTION 
        "Each row entry in the tmnxVrrpAssoBfdIntfTable represents the
         BFD interface associated with VRRP virtual router instance
         identified by ifIndex and vrrpOperVrId."
    INDEX { ifIndex, vrrpOperVrId, tmnxVrrpAssoBfdIntfSvcId,
            tmnxVrrpAssoBfdIntfIfName, tmnxVrrpAssoBfdIntfDestIpType,
            tmnxVrrpAssoBfdIntfDestIp }
    ::= { tmnxVrrpAssoBfdIntfTable 1 }

TmnxVrrpAssoBfdIntfEntry ::= 
    SEQUENCE {
        tmnxVrrpAssoBfdIntfSvcId            TmnxServId,
        tmnxVrrpAssoBfdIntfIfName           TNamedItem,
        tmnxVrrpAssoBfdIntfDestIpType       InetAddressType,
        tmnxVrrpAssoBfdIntfDestIp           InetAddress,
        tmnxVrrpAssoBfdIntfRowStatus        RowStatus,
        tmnxVrrpAssoBfdIntfLastChgd         TimeStamp,
        tmnxVrrpAssoBfdIntfSrcIpType        InetAddressType,
        tmnxVrrpAssoBfdIntfSrcIp            InetAddress,
        tmnxVrrpAssoBfdIntfSessOperState    TmnxVrrpAssoBfdIntfSessOperState
    }

tmnxVrrpAssoBfdIntfSvcId OBJECT-TYPE
    SYNTAX       TmnxServId
    MAX-ACCESS   not-accessible
    STATUS       obsolete
    DESCRIPTION
        "The value of tmnxVrrpAssoBfdIntfSvcId specifies the service
         ID of the interface running BFD."
    ::= { tmnxVrrpAssoBfdIntfEntry 1 }

tmnxVrrpAssoBfdIntfIfName OBJECT-TYPE
    SYNTAX       TNamedItem
    MAX-ACCESS   not-accessible
    STATUS       obsolete
    DESCRIPTION         
        "The value of tmnxVrrpAssoBfdIntfIfName specifies the name of the
         interface running BFD."
    ::= { tmnxVrrpAssoBfdIntfEntry 2 }

tmnxVrrpAssoBfdIntfDestIpType OBJECT-TYPE
    SYNTAX       InetAddressType
    MAX-ACCESS   not-accessible
    STATUS       obsolete
    DESCRIPTION
        "The value of tmnxVrrpAssoBfdIntfDestIpType specifies the address type
         of tmnxVrrpAssoBfdIntfDestIp object."
    ::= { tmnxVrrpAssoBfdIntfEntry 3 }

tmnxVrrpAssoBfdIntfDestIp OBJECT-TYPE
    SYNTAX       InetAddress (SIZE (0|4|16|20))
    MAX-ACCESS   not-accessible
    STATUS       obsolete
    DESCRIPTION
        "The value of tmnxVrrpAssoBfdIntfDestIp specifies the destination
         IP address on the interface running BFD."
    ::= { tmnxVrrpAssoBfdIntfEntry 4 }

tmnxVrrpAssoBfdIntfRowStatus  OBJECT-TYPE
    SYNTAX       RowStatus
    MAX-ACCESS   read-create
    STATUS       obsolete
    DESCRIPTION 
        "This object tmnxVrrpAssoBfdIntfRowStatus is used for creation or
         deletion of entries in the tmnxVrrpAssoBfdIntfEntry. Deletion of an
         entry in this table will not succeed if it is obsoletely associated
         with any VRRP virtual router instance."
    ::= { tmnxVrrpAssoBfdIntfEntry 5 }    

tmnxVrrpAssoBfdIntfLastChgd  OBJECT-TYPE
    SYNTAX       TimeStamp
    MAX-ACCESS   read-only
    STATUS       obsolete
    DESCRIPTION 
        "The value of tmnxVrrpAssoBfdIntfLastChgd specifies the
         time stamp of the last change to this row of this table."
    ::= { tmnxVrrpAssoBfdIntfEntry 6 } 
   
tmnxVrrpAssoBfdIntfSrcIpType OBJECT-TYPE
    SYNTAX       InetAddressType
    MAX-ACCESS   read-only
    STATUS       obsolete
    DESCRIPTION
        "The value of tmnxVrrpAssoBfdIntfSrcIpType indicates the address type
         of tmnxVrrpAssoBfdIntfSrcIp object."
    ::= { tmnxVrrpAssoBfdIntfEntry 7 }

tmnxVrrpAssoBfdIntfSrcIp OBJECT-TYPE
    SYNTAX       InetAddress (SIZE (0|4|16|20))
    MAX-ACCESS   read-only
    STATUS       obsolete
    DESCRIPTION
        "The value of tmnxVrrpAssoBfdIntfSrcIp indicates the source
         IP address on the interface running BFD."
    ::= { tmnxVrrpAssoBfdIntfEntry 8 }

tmnxVrrpAssoBfdIntfSessOperState OBJECT-TYPE
    SYNTAX       TmnxVrrpAssoBfdIntfSessOperState
    MAX-ACCESS   read-only
    STATUS       obsolete
    DESCRIPTION
        "The value of tmnxVrrpAssoBfdIntfSessOperState indicates the operational
         state of the BFD session the VRRP virtual router instance is relying
         upon for its fast triggering mechanism."
    ::= { tmnxVrrpAssoBfdIntfEntry 9 }


-- ***************************************************************************
-- TIMETRA-VRRP-MIB Policy objects
-- ***************************************************************************

-- ***************************************************************************
-- The Nokia SROS series VRRP Policy Table
-- ***************************************************************************

tmnxVrrpPolicyTable OBJECT-TYPE
    SYNTAX       SEQUENCE OF TmnxVrrpPolicyEntry
    MAX-ACCESS   not-accessible
    STATUS       current
    DESCRIPTION  
        "The tmnxVrrpPolicyTable contains a list of VRRP Priority Control 
         Policies."
    ::= { tmnxVrrpPolicyObjects 1 }

tmnxVrrpPolicyEntry OBJECT-TYPE
    SYNTAX       TmnxVrrpPolicyEntry
    MAX-ACCESS   not-accessible
    STATUS       current
    DESCRIPTION 
        "Each row entry in the tmnxVrrpPolicyTable represents an instance 
         of a Priority Control Policy used to override or adjust the base 
         priority value of a VRRP virtual router instance depending on 
         events or conditions within the chassis.
    
         Entries can be created and deleted via SNMP SET operations using
         tmnxVrrpPolicyRowStatus."
    INDEX { tmnxVrrpPolicyId }
    ::= { tmnxVrrpPolicyTable 1 }

TmnxVrrpPolicyEntry ::= 
    SEQUENCE {
        tmnxVrrpPolicyId                        TmnxVrrpPolicyID,
        tmnxVrrpPolicyRowStatus                 RowStatus,
        tmnxVrrpPolicyDescription               TItemDescription, 
        tmnxVrrpPolicyDeltaInUseLimit           TmnxVrrpPriority,
        tmnxVrrpPolicyReferenceCount            Unsigned32,
        tmnxVrrpPolicyCurrentExplicit           TmnxVrrpPriority,
        tmnxVrrpPolicyCurrentDeltaSum           TmnxVrrpPriority,
        tmnxVrrpPolicySvcContext                TmnxServId,
        tmnxVrrpPolicyAdminState                TmnxAdminState
    }

tmnxVrrpPolicyId  OBJECT-TYPE
    SYNTAX       TmnxVrrpPolicyID
    MAX-ACCESS   not-accessible
    STATUS       current
    DESCRIPTION 
        "The index value tmnxVrrpPolicyId uniquely identifies a policy-id 
         to be used when creating a Priority Control Policy."
    ::= { tmnxVrrpPolicyEntry 1 } 

tmnxVrrpPolicyRowStatus  OBJECT-TYPE
    SYNTAX       RowStatus
    MAX-ACCESS   read-create
    STATUS       current
    DESCRIPTION 
        "tmnxVrrpPolicyRowStatus is used for creation or deletion of 
         entries in the tmnxVrrpPolicyTable. Deletion of an entry in 
         this table will not succeed if it is currently associated with 
         any VRRP virtual router instance."
    ::= { tmnxVrrpPolicyEntry 2 } 

tmnxVrrpPolicyDescription  OBJECT-TYPE
    SYNTAX       TItemDescription
    MAX-ACCESS   read-create
    STATUS       current
    DESCRIPTION 
        "The value of tmnxVrrpPolicyDescription specifies a user provided
         description for the VRRP Policy. It can consist of any printable
         ASCII characters."
    DEFVAL { ''H }
    ::= { tmnxVrrpPolicyEntry 3 }

tmnxVrrpPolicyDeltaInUseLimit  OBJECT-TYPE
    SYNTAX       TmnxVrrpPriority (1..254)
    MAX-ACCESS   read-create
    STATUS       current
    DESCRIPTION 
        "The value of tmnxVrrpPolicyDeltaInUseLimit specifies the 
         delta-in-use-limit for a VRRP policy. Once the total sum of 
         all delta events has been calculated and subtracted from the 
         base-priority of the virtual router, the result is compared
         to the delta-in-use-limit value. If the result is less 
         than this value, the delta-in-use-limit value is used as the 
         virtual router in-use priority value. If an explicit priority 
         control event overrides the delta priority control events, the 
         delta-in-use-limit has no effect.

         Setting tmnxVrrpPolicyDeltaInUseLimit to 0 and allowing the 
         sum of the delta priority control events to reduce the virtual 
         router's in-use-priority to 0, can prevented it from 
         becoming or staying master."
    DEFVAL { 1 }
    ::= { tmnxVrrpPolicyEntry 4 }

tmnxVrrpPolicyReferenceCount  OBJECT-TYPE
    SYNTAX       Unsigned32
    MAX-ACCESS   read-only
    STATUS       current
    DESCRIPTION 
        "The value of tmnxVrrpPolicyReferenceCount indicates the number
         of virtual router instances to which the policy has been applied. 
         The policy cannot be deleted unless this value is 0."
    ::= { tmnxVrrpPolicyEntry 5 }

tmnxVrrpPolicyCurrentExplicit  OBJECT-TYPE
    SYNTAX       TmnxVrrpPriority
    MAX-ACCESS   read-only
    STATUS       current
    DESCRIPTION 
        "When multiple explicitly defined events associated with the 
         priority control policy happen simultaneously, the lowest value 
         of all the current explicit priorities will be used as the 
         in-use priority for the virtual router. This value is specified 
         by the variable tmnxVrrpPolicyCurrentExplicit."
    ::= { tmnxVrrpPolicyEntry 6 }

tmnxVrrpPolicyCurrentDeltaSum  OBJECT-TYPE
    SYNTAX       TmnxVrrpPriority
    MAX-ACCESS   read-only
    STATUS       current
    DESCRIPTION 
        "When multiple delta events associated with the priority control 
         policy happen simultaneously, the sum of the priorites of all 
         these delta events is specified by the variable 
         tmnxVrrpPolicyCurrentDeltaSum. This sum is subtracted from the 
         base priority of the virtual router to give the in-use priority."
    ::= { tmnxVrrpPolicyEntry 7 }

tmnxVrrpPolicySvcContext       OBJECT-TYPE
    SYNTAX      TmnxServId
    MAX-ACCESS  read-create
    STATUS      current
    DESCRIPTION
        "The value of tmnxVrrpPolicySvcContext specifies the service  ID 
         to which this policy applies. A value of '0' means that this policy
         does not apply to a service, but to the base router instance. This 
         object can only be set at row creation time."
    DEFVAL      { 0 }
    ::= { tmnxVrrpPolicyEntry 8 }

tmnxVrrpPolicyAdminState       OBJECT-TYPE
    SYNTAX      TmnxAdminState
    MAX-ACCESS  read-create
    STATUS      current
    DESCRIPTION
        "The value of tmnxVrrpPolicyAdminState specifies the adminstrative
         status of this VRRP policy."
    DEFVAL      { inService }
    ::= { tmnxVrrpPolicyEntry 9 }

-- ***************************************************************************
-- The Nokia SROS series VRRP Port Down Priority Event Table
-- ***************************************************************************

tmnxVrrpPortDownEventTable OBJECT-TYPE
    SYNTAX       SEQUENCE OF TmnxVrrpPortDownEventEntry
    MAX-ACCESS   not-accessible
    STATUS       current
    DESCRIPTION  
        "The tmnxVrrpPortDownEventTable contains a list of Port Down 
         Priority Events."
    ::= { tmnxVrrpPolicyObjects 2 }

tmnxVrrpPortDownEventEntry OBJECT-TYPE
    SYNTAX       TmnxVrrpPortDownEventEntry
    MAX-ACCESS   not-accessible
    STATUS       current
    DESCRIPTION 
        "Each row entry in the tmnxVrrpPortDownEventTable represents 
         an instance of a Port Down Priority Event used to override 
         or adjust the base priority value of a VRRP virtual router 
         instance depending on the operational state of the event.
    
         Entries can be created and deleted via SNMP SET operations 
         using tmnxVrrpPortDownEventRowStatus."
    INDEX { tmnxVrrpPolicyId, 
            tmnxVrrpPortDownEventPortId }
    ::= { tmnxVrrpPortDownEventTable 1 }

TmnxVrrpPortDownEventEntry ::= 
    SEQUENCE {
        tmnxVrrpPortDownEventPortId              TmnxPortID,
        tmnxVrrpPortDownEventRowStatus           RowStatus,
        tmnxVrrpPortDownEventPriority            TmnxVrrpPriority,
        tmnxVrrpPortDownEventType                TmnxEventType,
        tmnxVrrpPortDownEventHoldSet             TmnxEventHoldSet,        
        tmnxVrrpPortDownEventOperState           TmnxPortDownEventOperState,
        tmnxVrrpPortDownEventHoldSetRemaining    TmnxEventHoldSet,
        tmnxVrrpPortDownEventPrevState           TmnxPortDownEventOperState,
        tmnxVrrpPortDownEventLastTransition      TimeStamp,
        tmnxVrrpPortDownEventSetCounter          Counter32,
        tmnxVrrpPortDownEventInUse               TruthValue,
        tmnxVrrpPortDownEventHoldClear           TmnxEventHoldClear,
        tmnxVrrpPortDownEventHoldClearRemaining  TmnxEventHoldClear
    }

tmnxVrrpPortDownEventPortId  OBJECT-TYPE
    SYNTAX       TmnxPortID
    MAX-ACCESS   not-accessible
    STATUS       current
    DESCRIPTION 
        "The index value tmnxVrrpPortDownEventPortId uniquely identifies 
         the port or channel whose operational state is monitored by this 
         priority control event."
    ::= { tmnxVrrpPortDownEventEntry 1 } 

tmnxVrrpPortDownEventRowStatus  OBJECT-TYPE
    SYNTAX       RowStatus
    MAX-ACCESS   read-create
    STATUS       current
    DESCRIPTION 
        "tmnxVrrpPortDownEventRowStatus is used for the creation or 
         deletion of entries in the tmnxVrrpPortDownEventTable."
    ::= { tmnxVrrpPortDownEventEntry 2 } 

tmnxVrrpPortDownEventPriority  OBJECT-TYPE
    SYNTAX       TmnxVrrpPriority
    MAX-ACCESS   read-create
    STATUS       current
    DESCRIPTION 
        "The value of tmnxVrrpPortDownEventPriority specifies the 
         priority level associated with this event. When the operational 
         state of the event transitions to one of the 'set' states, 
         this value will either be subtracted from the in-use priority 
         (if the event is a 'delta' event) or the in-use priority 
         will be explicitly overridden by this priority value 
         (if the event is an 'explicit' event)."
    DEFVAL { 0 }
    ::= { tmnxVrrpPortDownEventEntry 3 } 

tmnxVrrpPortDownEventType  OBJECT-TYPE
    SYNTAX       TmnxEventType
    MAX-ACCESS   read-create
    STATUS       current
    DESCRIPTION 
        "The value of tmnxVrrpPortDownEventType specifies whether this 
         event is a 'delta' or an 'explicit' event. When the event is 
         'set', the value of tmnxVrrpPortDownEventPriority will be 
         subtracted from the in-use priority in case of a 'delta' event 
         or the in-use priority will be explicitly overridden by the 
         value of tmnxVrrpPortDownEventPriority in case of an 'explicit' 
         event."
    DEFVAL { delta }
    ::= { tmnxVrrpPortDownEventEntry 4 } 

tmnxVrrpPortDownEventHoldSet  OBJECT-TYPE
    SYNTAX       TmnxEventHoldSet
    UNITS        "seconds"
    MAX-ACCESS   read-create
    STATUS       current
    DESCRIPTION 
        "The value of tmnxVrrpPortDownEventHoldSet specifies the 
         configured Hold Set time associated with the event."
    DEFVAL { 0 }
    ::= { tmnxVrrpPortDownEventEntry 5 } 

tmnxVrrpPortDownEventOperState  OBJECT-TYPE
    SYNTAX       TmnxPortDownEventOperState
    MAX-ACCESS   read-only
    STATUS       current
    DESCRIPTION 
        "The value of tmnxVrrpPortDownEventOperState indicates
         the current operational state of the event."
    ::= { tmnxVrrpPortDownEventEntry 6 } 

tmnxVrrpPortDownEventHoldSetRemaining  OBJECT-TYPE
    SYNTAX       TmnxEventHoldSet
    UNITS        "seconds"
    MAX-ACCESS   read-only
    STATUS       current
    DESCRIPTION 
        "The value of tmnxVrrpPortDownEventHoldSetRemaining 
         indicates the current value of the hold-set timer i.e. the
         amount of time remaining before the event will transition 
         into the cleared state."
    ::= { tmnxVrrpPortDownEventEntry 7 } 

tmnxVrrpPortDownEventPrevState  OBJECT-TYPE
    SYNTAX       TmnxPortDownEventOperState 
    MAX-ACCESS   read-only
    STATUS       current
    DESCRIPTION 
        "The value of tmnxVrrpPortDownEventPrevState indicates the
         previous operational state of the event."
    ::= { tmnxVrrpPortDownEventEntry 8 } 

tmnxVrrpPortDownEventLastTransition  OBJECT-TYPE
    SYNTAX       TimeStamp
    MAX-ACCESS   read-only
    STATUS       current
    DESCRIPTION 
        "The value of tmnxVrrpPortDownEventLastTransition indicates
         the sysUpTime when the operational state of the event last 
         changed."
    ::= { tmnxVrrpPortDownEventEntry 9 } 

tmnxVrrpPortDownEventSetCounter  OBJECT-TYPE
    SYNTAX       Counter32
    MAX-ACCESS   read-only
    STATUS       current
    DESCRIPTION 
        "The value of tmnxVrrpPortDownEventSetCounter indicates the
         number of times the event has transitioned to one of the 
         'set' states."
    ::= { tmnxVrrpPortDownEventEntry 10 } 

tmnxVrrpPortDownEventInUse  OBJECT-TYPE
    SYNTAX       TruthValue
    MAX-ACCESS   read-only
    STATUS       current
    DESCRIPTION 
        "If value of tmnxVrrpPortDownEventInUse is 'true', then the 
         event is currently affecting the in-use priority of some virtual
         router."
    ::= { tmnxVrrpPortDownEventEntry 11 } 

tmnxVrrpPortDownEventHoldClear  OBJECT-TYPE
    SYNTAX       TmnxEventHoldClear
    UNITS        "seconds"
    MAX-ACCESS   read-create
    STATUS       current
    DESCRIPTION 
        "The value of tmnxVrrpPortDownEventHoldClear specifies the 
         configured Hold Clear time associated with the event."
    DEFVAL { 0 }
    ::= { tmnxVrrpPortDownEventEntry 12 } 

tmnxVrrpPortDownEventHoldClearRemaining  OBJECT-TYPE
    SYNTAX       TmnxEventHoldClear
    UNITS        "seconds"
    MAX-ACCESS   read-only
    STATUS       current
    DESCRIPTION 
        "The value of tmnxVrrpPortDownEventHoldClearRemaining
         indicates the current value of the hold-clear timer i.e. the
         amount of time remaining before the cleared event will have 
         an effect on the virtual router instance."
    ::= { tmnxVrrpPortDownEventEntry 13 } 



-- ***************************************************************************
-- The Nokia SROS series VRRP Lag Port Down Priority Event Table
-- ***************************************************************************

tmnxVrrpLagPortDownEventTable OBJECT-TYPE
    SYNTAX       SEQUENCE OF TmnxVrrpLagPortDownEventEntry
    MAX-ACCESS   not-accessible
    STATUS       current
    DESCRIPTION  
        "The tmnxVrrpLagPortDownEventTable contains a list of Lag Port 
         Down Priority Events."
    ::= { tmnxVrrpPolicyObjects 3 }

tmnxVrrpLagPortDownEventEntry OBJECT-TYPE
    SYNTAX       TmnxVrrpLagPortDownEventEntry
    MAX-ACCESS   not-accessible
    STATUS       current
    DESCRIPTION 
        "Each row entry in the tmnxVrrpLagPortDownEventTable represents 
         an instance of a Lag Port Down Priority Event used to override 
         or adjust the base priority value of a VRRP virtual router 
         instance depending on the operational state of the event.
    
         Entries can be created and deleted via SNMP SET operations 
         using tmnxVrrpLagPortDownEventRowStatus."
    INDEX { tmnxVrrpPolicyId, 
            tmnxVrrpLagPortDownEventLagId }
    ::= { tmnxVrrpLagPortDownEventTable 1 }

TmnxVrrpLagPortDownEventEntry ::= 
    SEQUENCE {
        tmnxVrrpLagPortDownEventLagId               LAGInterfaceNumber,
        tmnxVrrpLagPortDownEventRowStatus           RowStatus,
        tmnxVrrpLagPortDownEventHoldSet             TmnxEventHoldSet,        
        tmnxVrrpLagPortDownEventOperState           Integer32,
        tmnxVrrpLagPortDownEventHoldSetRemaining    TmnxEventHoldSet,
        tmnxVrrpLagPortDownEventPrevState           Integer32,
        tmnxVrrpLagPortDownEventLastTransition      TimeStamp,
        tmnxVrrpLagPortDownEventSetCounter          Counter32,
        tmnxVrrpLagPortDownEventInUse               TruthValue,
        tmnxVrrpLagPortDownEventHoldClear           TmnxEventHoldClear,
        tmnxVrrpLagPortDownEventHoldClearRemaining  TmnxEventHoldClear
    }

tmnxVrrpLagPortDownEventLagId  OBJECT-TYPE
    SYNTAX       LAGInterfaceNumber
    MAX-ACCESS   not-accessible
    STATUS       current
    DESCRIPTION 
        "The index value tmnxVrrpLagPortDownEventLagId uniquely identifies 
         the Link Aggregation Group (LAG) whose operational state is
         monitored by this priority control event."
    ::= { tmnxVrrpLagPortDownEventEntry 1 } 

tmnxVrrpLagPortDownEventRowStatus  OBJECT-TYPE
    SYNTAX       RowStatus
    MAX-ACCESS   read-create
    STATUS       current
    DESCRIPTION 
        "tmnxVrrpLagPortDownEventRowStatus is used for the creation or 
         deletion of entries in the tmnxVrrpLagPortDownEventTable."
    ::= { tmnxVrrpLagPortDownEventEntry 2 } 

tmnxVrrpLagPortDownEventHoldSet  OBJECT-TYPE
    SYNTAX       TmnxEventHoldSet
    UNITS        "seconds"
    MAX-ACCESS   read-create
    STATUS       current
    DESCRIPTION 
        "The value of tmnxVrrpLagPortDownEventHoldSet specifies the 
         configured Hold Set time associated with the event."
    DEFVAL { 0 }
    ::= { tmnxVrrpLagPortDownEventEntry 3 } 

tmnxVrrpLagPortDownEventOperState  OBJECT-TYPE
    SYNTAX       Integer32 (0..65)
    MAX-ACCESS   read-only
    STATUS       current
    DESCRIPTION 
        "The value of tmnxVrrpLagPortDownEventOperState indicates the
         current operational state of the event.
         
         The value of zero indicates operational state of 'cleared' and
         '1' indicates 'setNonExistant'. Otherwise the value indicates
         one more than the number of ports down."
    ::= { tmnxVrrpLagPortDownEventEntry 4 } 

tmnxVrrpLagPortDownEventHoldSetRemaining  OBJECT-TYPE
    SYNTAX       TmnxEventHoldSet
    UNITS        "seconds"
    MAX-ACCESS   read-only
    STATUS       current
    DESCRIPTION 
        "The value of tmnxVrrpLagPortDownEventHoldSetRemaining 
         indicates the current value of the hold-set timer i.e. the
         amount of time remaining before the event will transition into 
         the cleared state."
    ::= { tmnxVrrpLagPortDownEventEntry 5 } 

tmnxVrrpLagPortDownEventPrevState  OBJECT-TYPE
    SYNTAX       Integer32 (0..65)
    MAX-ACCESS   read-only
    STATUS       current
    DESCRIPTION 
        "The value of tmnxVrrpLagPortDownEventPrevState indicates the
         previous operational state of the event.

         The value of zero indicates operational state of 'cleared' and
         '1' indicates 'setNonExistant'. Otherwise the value indicates
         one more than the number of ports down."
    ::= { tmnxVrrpLagPortDownEventEntry 6 } 

tmnxVrrpLagPortDownEventLastTransition  OBJECT-TYPE
    SYNTAX       TimeStamp
    MAX-ACCESS   read-only
    STATUS       current
    DESCRIPTION 
        "The value of tmnxVrrpLagPortDownEventLastTransition indicates
         the sysUpTime when the operational state of the event last 
         changed."
    ::= { tmnxVrrpLagPortDownEventEntry 7 } 

tmnxVrrpLagPortDownEventSetCounter  OBJECT-TYPE
    SYNTAX       Counter32
    MAX-ACCESS   read-only
    STATUS       current
    DESCRIPTION 
        "The value of tmnxVrrpLagPortDownEventSetCounter indicates
         the number of times the event has transitioned to one of 
         the 'set' states."
    ::= { tmnxVrrpLagPortDownEventEntry 8 } 

tmnxVrrpLagPortDownEventInUse  OBJECT-TYPE
    SYNTAX       TruthValue
    MAX-ACCESS   read-only
    STATUS       current
    DESCRIPTION 
        "If value of tmnxVrrpLagPortDownEventInUse is 'true', then 
         the event is currently affecting the in-use priority of some 
         virtual router."
    ::= { tmnxVrrpLagPortDownEventEntry 9 } 

tmnxVrrpLagPortDownEventHoldClear  OBJECT-TYPE
    SYNTAX       TmnxEventHoldClear
    UNITS        "seconds"
    MAX-ACCESS   read-create
    STATUS       current
    DESCRIPTION 
        "The value of tmnxVrrpLagPortDownEventHoldClear specifies the 
         configured Hold Clear time associated with the event."
    DEFVAL { 0 }
    ::= { tmnxVrrpLagPortDownEventEntry 10 } 

tmnxVrrpLagPortDownEventHoldClearRemaining  OBJECT-TYPE
    SYNTAX       TmnxEventHoldClear
    UNITS        "seconds"
    MAX-ACCESS   read-only
    STATUS       current
    DESCRIPTION 
        "The value of tmnxVrrpLagPortDownEventHoldClearRemaining 
         indicates the current value of the hold-clear timer i.e. the
         amount of time remaining before the cleared event will have
         an effect on the virtual router instance."
    ::= { tmnxVrrpLagPortDownEventEntry 11 } 

-- ***************************************************************************
-- The Nokia SROS series VRRP Number of LAG Ports Down Table
-- ***************************************************************************

tmnxVrrpLagNumberDownEventTable OBJECT-TYPE
    SYNTAX       SEQUENCE OF TmnxVrrpLagNumberDownEventEntry
    MAX-ACCESS   not-accessible
    STATUS       current
    DESCRIPTION  
        "The tmnxVrrpLagNumberDownEventTable contains a list of 
         events corresponding to the number of LAG ports that are 
         operationally down within a specific LAG."
    ::= { tmnxVrrpPolicyObjects 4 }

tmnxVrrpLagNumberDownEventEntry OBJECT-TYPE
    SYNTAX       TmnxVrrpLagNumberDownEventEntry
    MAX-ACCESS   not-accessible
    STATUS       current
    DESCRIPTION 
        "Each tmnxVrrpLagNumberDownEventEntry is associated with an entry
         in the tmnxVrrpLagPortDownEventTable. It is used to assign  
         a priority value to the LAG Port Down Priority Event
         depending on the number of LAG ports that are in the 
         operationally down state.  
         
         Entries can be created and deleted via SNMP SET operations 
         using tmnxVrrpLagNumberDownEventRowStatus. When a 
         tmnxVrrpLagPortDownEventEntry is deleted all 
         tmnxVrrpLagNumberDownEventTable entries associated with it are 
         also deleted."
    INDEX { tmnxVrrpPolicyId, 
            tmnxVrrpLagPortDownEventLagId,
            tmnxVrrpLagNumberDown }
    ::= { tmnxVrrpLagNumberDownEventTable 1 }

TmnxVrrpLagNumberDownEventEntry ::= 
    SEQUENCE {
        tmnxVrrpLagNumberDown                   Unsigned32,
        tmnxVrrpLagNumberDownEventRowStatus     RowStatus,
        tmnxVrrpLagNumberDownEventPriority      TmnxVrrpPriority,
        tmnxVrrpLagNumberDownEventType          TmnxEventType
    }

tmnxVrrpLagNumberDown  OBJECT-TYPE
    SYNTAX       Unsigned32
    MAX-ACCESS   not-accessible
    STATUS       current
    DESCRIPTION 
        "The index value tmnxVrrpLagNumberDown corresponds to the 
         number of LAG ports that are operationally down for a 
         specific LAG. This value sets a threshold for a LAG Port
         Down Event."
    ::= { tmnxVrrpLagNumberDownEventEntry 1 } 

tmnxVrrpLagNumberDownEventRowStatus  OBJECT-TYPE
    SYNTAX       RowStatus
    MAX-ACCESS   read-create
    STATUS       current
    DESCRIPTION 
        "tmnxVrrpLagNumberDownEventRowStatus is used for the creation or 
         deletion of entries in the tmnxVrrpLagNumberDownEventTable."
    ::= { tmnxVrrpLagNumberDownEventEntry 2 } 

tmnxVrrpLagNumberDownEventPriority  OBJECT-TYPE
    SYNTAX       TmnxVrrpPriority
    MAX-ACCESS   read-create
    STATUS       current
    DESCRIPTION 
        "The value of tmnxVrrpLagNumberDownEventPriority specifies 
         the priority level associated with this event. When the number 
         of LAG ports that are operationally down exceeds the threshold
         defined by tmnxVrrpLagNumberDown, this priority value will either
         be subtracted from the in-use priority (if the event is a 'delta' 
         event) or the in-use priority will be explicitly overridden by 
         this priority value (if the event is an 'explicit' event)."
    DEFVAL { 0 }
    ::= { tmnxVrrpLagNumberDownEventEntry 3 } 

tmnxVrrpLagNumberDownEventType  OBJECT-TYPE
    SYNTAX       TmnxEventType
    MAX-ACCESS   read-create
    STATUS       current
    DESCRIPTION 
        "The value of tmnxVrrpLagNumberDownEventType specifies whether 
         this event is a 'delta' or an 'explicit' event. When the number 
         of LAG ports that are operationally down exceeds the threshold 
         defined by tmnxVrrpLagNumberDown, the value of 
         tmnxVrrpLagNumberDownEventPriority will be subtracted from the 
         in-use priority in case of a 'delta' event or the in-use priority 
         will be explicitly overridden by the value of 
         tmnxVrrpLagNumberDownEventPriority in case of an 'explicit' 
         event."
    DEFVAL { delta }
    ::= { tmnxVrrpLagNumberDownEventEntry 4 } 


-- ***************************************************************************
-- The Nokia SROS series VRRP Host Unreachable Priority Event Table
-- ***************************************************************************

tmnxVrrpHostUnreachableEventTable OBJECT-TYPE
    SYNTAX       SEQUENCE OF TmnxVrrpHostUnreachableEventEntry
    MAX-ACCESS   not-accessible
    STATUS       current
    DESCRIPTION  
        "The tmnxVrrpHostUnreachableEventTable contains a list of Host 
         Unreachable Priority Events."
    ::= { tmnxVrrpPolicyObjects 5 }

tmnxVrrpHostUnreachableEventEntry OBJECT-TYPE
    SYNTAX       TmnxVrrpHostUnreachableEventEntry
    MAX-ACCESS   not-accessible
    STATUS       current
    DESCRIPTION 
        "Each row entry in the tmnxVrrpHostUnreachableEventTable 
         represents an instance of a 'HostUnreachable' Priority 
         Event used to override or adjust the base priority value 
         of a VRRP virtual router instance depending on the operational 
         state of the event.
    
         Entries can be created and deleted via SNMP SET operations 
         using tmnxVrrpHostUnreachableEventRowStatus."
    INDEX { tmnxVrrpPolicyId, 
            tmnxVrrpHostUnreachableEventIpAddr }
    ::= { tmnxVrrpHostUnreachableEventTable 1 }

TmnxVrrpHostUnreachableEventEntry ::= 
    SEQUENCE {
        tmnxVrrpHostUnreachableEventIpAddr              IpAddress,
        tmnxVrrpHostUnreachableEventRowStatus           RowStatus,
        tmnxVrrpHostUnreachableEventPriority            TmnxVrrpPriority,
        tmnxVrrpHostUnreachableEventType                TmnxEventType,
        tmnxVrrpHostUnreachableEventHoldSet             TmnxEventHoldSet,
        tmnxVrrpHostUnreachableEventInterval            Unsigned32,
        tmnxVrrpHostUnreachableEventTimeout             Unsigned32,
        tmnxVrrpHostUnreachableEventDropCount           Unsigned32,
        tmnxVrrpHostUnreachableEventOperState   
                                        TmnxHostUnreachableEventOperState,
        tmnxVrrpHostUnreachableEventHoldSetRemaining    TmnxEventHoldSet,
        tmnxVrrpHostUnreachableEventPrevState           
                                        TmnxHostUnreachableEventOperState,
        tmnxVrrpHostUnreachableEventLastTransition      TimeStamp,
        tmnxVrrpHostUnreachableEventSetCounter          Counter32,
        tmnxVrrpHostUnreachableEventInUse               TruthValue,
        tmnxVrrpHostUnreachableEventHoldClear           TmnxEventHoldClear,
        tmnxVrrpHostUnreachableEventHoldClearRemaining  TmnxEventHoldClear,
        tmnxVrrpHostUnreachableEvtSize                  Unsigned32
    }

tmnxVrrpHostUnreachableEventIpAddr  OBJECT-TYPE
    SYNTAX       IpAddress
    MAX-ACCESS   not-accessible
    STATUS       current
    DESCRIPTION 
        "This priority control event monitors the ability to receive ICMP 
         Echo Reply packets from a host which is uniquely identified by 
         the index value tmnxVrrpHostUnreachableEventIpAddr."
    ::= { tmnxVrrpHostUnreachableEventEntry 1 } 

tmnxVrrpHostUnreachableEventRowStatus  OBJECT-TYPE
    SYNTAX       RowStatus
    MAX-ACCESS   read-create
    STATUS       current
    DESCRIPTION 
        "tmnxVrrpHostUnreachableEventRowStatus is used for the creation
         or deletion of entries in the tmnxVrrpHostUnreachableEventTable."
    ::= { tmnxVrrpHostUnreachableEventEntry 2 } 

tmnxVrrpHostUnreachableEventPriority  OBJECT-TYPE
    SYNTAX       TmnxVrrpPriority
    MAX-ACCESS   read-create
    STATUS       current
    DESCRIPTION 
        "The value of tmnxVrrpHostUnreachableEventPriority specifies 
         the priority level associated with this event. When the 
         operational state of the event transitions to one of the 
         'set' states, this value will either be subtracted from the 
         in-use priority (if the event is a 'delta' event) or the 
         in-use priority will be explicitly overridden by this 
         priority value (if the event is an 'explicit' event)."
    DEFVAL { 0 }
    ::= { tmnxVrrpHostUnreachableEventEntry 3 } 

tmnxVrrpHostUnreachableEventType  OBJECT-TYPE
    SYNTAX       TmnxEventType
    MAX-ACCESS   read-create
    STATUS       current
    DESCRIPTION 
        "The value of tmnxVrrpHostUnreachableEventType specifies whether
         this event is a 'delta' or an 'explicit' event. When the event 
         is 'set', the value of tmnxVrrpHostUnreachableEventPriority will 
         be subtracted from the in-use priority in case of a 'delta' event
         or the in-use priority will be explicitly overridden by the value
         of tmnxVrrpHostUnreachableEventPriority in case of an 'explicit' 
         event."
    DEFVAL { delta }
    ::= { tmnxVrrpHostUnreachableEventEntry 4 } 

tmnxVrrpHostUnreachableEventHoldSet  OBJECT-TYPE
    SYNTAX       TmnxEventHoldSet
    UNITS        "seconds"
    MAX-ACCESS   read-create
    STATUS       current
    DESCRIPTION 
        "The value of tmnxVrrpHostUnreachableEventHoldSet specifies 
         the configured Hold Set time associated with the event."
    DEFVAL { 0 }
    ::= { tmnxVrrpHostUnreachableEventEntry 5 } 

tmnxVrrpHostUnreachableEventInterval  OBJECT-TYPE
    SYNTAX       Unsigned32 (1..60)
    UNITS        "seconds"
    MAX-ACCESS   read-create
    STATUS       current
    DESCRIPTION 
        "The value of tmnxVrrpHostUnreachableEventInterval specifies 
         the amount of time in seconds between consecutive ICMP 
         Echo Requests sent to the far end host IP address."
    DEFVAL { 1 }
    ::= { tmnxVrrpHostUnreachableEventEntry 6 } 

tmnxVrrpHostUnreachableEventTimeout  OBJECT-TYPE
    SYNTAX       Unsigned32 (1..60)
    UNITS        "seconds"
    MAX-ACCESS   read-create
    STATUS       current
    DESCRIPTION 
        "The value of tmnxVrrpHostUnreachableEventTimeout specifies 
         the amount of time in seconds that is allowed for receiving
         an ICMP Echo Reply message from the far end host IP address
         to which a ICMP Echo Request message was sent out. If a reply 
         is not received within this time the far end host is considered 
         unresponsive."
    DEFVAL { 1 }
    ::= { tmnxVrrpHostUnreachableEventEntry 7 } 

tmnxVrrpHostUnreachableEventDropCount  OBJECT-TYPE
    SYNTAX       Unsigned32 (1..60)
    MAX-ACCESS   read-create
    STATUS       current
    DESCRIPTION 
        "The value of tmnxVrrpHostUnreachableEventDropCount specifies 
         the number of consecutive ICMP Echo Request message send attempts
         that must fail for the priority event to enter a 'set' state."
    DEFVAL { 3 }
    ::= { tmnxVrrpHostUnreachableEventEntry 8 } 

tmnxVrrpHostUnreachableEventOperState  OBJECT-TYPE
    SYNTAX       TmnxHostUnreachableEventOperState
    MAX-ACCESS   read-only
    STATUS       current
    DESCRIPTION 
        "The value of tmnxVrrpHostUnreachableEventOperState indicates
         the current operational state of the event."
    ::= { tmnxVrrpHostUnreachableEventEntry 9 } 

tmnxVrrpHostUnreachableEventHoldSetRemaining  OBJECT-TYPE
    SYNTAX       TmnxEventHoldSet
    UNITS        "seconds"
    MAX-ACCESS   read-only
    STATUS       current
    DESCRIPTION 
        "The value of tmnxVrrpHostUnreachableEventHoldSetRemaining 
         indicates the current value of the hold-set timer i.e. the
         amount of time remaining before the event will transition 
         into the cleared state."
    ::= { tmnxVrrpHostUnreachableEventEntry 10 } 

tmnxVrrpHostUnreachableEventPrevState  OBJECT-TYPE
    SYNTAX       TmnxHostUnreachableEventOperState 
    MAX-ACCESS   read-only
    STATUS       current
    DESCRIPTION 
        "The value of tmnxVrrpHostUnreachableEventPrevState indicates
         the previous operational state of the event."
    ::= { tmnxVrrpHostUnreachableEventEntry 11 } 

tmnxVrrpHostUnreachableEventLastTransition  OBJECT-TYPE
    SYNTAX       TimeStamp
    MAX-ACCESS   read-only
    STATUS       current
    DESCRIPTION 
        "The value of tmnxVrrpHostUnreachableEventLastTransition 
         indicates the sysUpTime when the operational state of the
         event last changed."
    ::= { tmnxVrrpHostUnreachableEventEntry 12 } 

tmnxVrrpHostUnreachableEventSetCounter  OBJECT-TYPE
    SYNTAX       Counter32
    MAX-ACCESS   read-only
    STATUS       current
    DESCRIPTION 
        "The value of tmnxVrrpHostUnreachableEventSetCounter indicates
         the number of times the event has transitioned to one of the 
         'set' states."
    ::= { tmnxVrrpHostUnreachableEventEntry 13 } 

tmnxVrrpHostUnreachableEventInUse  OBJECT-TYPE
    SYNTAX       TruthValue
    MAX-ACCESS   read-only
    STATUS       current
    DESCRIPTION 
        "If value of tmnxVrrpHostUnreachableEventInUse is 'true', then 
         the event is currently affecting the in-use priority of some 
         virtual router."
    ::= { tmnxVrrpHostUnreachableEventEntry 14 } 

tmnxVrrpHostUnreachableEventHoldClear  OBJECT-TYPE
    SYNTAX       TmnxEventHoldClear
    UNITS        "seconds"
    MAX-ACCESS   read-create
    STATUS       current
    DESCRIPTION 
        "The value of tmnxVrrpHostUnreachableEventHoldClear specifies 
         the configured Hold Clear time associated with the event."
    DEFVAL { 0 }
    ::= { tmnxVrrpHostUnreachableEventEntry 15 } 

tmnxVrrpHostUnreachableEventHoldClearRemaining  OBJECT-TYPE
    SYNTAX       TmnxEventHoldClear
    UNITS        "seconds"
    MAX-ACCESS   read-only
    STATUS       current
    DESCRIPTION 
        "The value of tmnxVrrpHostUnreachableEventHoldClearRemaining 
         indicates the current value of the hold-clear timer i.e. the
         amount of time remaining before the cleared event will have
         an effect on the virtual router instance."
    ::= { tmnxVrrpHostUnreachableEventEntry 16 } 

tmnxVrrpHostUnreachableEvtSize  OBJECT-TYPE
    SYNTAX       Unsigned32 (0..16384)
    UNITS        "bytes"
    MAX-ACCESS   read-create
    STATUS       current
    DESCRIPTION 
        "The value of tmnxVrrpHostUnreachableEvtSize specifies the padding size
         to be used for the ICMP packet for this event."
    DEFVAL { 56 }
    ::= { tmnxVrrpHostUnreachableEventEntry 17 } 

-- ***************************************************************************
-- The Nokia SROS series VRRP Route Unknown Priority Event Table
-- ***************************************************************************

tmnxVrrpRouteUnknownEventTable OBJECT-TYPE
    SYNTAX       SEQUENCE OF TmnxVrrpRouteUnknownEventEntry
    MAX-ACCESS   not-accessible
    STATUS       current
    DESCRIPTION  
        "The tmnxVrrpRouteUnknownEventTable contains a list of Route 
         Unknown Priority Events."
    ::= { tmnxVrrpPolicyObjects 6 }

tmnxVrrpRouteUnknownEventEntry OBJECT-TYPE
    SYNTAX       TmnxVrrpRouteUnknownEventEntry
    MAX-ACCESS   not-accessible
    STATUS       current
    DESCRIPTION 
        "Each row entry in the tmnxVrrpRouteUnknownEventTable represents 
         an instance of a Route Unknown Priority Event used to override 
         or adjust the base priority value of a VRRP virtual router 
         instance depending on the operational state of the event.
    
         Entries can be created and deleted via SNMP SET operations 
         using tmnxVrrpRouteUnknownEventRowStatus."
    INDEX { tmnxVrrpPolicyId, 
            tmnxVrrpRouteUnknownEventPrefix,
            tmnxVrrpRouteUnknownEventMaskLen}
    ::= { tmnxVrrpRouteUnknownEventTable 1 }

TmnxVrrpRouteUnknownEventEntry ::= 
    SEQUENCE {
        tmnxVrrpRouteUnknownEventPrefix              IpAddress,
        tmnxVrrpRouteUnknownEventMaskLen             Unsigned32,
        tmnxVrrpRouteUnknownEventRowStatus           RowStatus,
        tmnxVrrpRouteUnknownEventPriority            TmnxVrrpPriority,
        tmnxVrrpRouteUnknownEventType                TmnxEventType,
        tmnxVrrpRouteUnknownEventHoldSet             TmnxEventHoldSet,
        tmnxVrrpRouteUnknownEventLessSpecific        TruthValue,
        tmnxVrrpRouteUnknownEventDefaultAllowed      TruthValue,
        tmnxVrrpRouteUnknownEventProtocol            BITS,
        tmnxVrrpRouteUnknownEventOperState      TmnxRouteUnknownEventOperState,
        tmnxVrrpRouteUnknownEventHoldSetRemaining    TmnxEventHoldSet,
        tmnxVrrpRouteUnknownEventPrevState      TmnxRouteUnknownEventOperState,
        tmnxVrrpRouteUnknownEventLastTransition      TimeStamp,
        tmnxVrrpRouteUnknownEventSetCounter          Counter32,
        tmnxVrrpRouteUnknownEventInUse               TruthValue,
        tmnxVrrpRouteUnknownEventHoldClear           TmnxEventHoldClear,
        tmnxVrrpRouteUnknownEventHoldClearRemaining  TmnxEventHoldClear
    }

tmnxVrrpRouteUnknownEventPrefix  OBJECT-TYPE
    SYNTAX       IpAddress
    MAX-ACCESS   not-accessible
    STATUS       current
    DESCRIPTION 
        "The index value tmnxVrrpRouteUnknownEventPrefix identifies the 
         IP prefix of the route whose existence within the routing table 
         is being monitored by this priority control event."
    ::= { tmnxVrrpRouteUnknownEventEntry 1 } 

tmnxVrrpRouteUnknownEventMaskLen  OBJECT-TYPE
    SYNTAX       Unsigned32 (0..32)
    MAX-ACCESS   not-accessible
    STATUS       current
    DESCRIPTION 
        "The index value tmnxVrrpRouteUnknownEventMaskLen identifies the 
         prefix mask length of the route whose existence within the routing
         table is being monitored by this priority control event."
    ::= { tmnxVrrpRouteUnknownEventEntry 2 } 

tmnxVrrpRouteUnknownEventRowStatus  OBJECT-TYPE
    SYNTAX       RowStatus
    MAX-ACCESS   read-create
    STATUS       current
    DESCRIPTION 
        "tmnxVrrpRouteUnknownEventRowStatus is used for the creation or 
         deletion of entries in the tmnxVrrpRouteUnknownEventTable."
    ::= { tmnxVrrpRouteUnknownEventEntry 3 } 

tmnxVrrpRouteUnknownEventPriority  OBJECT-TYPE
    SYNTAX       TmnxVrrpPriority
    MAX-ACCESS   read-create
    STATUS       current
    DESCRIPTION 
        "The value of tmnxVrrpRouteUnknownEventPriority specifies the 
         priority level associated with this event. When the operational 
         state of the event transitions to one of the 'set' states, this 
         value will either be subtracted from the in-use priority (if the 
         event is a 'delta' event) or the in-use priority will be 
         explicitly overridden by this priority value (if the event is 
         an 'explicit' event)."
    DEFVAL { 0 }
    ::= { tmnxVrrpRouteUnknownEventEntry 4 } 

tmnxVrrpRouteUnknownEventType  OBJECT-TYPE
    SYNTAX       TmnxEventType
    MAX-ACCESS   read-create
    STATUS       current
    DESCRIPTION 
        "The value of tmnxVrrpRouteUnknownEventType specifies whether 
         this event is a 'delta' or an 'explicit' event. When the event 
         is 'set', the value of tmnxVrrpRouteUnknownEventPriority will 
         be subtracted from the in-use priority in case of a 'delta' 
         event or the in-use priority will be explicitly overridden by 
         the value of tmnxVrrpRouteUnknownEventPriority in case of an
         'explicit' event."
    DEFVAL { delta }
    ::= { tmnxVrrpRouteUnknownEventEntry 5 } 

tmnxVrrpRouteUnknownEventHoldSet  OBJECT-TYPE
    SYNTAX       TmnxEventHoldSet
    UNITS        "seconds"
    MAX-ACCESS   read-create
    STATUS       current
    DESCRIPTION 
        "The value of tmnxVrrpRouteUnknownEventHoldSet specifies the 
         configured Hold Set time associated with the event."
    DEFVAL { 0 }
    ::= { tmnxVrrpRouteUnknownEventEntry 6 } 

tmnxVrrpRouteUnknownEventLessSpecific  OBJECT-TYPE
    SYNTAX       TruthValue
    MAX-ACCESS   read-create
    STATUS       current
    DESCRIPTION 
        "Setting the value of tmnxVrrpRouteUnknownEventLessSpecific 
         to 'true', allows a route with a less specific IP prefix to 
         match the IP prefix associated with the event."
    DEFVAL { false }
    ::= { tmnxVrrpRouteUnknownEventEntry 7 } 

tmnxVrrpRouteUnknownEventDefaultAllowed  OBJECT-TYPE
    SYNTAX       TruthValue
    MAX-ACCESS   read-create
    STATUS       current
    DESCRIPTION 
        "Setting the value of tmnxVrrpRouteUnknownEventDefaultAllowed 
         to 'true', allows the default route to match the IP prefix 
         associated with the event. This value is valid only when
         tmnxVrrpRouteUnknownEventLessSpecific is 'true'. If 
         tmnxVrrpRouteUnknownEventLessSpecific is 'false' this value
         is ignored."
    DEFVAL { false }
    ::= { tmnxVrrpRouteUnknownEventEntry 8 } 

tmnxVrrpRouteUnknownEventProtocol  OBJECT-TYPE
    SYNTAX       BITS {
                     bgp(0),
                     ospf(1),
                     isis(2),
                     rip(3),
                     static(4),
                     bgpVpn(5)
                 }
    MAX-ACCESS   read-create
    STATUS       current
    DESCRIPTION 
        "The bits of tmnxVrrpRouteUnknownEventProtocol identify the 
         allowed route sources when matching the IP prefix associated 
         with this event with the results of a Route table lookup.
         If the bit corresponding to a protocol is set then the 
         protocol is considered as a route source match constraint."
    DEFVAL { { } }
    ::= { tmnxVrrpRouteUnknownEventEntry 9 } 

tmnxVrrpRouteUnknownEventOperState  OBJECT-TYPE
    SYNTAX       TmnxRouteUnknownEventOperState
    MAX-ACCESS   read-only
    STATUS       current
    DESCRIPTION 
        "The value of tmnxVrrpRouteUnknownEventOperState indicates the
         current operational state of the event."
    ::= { tmnxVrrpRouteUnknownEventEntry 10 } 

tmnxVrrpRouteUnknownEventHoldSetRemaining  OBJECT-TYPE
    SYNTAX       TmnxEventHoldSet
    UNITS        "seconds"
    MAX-ACCESS   read-only
    STATUS       current
    DESCRIPTION 
        "The value of tmnxVrrpRouteUnknownEventHoldSetRemaining indicates
         the current value of the hold-set timer i.e. the amount of time 
         remaining before the event will transition into the cleared state."
    ::= { tmnxVrrpRouteUnknownEventEntry 11 } 

tmnxVrrpRouteUnknownEventPrevState  OBJECT-TYPE
    SYNTAX       TmnxRouteUnknownEventOperState 
    MAX-ACCESS   read-only
    STATUS       current
    DESCRIPTION 
        "The value of tmnxVrrpRouteUnknownEventPrevState indicates the
         previous operational state of the event."
    ::= { tmnxVrrpRouteUnknownEventEntry 12 } 

tmnxVrrpRouteUnknownEventLastTransition  OBJECT-TYPE
    SYNTAX       TimeStamp
    MAX-ACCESS   read-only
    STATUS       current
    DESCRIPTION 
        "The value of tmnxVrrpRouteUnknownEventLastTransition indicates
         the sysUpTime when the operational state of the event last 
         changed."
    ::= { tmnxVrrpRouteUnknownEventEntry 13 } 

tmnxVrrpRouteUnknownEventSetCounter  OBJECT-TYPE
    SYNTAX       Counter32
    MAX-ACCESS   read-only
    STATUS       current
    DESCRIPTION 
        "The value of tmnxVrrpRouteUnknownEventSetCounter indicates the
         number of times the event has transitioned to one of the 'set' 
         states."
    ::= { tmnxVrrpRouteUnknownEventEntry 14 } 

tmnxVrrpRouteUnknownEventInUse  OBJECT-TYPE
    SYNTAX       TruthValue
    MAX-ACCESS   read-only
    STATUS       current
    DESCRIPTION 
        "If value of tmnxVrrpRouteUnknownEventInUse is 'true', then the 
         event is currently affecting the in-use priority of some virtual
         router."
    ::= { tmnxVrrpRouteUnknownEventEntry 15 } 

tmnxVrrpRouteUnknownEventHoldClear  OBJECT-TYPE
    SYNTAX       TmnxEventHoldClear
    UNITS        "seconds"
    MAX-ACCESS   read-create
    STATUS       current
    DESCRIPTION 
        "The value of tmnxVrrpRouteUnknownEventHoldClear specifies the 
         configured Hold Clear time associated with the event."
    DEFVAL { 0 }
    ::= { tmnxVrrpRouteUnknownEventEntry 16 } 

tmnxVrrpRouteUnknownEventHoldClearRemaining  OBJECT-TYPE
    SYNTAX       TmnxEventHoldClear
    UNITS        "seconds"
    MAX-ACCESS   read-only
    STATUS       current
    DESCRIPTION 
        "The value of tmnxVrrpRouteUnknownEventHoldClearRemaining indicates
         the current value of the hold-clear timer i.e. the amount of time
         amount of time remaining before the cleared event will have an
         effect on the virtual router instance."
    ::= { tmnxVrrpRouteUnknownEventEntry 17 } 


-- ***************************************************************************
-- The Nokia SROS series VRRP Route Unknown Event Next Hop Table
-- ***************************************************************************

tmnxVrrpRouteUnknownEventNextHopTable OBJECT-TYPE
    SYNTAX       SEQUENCE OF TmnxVrrpRouteUnknownEventNextHopEntry
    MAX-ACCESS   not-accessible
    STATUS       current
    DESCRIPTION  
        "The tmnxVrrpRouteUnknownEventNextHopTable contains a list of 
         next-hop IP addresses associated with each Route Unknown 
         Priority Events defined in tmnxVrrpRouteUnknownEventTable."
    ::= { tmnxVrrpPolicyObjects 7 }

tmnxVrrpRouteUnknownEventNextHopEntry OBJECT-TYPE
    SYNTAX       TmnxVrrpRouteUnknownEventNextHopEntry
    MAX-ACCESS   not-accessible
    STATUS       current
    DESCRIPTION 
        "Each row entry in the tmnxVrrpRouteUnknownEventNextHopTable
         represents an instance of a next-hop IP address which is 
         defined as a match criterion for the Route Unknown Priority 
         Event associated with this entry. 
    
         Entries can be created and deleted via SNMP SET operations 
         using tmnxVrrpRouteUnknownEventNextHopRowStatus."
    INDEX { tmnxVrrpPolicyId, 
            tmnxVrrpRouteUnknownEventPrefix,
            tmnxVrrpRouteUnknownEventMaskLen, 
            tmnxVrrpRouteUnknownEventNextHop }
    ::= { tmnxVrrpRouteUnknownEventNextHopTable 1 }

TmnxVrrpRouteUnknownEventNextHopEntry ::= 
    SEQUENCE {
        tmnxVrrpRouteUnknownEventNextHop           IpAddress,
        tmnxVrrpRouteUnknownEventNextHopRowStatus  RowStatus
    }

tmnxVrrpRouteUnknownEventNextHop  OBJECT-TYPE
    SYNTAX       IpAddress
    MAX-ACCESS   not-accessible
    STATUS       current
    DESCRIPTION 
        "The index value tmnxVrrpRouteUnknownEventNextHop identifies 
         the next-hop IP address which is used to match the route prefix
         being monitored by this priority control event with the results
         of a route table lookup."
    ::= { tmnxVrrpRouteUnknownEventNextHopEntry 1 } 

tmnxVrrpRouteUnknownEventNextHopRowStatus  OBJECT-TYPE
    SYNTAX       RowStatus
    MAX-ACCESS   read-create
    STATUS       current
    DESCRIPTION 
        "tmnxVrrpRouteUnknownEventNextHopRowStatus is used for the 
         creation or deletion of entries in the 
         tmnxVrrpRouteUnknownEventNextHopTable."
    ::= { tmnxVrrpRouteUnknownEventNextHopEntry 2 } 

-- ***************************************************************************
-- Augmentation of the vrrpOperationsTable defined in the TIMETRA-VRRP-V3-MIB
-- ***************************************************************************

tVrrpOpTblLastChgd OBJECT-TYPE
    SYNTAX      TimeStamp
    MAX-ACCESS  read-only
    STATUS      current
    DESCRIPTION
        "Timestamp of the last change to the vrrpOperationsTable
         either from adding a row or removing a row."
    ::= { tmnxVrrpObjects 6 }

tVrrpOpTable OBJECT-TYPE
    SYNTAX       SEQUENCE OF TVrrpOperationsEntry
    MAX-ACCESS   not-accessible
    STATUS       current
    DESCRIPTION  
        "The tVrrpOpTable provides an extension of the
         vrrpOperationsTable in the TIMETRA-VRRP-V3-MIB.

         Use of AUGMENTS clause implies a one-to-one dependent relationship 
         between the base table, vrrpOperationsTable, and the augmenting table, 
         tVrrpOpTable. This in effect extends the vrrpOperationsTable with 
         additional columns. Creation (or deletion) of a row in the 
         vrrpOperationsTable results in the same fate for the row in the 
         tVrrpOpTable."
    ::= { tmnxVrrpObjects 7 }

tVrrpOpEntry OBJECT-TYPE
    SYNTAX       TVrrpOperationsEntry
    MAX-ACCESS   not-accessible
    STATUS       current
    DESCRIPTION 
        "Each row entry in the tVrrpOpTable represents additional 
         columns in the vrrpOperationsTable for attributes specific to the
         Nokia SROS series VRRP implementation."
    AUGMENTS { vrrpOperationsEntry }
    ::= { tVrrpOpTable 1 }

TVrrpOperationsEntry ::= 
    SEQUENCE {
        tVrrpOpState                     INTEGER,
        tVrrpOpVirtualMacAddr            MacAddress,
        tVrrpOpPingReply                 TruthValue,
        tVrrpOpTelnetReply               TruthValue,
        tVrrpOpPolicyId                  Unsigned32,
        tVrrpOpInUsePriority             Unsigned32,
        tVrrpOpMasterSince               TimeStamp,
        tVrrpOpMasterPriority            Unsigned32,
        tVrrpOpOwner                     TruthValue,
        tVrrpOpMasterDownInterval        TimeInterval,
        tVrrpOpMasterDownTimer           TimeInterval,
        tVrrpOpAdvIntervalInherit        TruthValue,
        tVrrpOpInUseAdvInterval          TimeInterval,
        tVrrpOpTracerouteReply           TruthValue,
        tVrrpOpStandbyFwding             TruthValue,
        tVrrpOpInitDelay                 Unsigned32,
        tVrrpOpInitTimer                 TimeInterval,
        tVrrpOpLastChgd                  TimeStamp,
        tVrrpOpOperDownReason            INTEGER,
        tVrrpOpPassive TruthValue,
        tVrrpOpRowStatus RowStatus,
        tVrrpOpOperGroupName TNamedItemOrEmpty
    }

tVrrpOpState  OBJECT-TYPE
    SYNTAX       INTEGER {
                     up(1),
                     down(2)
                 }
    MAX-ACCESS   read-only
    STATUS       current
    DESCRIPTION 
        "The value of tVrrpOpState indicates the operational state 
         of the VRRP virtual router instance."
    ::= { tVrrpOpEntry 1 }

tVrrpOpVirtualMacAddr  OBJECT-TYPE
    SYNTAX       MacAddress
    MAX-ACCESS   read-create
    STATUS       current
    DESCRIPTION 
        "The value of tVrrpOpVirtualMacAddr specifies the configured virtual MAC
         address used in ARP (IPv4) or ND (IPv6) responses when the VRRP
         virtual router instance is operating as a master."
    DEFVAL { '000000000000'H }
    ::= { tVrrpOpEntry 2 }

tVrrpOpPingReply  OBJECT-TYPE
    SYNTAX       TruthValue
    MAX-ACCESS   read-create
    STATUS       current
    DESCRIPTION 
        "The tVrrpOpPingReply is valid only if the VRRP virtual router
         instance associated with this entry is a non-owner.
         
         By setting tVrrpOpPingReply to 'true', a non-owner master is 
         enabled to reply to ICMP Echo requests directed to the virtual 
         router instance IP addresses. 
 
         A non-owner backup virtual router never responds to such ICMP echo 
         requests irrespective of the value of tVrrpOpPingReply."
    DEFVAL { false }
    ::= { tVrrpOpEntry 3 }

tVrrpOpTelnetReply  OBJECT-TYPE
    SYNTAX       TruthValue
    MAX-ACCESS   read-create
    STATUS       current
    DESCRIPTION 
        "The tVrrpOpTelnetReply is valid only if the VRRP virtual router
         instance associated with this entry is a non-owner.
         
         By setting tVrrpOpTelnetReply to 'true', a non-owner master is
         enabled to reply to TCP Port 23 Telnet Requests directed to the 
         virtual router instance IP addresses. 
         
         A non-owner backup virtual router never responds to such Telnet  
         requests irrespective of the value of tVrrpOpTelnetReply."
    DEFVAL { false }
    ::= { tVrrpOpEntry 4 }

tVrrpOpPolicyId  OBJECT-TYPE
    SYNTAX       Unsigned32 
    MAX-ACCESS   read-create
    STATUS       current
    DESCRIPTION 
        "The tVrrpOpPolicyId specifies the VRRP Priority Control policy 
         associated with the VRRP virtual router instance. This policy must 
         be a valid policy in the tmnxVrrpPolicyTable. 
         A value of 0 indicates that no Priority Control policy is associated
         with the virtual router instance."
    DEFVAL { 0 }
    ::= { tVrrpOpEntry 5 }

tVrrpOpInUsePriority  OBJECT-TYPE
    SYNTAX       Unsigned32 (0..255)
    MAX-ACCESS   read-only
    STATUS       current
    DESCRIPTION 
        "The tVrrpOpInUsePriority indicates the current in-use priority 
         associated with the VRRP virtual router instance."
    ::= { tVrrpOpEntry 6 }

tVrrpOpMasterSince  OBJECT-TYPE
    SYNTAX       TimeStamp
    MAX-ACCESS   read-only
    STATUS       current
    DESCRIPTION 
        "The tVrrpOpMasterSince, in case of a virtual router which 
         is the current master, indicates the sysUpTime when operational state 
         (vrrpOperState) of the virtual router changed to master(3).
         In case of a backup virtual router, this value specifies the
         sysUpTime when it received the first VRRP advertisement message
         from the virtual router which is the current master."
    ::= { tVrrpOpEntry 7 }

tVrrpOpMasterPriority  OBJECT-TYPE
    SYNTAX       Unsigned32 (0..255)
    MAX-ACCESS   read-only
    STATUS       current
    DESCRIPTION 
        "The value of tVrrpOpMasterPriority indicates the priority of
         the virtual router instance which is the current master" 
    ::= { tVrrpOpEntry 8 }

tVrrpOpOwner  OBJECT-TYPE
    SYNTAX       TruthValue
    MAX-ACCESS   read-create
    STATUS       current
    DESCRIPTION 
        "The value of tVrrpOpOwner specifies whether or not the virtual
         router instance has been configured as an owner. If 'true', then 
         the virtual router instance is an 'owner', if 'false' then the
         instance is a 'non-owner'."
    DEFVAL { false }
    ::= { tVrrpOpEntry 9 }

tVrrpOpMasterDownInterval  OBJECT-TYPE
    SYNTAX       TimeInterval
    UNITS        "milliseconds"
    MAX-ACCESS   read-only
    STATUS       current
    DESCRIPTION 
        "The value of tVrrpOpMasterDownInterval indicates the time
         interval in milliseconds for the backup router to declare the master
         as down.  

         It is calculated as
                (3 * Advertisement_Interval) + Skew_time
         where Skew_Time is calculated as
                ((256 - Priority) * Master_Adver_Interval) / 256
        " 
    REFERENCE 
        "www.ietf.org/internet-drafts/draft-ietf-vrrp-spec-v2-06.txt"  
    ::= { tVrrpOpEntry 10 }

tVrrpOpMasterDownTimer  OBJECT-TYPE
    SYNTAX       TimeInterval
    UNITS        "milliseconds"
    MAX-ACCESS   read-only
    STATUS       current
    DESCRIPTION 
        "The value of tVrrpOpMasterDownTimer indicates the current 
         value of the Master Down Timer in milliseconds. 

         When a backup router receives a VRRP advertisement from a master,
         it resets this timer to the value of the Master Down Interval 
         and begins to count down. If the backup router does not receive
         an advertisement till this timer times out, it will assume that
         the master is down and will declare itself to be the master." 
    REFERENCE    
        "www.ietf.org/internet-drafts/draft-ietf-vrrp-spec-v2-06.txt"
    ::= { tVrrpOpEntry 11 }

tVrrpOpAdvIntervalInherit  OBJECT-TYPE
    SYNTAX       TruthValue
    MAX-ACCESS   read-create
    STATUS       current
    DESCRIPTION 
        "The tVrrpOpAdvIntervalInherit object is valid only if the VRRP
         virtual router instance associated with this entry is a non-owner.
         
         When the VRRP instance is operating as a backup and the value of
         tVrrpOpAdvIntervalInherit is set to 'true', the master down 
         timer is indirectly derived from the value in the advertisement 
         interval field of the VRRP message received from the current master. 
         
         When the VRRP instance is operating as a backup and the value of
         tVrrpOpAdvIntervalInherit is set to 'false', the configured 
         advertisement interval (vrrpOperationsAdvInterval) is matched
         against the value in the advertisement interval field of the VRRP
         message received from the current master. If the two values do not 
         match then the VRRP advertisement is discarded

         When the VRRP instance is operating as a master, the value of 
         tVrrpOpAdvIntervalInherit has no effect."
    DEFVAL { true }
    ::= { tVrrpOpEntry 12 }

tVrrpOpInUseAdvInterval  OBJECT-TYPE
    SYNTAX       TimeInterval (1..4096)
    UNITS        "centiseconds"
    MAX-ACCESS   read-only
    STATUS       current
    DESCRIPTION 
        "The tVrrpOpInUseAdvInterval indicates the operational value
         for the advertisement interval. 

         When the VRRP instance is operating as a master, the value
         of tVrrpOpInUseAdvInterval is equivalent to the value of 
         vrrpOperationsAdvInterval.
         
         When the VRRP instance is operating as a backup and the value of
         tVrrpOpAdvIntervalInherit is set to 'true', the value of
         tVrrpOpInUseAdvInterval equals the value in the advertisement
         interval field of the VRRP Advertisement message received from the
         current master.
         
         When the VRRP instance is operating as a backup and the value of
         tVrrpOpAdvIntervalInherit is set to 'false', the value of
         tVrrpOpInUseAdvInterval is equivalent to the value of 
         vrrpOperationsAdvInterval.
         
         Only the master router sends VRRP advertisements."
    ::= { tVrrpOpEntry 13 }
    
tVrrpOpTracerouteReply  OBJECT-TYPE
    SYNTAX       TruthValue
    MAX-ACCESS   read-create
    STATUS       current
    DESCRIPTION 
        "The tVrrpOpTracerouteReply is valid only if the VRRP virtual router
         instance associated with this entry is a non-owner.
         
         By setting tVrrpOpTracerouteReply to 'true', a non-owner master is 
         enabled to reply to traceroute requests directed to the virtual 
         router instance IP addresses. 
 
         A non-owner backup virtual router never responds to such traceroute 
         requests irrespective of the value of tVrrpOpTracerouteReply."
    DEFVAL { false }
    ::= { tVrrpOpEntry 14 }

tVrrpOpStandbyFwding OBJECT-TYPE
    SYNTAX       TruthValue
    MAX-ACCESS   read-create
    STATUS       current
    DESCRIPTION 
        "The value of tVrrpOpStandbyFwding specifies
         whether this vrrp instance allows forwarding packets to
         standby router.
         
         The value 'false' specifies that a standby router should
         not forward traffic sent to virtual router's MAC address.
         However, the standby router should forward traffic sent
         to the standby routers real MAC address.
 
         The value 'true' specifies that a standby router should
         forward all traffic."
    DEFVAL { false }
    ::= { tVrrpOpEntry 15 }   

tVrrpOpInitDelay  OBJECT-TYPE
    SYNTAX       Unsigned32 (0..65535)
    UNITS        "seconds"
    MAX-ACCESS   read-create
    STATUS       current
    DESCRIPTION
        "The value of tVrrpOpInitDelay specifies the initialization delay
        timer for VRRP, in seconds."
    DEFVAL { 0 } 
    ::= { tVrrpOpEntry 16 }

tVrrpOpInitTimer  OBJECT-TYPE
    SYNTAX       TimeInterval
    UNITS        "milliseconds"
    MAX-ACCESS   read-only
    STATUS       current
    DESCRIPTION
        "The value of tVrrpOpInitTimer indicates the current value of
         initialization delay timer for VRRP, in milli-seconds."
    ::= { tVrrpOpEntry 17 }

tVrrpOpLastChgd  OBJECT-TYPE
    SYNTAX       TimeStamp
    MAX-ACCESS   read-only
    STATUS       current
    DESCRIPTION 
        "The value of tVrrpOpLastChgd indicates the time stamp of the last
        change to this row of this table."
    ::= { tVrrpOpEntry 18 } 
   
tVrrpOpOperDownReason  OBJECT-TYPE
    SYNTAX       INTEGER {
                     unknown (0),
                     notActive (1),       -- row-status not active
                     adminDown (2),       
                     ifDown (3),
                     noLnkLclAddrCfg (4), -- no link local address configured
                     rtrAdvNoProperCfg (5),
                          -- interface not configured with IPv6 router-advert.
                          -- and with use of virtual MAC Address
                     invalidMac (6)
                 }
    MAX-ACCESS   read-only
    STATUS       current
    DESCRIPTION 
        "The value of tVrrpOpOperDownReason indicates the reason for the 
        operational state to be 'down'."
    ::= { tVrrpOpEntry 19 } 

tVrrpOpPassive OBJECT-TYPE
    SYNTAX       TruthValue
    MAX-ACCESS   read-create
    STATUS       current
    DESCRIPTION 
        "The tVrrpOpPassive specifies whether to suppress the
         transmit/receive of keep-alive messages."
    DEFVAL { false }
    ::= { tVrrpOpEntry 20 } 

tVrrpOpRowStatus OBJECT-TYPE
    SYNTAX       RowStatus
    MAX-ACCESS   read-create
    STATUS       current
    DESCRIPTION
        "The tVrrpOpRowStatus is used for creation or deletion of entries
         in this table."
    ::= { tVrrpOpEntry 21 }

tVrrpOpOperGroupName OBJECT-TYPE
    SYNTAX      TNamedItemOrEmpty
    MAX-ACCESS  read-create
    STATUS      current
    DESCRIPTION
        "The tVrrpOpOperGroupName specifies the operational group associated with
        the VRRP."
    DEFVAL { ''H}
    ::= { tVrrpOpEntry 25 }
-- ***************************************************************************
-- Augmentation of the vrrpRouterStatisticsTable in TIMETRA-VRRP-V3-MIB
-- ***************************************************************************

tVrrpRtrStatisticsTable OBJECT-TYPE
    SYNTAX       SEQUENCE OF TVrrpRtrStatisticsEntry
    MAX-ACCESS   not-accessible
    STATUS       current
    DESCRIPTION  
        "The tVrrpRtrStatisticsTable provides an extension of the 
         vrrpRouterStatisticsTable in the TIMETRA-VRRP-V3-MIB.

         Use of AUGMENTS clause implies a one-to-one dependent relationship 
         between the base table, vrrpRouterStatisticsTable, and the augmenting 
         table, tVrrpRtrStatisticsTable. This in effect extends the 
         vrrpRouterStatisticsTable with additional columns."
    ::= { tmnxVrrpObjects 8 }

tVrrpRtrStatisticsEntry OBJECT-TYPE
    SYNTAX       TVrrpRtrStatisticsEntry
    MAX-ACCESS   not-accessible
    STATUS       current
    DESCRIPTION 
        "Each row entry in the tVrrpRtrStatisticsTable represents additional 
         columns in the vrrpRouterStatisticsTable for statistics specific to the
         Nokia SROS series VRRP implementation."
    AUGMENTS { vrrpRouterStatisticsEntry }
    ::= { tVrrpRtrStatisticsTable 1 }

TVrrpRtrStatisticsEntry ::= 
    SEQUENCE {
        tVrrpStatAdvertiseSent                 Counter32,
        tVrrpStatPreemptEvents                 Counter32,
        tVrrpStatPreemptedEvents               Counter32,
        tVrrpStatMasterChanges                 Counter32,
        tVrrpStatAdvIntvlDiscards              Counter32,
        tVrrpStatTotalDiscards                 Counter32
    }

tVrrpStatAdvertiseSent  OBJECT-TYPE
    SYNTAX       Counter32
    MAX-ACCESS   read-only
    STATUS       current
    DESCRIPTION 
        "The value of tVrrpStatAdvertiseSent indicates the total number of VRRP
        advertisements sent by this virtual router."
    ::= { tVrrpRtrStatisticsEntry 1 }    

tVrrpStatPreemptEvents  OBJECT-TYPE
    SYNTAX       Counter32
    MAX-ACCESS   read-only
    STATUS       current
    DESCRIPTION 
        "The value for tVrrpStatPreemptEvents indicates the total 
         number of times the virtual router has preempted another
         non-owner master with lower priority."
    ::= { tVrrpRtrStatisticsEntry 2 }    

tVrrpStatPreemptedEvents  OBJECT-TYPE
    SYNTAX       Counter32
    MAX-ACCESS   read-only
    STATUS       current
    DESCRIPTION 
        "The value for tVrrpStatPreemptedEvents indicates the total 
         number of times the virtual router has been preempted by another
         non-owner master with higher priority."
    ::= { tVrrpRtrStatisticsEntry 3 }    

tVrrpStatMasterChanges  OBJECT-TYPE
    SYNTAX       Counter32
    MAX-ACCESS   read-only
    STATUS       current
    DESCRIPTION 
        "The value for tVrrpStatMasterChanges indicates the total 
         number of times the virtual router has seen the master virtual
         router change."
    ::= { tVrrpRtrStatisticsEntry 4 }

tVrrpStatAdvIntvlDiscards OBJECT-TYPE
    SYNTAX       Counter32
    MAX-ACCESS   read-only
    STATUS       current
    DESCRIPTION
        "The value of tVrrpStatAdvIntvlDiscards indicates the total
         number of VRRP advertisement packets discarded because the
         advertisement interval in the received packet was different than the
         one configured for the local virtual router."
    ::= { tVrrpRtrStatisticsEntry 5 }

tVrrpStatTotalDiscards OBJECT-TYPE
    SYNTAX       Counter32
    MAX-ACCESS   read-only
    STATUS       current
    DESCRIPTION
        "The value of tVrrpStatTotalDiscards indicates the total number of
         VRRP advertisement packets discarded for any reason. This includes
         the packets discarded due to advertise interval mismatch and address
         list mismatch."
    ::= { tVrrpRtrStatisticsEntry 6 }


-- ***************************************************************************
-- TIMETRA-VRRP-MIB Master Table for IPv6
-- ***************************************************************************

tVrrpRtrMasterTable OBJECT-TYPE
    SYNTAX       SEQUENCE OF TVrrpRtrMasterEntry
    MAX-ACCESS   not-accessible
    STATUS       current
    DESCRIPTION  
        "The tVrrpRtrMasterTable is a read-only table which provides
         a list of the master primary addresses that have been seen by the
         VRRP virtual router instance. Only the most recent 32 masters are 
         listed by this table."
    ::= { tmnxVrrpObjects 9 }

tVrrpRtrMasterEntry OBJECT-TYPE
    SYNTAX       TVrrpRtrMasterEntry
    MAX-ACCESS   not-accessible
    STATUS       current
    DESCRIPTION 
        "Each row entry in the tVrrpRtrMasterTable represents the
         primary address of a VRRP virtual router instance that has 
         become the master as seen by the virtual router instance identified
         by ifIndex and vrrpOperVrId."
    INDEX { ifIndex, vrrpOperationsVrId,
            tVrrpRtrMasterInetAddrType, tVrrpRtrMasterPrimaryAddr }
    ::= { tVrrpRtrMasterTable 1 }

TVrrpRtrMasterEntry ::= 
    SEQUENCE {
        tVrrpRtrMasterInetAddrType           InetAddressType,  
        tVrrpRtrMasterPrimaryAddr            InetAddress,
        tVrrpRtrMasterLastSeen               TimeStamp,
        tVrrpRtrMasterMessageCount           Counter32,
        tVrrpRtrMasterAuthSequence           Integer32,
        tVrrpRtrMasterIPListMatch            TruthValue      
    }

tVrrpRtrMasterInetAddrType OBJECT-TYPE  
    SYNTAX       InetAddressType  
    MAX-ACCESS   not-accessible  
    STATUS       current  
    DESCRIPTION  
        "The IP address type of tVrrpRtrMasterPrimaryAddr." 
    ::= { tVrrpRtrMasterEntry 1 }   

tVrrpRtrMasterPrimaryAddr  OBJECT-TYPE
    SYNTAX       InetAddress (SIZE(0|4|16)) 
    MAX-ACCESS   not-accessible
    STATUS       current
    DESCRIPTION 
        "The value of tVrrpRtrMasterPrimaryAddr identifies the primary 
         address of the virtual router that became a master as seen by the
         virtual router instance identified by ifIndex and vrrpOperVrId."
    ::= { tVrrpRtrMasterEntry 2 }    

tVrrpRtrMasterLastSeen  OBJECT-TYPE
    SYNTAX       TimeStamp
    MAX-ACCESS   read-only
    STATUS       current
    DESCRIPTION 
        "The value for tVrrpRtrMasterLastSeen indicates the sysUpTime
         when the master was last seen by this virtual router instance. In 
         other words it is the timestamp of the last advertisement message 
         that was received from that master."
    ::= { tVrrpRtrMasterEntry 3 }    

tVrrpRtrMasterMessageCount  OBJECT-TYPE
    SYNTAX       Counter32
    MAX-ACCESS   read-only
    STATUS       current
    DESCRIPTION 
        "The value for tVrrpRtrMasterMessageCount indicates the total 
         number of VRRP advertisement messages that have been received 
         from the master."
    ::= { tVrrpRtrMasterEntry 4 }    

tVrrpRtrMasterAuthSequence  OBJECT-TYPE
    SYNTAX       Integer32
    MAX-ACCESS   read-only
    STATUS       current
    DESCRIPTION 
        "The value for tVrrpRtrMasterAuthSequence indicates the last
         sequence number seen in the IP Authentication header of the 
         advertisement messages received from the master.
         A negative value implies that the master was not being 
         authenticated via IP authentication header."
    ::= { tVrrpRtrMasterEntry 5 }   

tVrrpRtrMasterIPListMatch  OBJECT-TYPE
    SYNTAX       TruthValue
    MAX-ACCESS   read-only
    STATUS       current
    DESCRIPTION 
        "The value for tVrrpRtrMasterIPListMatch indicates whether or not
         the IP address list in the advertisement messages received from 
         the master matched the configured virtual router IP address list."
    ::= { tVrrpRtrMasterEntry 6 }   

-- ***************************************************************************
-- The Nokia SROS series VRRP Host Unreachable Priority Event Table (IPv6)
-- ***************************************************************************

tVrrpHstUnrchEvtTblLastChgd OBJECT-TYPE
    SYNTAX      TimeStamp
    MAX-ACCESS  read-only
    STATUS      current
    DESCRIPTION
        "Timestamp of the last change to the tVrrpHstUnrchEvtTable
         either from adding a row or removing a row."
    ::= { tmnxVrrpPolicyObjects 8 }

tVrrpHstUnrchEvtTable OBJECT-TYPE
    SYNTAX       SEQUENCE OF TVrrpHostUnreachableEventEntry
    MAX-ACCESS   not-accessible
    STATUS       current
    DESCRIPTION  
        "The tVrrpHstUnrchEvtTable contains a list of Host 
         Unreachable Priority Events."
    ::= { tmnxVrrpPolicyObjects 9 }

tVrrpHstUnrchEvtEntry OBJECT-TYPE
    SYNTAX       TVrrpHostUnreachableEventEntry
    MAX-ACCESS   not-accessible
    STATUS       current
    DESCRIPTION 
        "Each row entry in the tVrrpHstUnrchEvtTable 
         represents an instance of a 'HostUnreachable' Priority 
         Event used to override or adjust the base priority value 
         of a VRRP virtual router instance depending on the operational 
         state of the event.
    
         Entries can be created and deleted via SNMP SET operations 
         using tVrrpHstUnrchEvtRowStatus."
    INDEX { tmnxVrrpPolicyId,
            tVrrpHstUnrchEvtAddrType,
            tVrrpHstUnrchEvtIpAddr,
            tVrrpHstUnrchEvtIfName
          }
    ::= { tVrrpHstUnrchEvtTable 1 }

TVrrpHostUnreachableEventEntry ::= 
    SEQUENCE {
        tVrrpHstUnrchEvtAddrType            InetAddressType,
        tVrrpHstUnrchEvtIpAddr              InetAddress,
        tVrrpHstUnrchEvtIfName              TNamedItemOrEmpty,
        tVrrpHstUnrchEvtRowStatus           RowStatus,
        tVrrpHstUnrchEvtPriority            TmnxVrrpPriority,
        tVrrpHstUnrchEvtType                TmnxEventType,
        tVrrpHstUnrchEvtHoldSet             TmnxEventHoldSet,
        tVrrpHstUnrchEvtInterval            Unsigned32,
        tVrrpHstUnrchEvtTimeout             Unsigned32,
        tVrrpHstUnrchEvtDropCount           Unsigned32,
        tVrrpHstUnrchEvtOperState           TmnxHostUnreachableEventOperState,
        tVrrpHstUnrchEvtHoldSetRemaining    TmnxEventHoldSet,
        tVrrpHstUnrchEvtPrevState           TmnxHostUnreachableEventOperState,
        tVrrpHstUnrchEvtLastTransition      TimeStamp,
        tVrrpHstUnrchEvtSetCounter          Counter32,
        tVrrpHstUnrchEvtInUse               TruthValue,
        tVrrpHstUnrchEvtHoldClear           TmnxEventHoldClear,
        tVrrpHstUnrchEvtHldClrRemain        TmnxEventHoldClear,
        tVrrpHstUnrchEvtLastChgd            TimeStamp,
        tVrrpHstUnrchEvtSize                Unsigned32
    }

tVrrpHstUnrchEvtAddrType OBJECT-TYPE  
    SYNTAX       InetAddressType  
    MAX-ACCESS   not-accessible  
    STATUS       current  
    DESCRIPTION  
        "The IP address type of tVrrpHstUnrchEvtIpAddr." 
    ::= { tVrrpHstUnrchEvtEntry 1 }   

tVrrpHstUnrchEvtIpAddr  OBJECT-TYPE
    SYNTAX       InetAddress ( SIZE (4|16|20)) 
    MAX-ACCESS   not-accessible
    STATUS       current
    DESCRIPTION 
        "This priority control event monitors the ability to receive ICMP 
         Echo Reply packets from a host which is uniquely identified by 
         the index value tVrrpHstUnrchEvtIpAddr."
    ::= { tVrrpHstUnrchEvtEntry 2 } 

tVrrpHstUnrchEvtIfName  OBJECT-TYPE
    SYNTAX       TNamedItemOrEmpty
    MAX-ACCESS   not-accessible
    STATUS       current
    DESCRIPTION 
        "The value of tVrrpHstUnrchEvtIfName specifies the interface
         name when a link-local address is specified for
         tVrrpHstUnrchEvtIpAddr. 

         This object is set to empty when tVrrpHstUnrchEvtIpAddr is not a
         link-local address."
    ::= { tVrrpHstUnrchEvtEntry 3 } 

tVrrpHstUnrchEvtRowStatus  OBJECT-TYPE
    SYNTAX       RowStatus
    MAX-ACCESS   read-create
    STATUS       current
    DESCRIPTION 
        "tVrrpHstUnrchEvtRowStatus is used for the creation
         or deletion of entries in the tVrrpHstUnrchEvtTable."
    ::= { tVrrpHstUnrchEvtEntry 4 } 

tVrrpHstUnrchEvtPriority  OBJECT-TYPE
    SYNTAX       TmnxVrrpPriority
    MAX-ACCESS   read-create
    STATUS       current
    DESCRIPTION 
        "The value of tVrrpHstUnrchEvtPriority specifies 
         the priority level associated with this event. When the 
         operational state of the event transitions to one of the 
         'set' states, this value will either be subtracted from the 
         in-use priority (if the event is a 'delta' event) or the 
         in-use priority will be explicitly overridden by this 
         priority value (if the event is an 'explicit' event)."
    DEFVAL { 0 }
    ::= { tVrrpHstUnrchEvtEntry 5 } 

tVrrpHstUnrchEvtType  OBJECT-TYPE
    SYNTAX       TmnxEventType
    MAX-ACCESS   read-create
    STATUS       current
    DESCRIPTION 
        "The value of tVrrpHstUnrchEvtType specifies whether
         this event is a 'delta' or an 'explicit' event. When the event 
         is 'set', the value of tVrrpHstUnrchEvtPriority will 
         be subtracted from the in-use priority in case of a 'delta' event
         or the in-use priority will be explicitly overridden by the value
         of tVrrpHstUnrchEvtPriority in case of an 'explicit' 
         event."
    DEFVAL { delta }
    ::= { tVrrpHstUnrchEvtEntry 6 } 

tVrrpHstUnrchEvtHoldSet  OBJECT-TYPE
    SYNTAX       TmnxEventHoldSet
    UNITS        "seconds"
    MAX-ACCESS   read-create
    STATUS       current
    DESCRIPTION 
        "The value of tVrrpHstUnrchEvtHoldSet specifies the configured Hold
         Set time associated with the event."
    DEFVAL { 0 }
    ::= { tVrrpHstUnrchEvtEntry 7 } 

tVrrpHstUnrchEvtInterval  OBJECT-TYPE
    SYNTAX       Unsigned32 (1..60)
    UNITS        "seconds"
    MAX-ACCESS   read-create
    STATUS       current
    DESCRIPTION 
        "The value of tVrrpHstUnrchEvtInterval specifies 
         the amount of time in seconds between consecutive ICMP 
         Echo Requests sent to the far end host IP address."
    DEFVAL { 1 }
    ::= { tVrrpHstUnrchEvtEntry 8 } 

tVrrpHstUnrchEvtTimeout  OBJECT-TYPE
    SYNTAX       Unsigned32 (1..60)
    UNITS        "seconds"
    MAX-ACCESS   read-create
    STATUS       current
    DESCRIPTION 
        "The value of tVrrpHstUnrchEvtTimeout specifies 
         the amount of time in seconds that is allowed for receiving
         an ICMP Echo Reply message from the far end host IP address
         to which a ICMP Echo Request message was sent out. If a reply 
         is not received within this time the far end host is considered 
         unresponsive."
    DEFVAL { 1 }
    ::= { tVrrpHstUnrchEvtEntry 9 } 

tVrrpHstUnrchEvtDropCount  OBJECT-TYPE
    SYNTAX       Unsigned32 (1..60)
    MAX-ACCESS   read-create
    STATUS       current
    DESCRIPTION 
        "The value of tVrrpHstUnrchEvtDropCount specifies 
         the number of consecutive ICMP Echo Request message send attempts
         that must fail for the priority event to enter a 'set' state."
    DEFVAL { 3 }
    ::= { tVrrpHstUnrchEvtEntry 10 } 

tVrrpHstUnrchEvtOperState  OBJECT-TYPE
    SYNTAX       TmnxHostUnreachableEventOperState
    MAX-ACCESS   read-only
    STATUS       current
    DESCRIPTION 
        "The value of tVrrpHstUnrchEvtOperState indicates
         the current operational state of the event."
    ::= { tVrrpHstUnrchEvtEntry 11 } 

tVrrpHstUnrchEvtHoldSetRemaining  OBJECT-TYPE
    SYNTAX       TmnxEventHoldSet
    UNITS        "seconds"
    MAX-ACCESS   read-only
    STATUS       current
    DESCRIPTION 
        "The value of tVrrpHstUnrchEvtHoldSetRemaining 
         indicates the current value of the hold-set timer i.e. the 
         amount of time remaining before the event will transition 
         into the cleared state."
    ::= { tVrrpHstUnrchEvtEntry 12 } 

tVrrpHstUnrchEvtPrevState  OBJECT-TYPE
    SYNTAX       TmnxHostUnreachableEventOperState 
    MAX-ACCESS   read-only
    STATUS       current
    DESCRIPTION 
        "The value of tVrrpHstUnrchEvtPrevState indicates the previous
         operational state of the event."
    ::= { tVrrpHstUnrchEvtEntry 13 } 

tVrrpHstUnrchEvtLastTransition  OBJECT-TYPE
    SYNTAX       TimeStamp
    MAX-ACCESS   read-only
    STATUS       current
    DESCRIPTION 
        "The value of tVrrpHstUnrchEvtLastTransition indicates the sysUpTime
         when the operational state of the event last changed."
    ::= { tVrrpHstUnrchEvtEntry 14 } 

tVrrpHstUnrchEvtSetCounter  OBJECT-TYPE
    SYNTAX       Counter32
    MAX-ACCESS   read-only
    STATUS       current
    DESCRIPTION 
        "The value of tVrrpHstUnrchEvtSetCounter indicates 
         the number of times the event has transitioned to one of the 
         'set' states."
    ::= { tVrrpHstUnrchEvtEntry 15 } 

tVrrpHstUnrchEvtInUse  OBJECT-TYPE
    SYNTAX       TruthValue
    MAX-ACCESS   read-only
    STATUS       current
    DESCRIPTION 
        "The value of tVrrpHstUnrchEvtInUse when set to 'true' indicates that
         the event is currently affecting the in-use priority of some 
         virtual router."
    ::= { tVrrpHstUnrchEvtEntry 16 } 

tVrrpHstUnrchEvtHoldClear  OBJECT-TYPE
    SYNTAX       TmnxEventHoldClear
    UNITS        "seconds"
    MAX-ACCESS   read-create
    STATUS       current
    DESCRIPTION 
        "The value of tVrrpHstUnrchEvtHoldClear specifies 
         the configured Hold Clear time associated with the event."
    DEFVAL { 0 }
    ::= { tVrrpHstUnrchEvtEntry 17 } 

tVrrpHstUnrchEvtHldClrRemain  OBJECT-TYPE
    SYNTAX       TmnxEventHoldClear
    UNITS        "seconds"
    MAX-ACCESS   read-only
    STATUS       current
    DESCRIPTION 
        "The value of tVrrpHstUnrchEvtHldClrRemain indicates the current value
         of the hold-clear timer i.e. the amount of time remaining before the
         cleared event will have an effect on the virtual router instance."
    ::= { tVrrpHstUnrchEvtEntry 18 } 

tVrrpHstUnrchEvtLastChgd  OBJECT-TYPE
    SYNTAX       TimeStamp
    MAX-ACCESS   read-only
    STATUS       current
    DESCRIPTION 
        "The value of tVrrpHstUnrchEvtLastChgd indicates the
         time stamp of the last change to this row of this table."
    ::= { tVrrpHstUnrchEvtEntry 19 } 

tVrrpHstUnrchEvtSize  OBJECT-TYPE
    SYNTAX       Unsigned32 (0..16384)
    UNITS        "bytes"
    MAX-ACCESS   read-create
    STATUS       current
    DESCRIPTION 
        "The value of tVrrpHstUnrchEvtSize specifies the padding size
         to be used for the ICMP packet for this event."
    DEFVAL { 56 }
    ::= { tVrrpHstUnrchEvtEntry 20 } 

   
-- ***************************************************************************
-- The Nokia SROS series VRRP Route Unknown Priority Event Table (IPv6)
-- ***************************************************************************

tVrrpRtUnknEvtTblLastChgd OBJECT-TYPE
    SYNTAX      TimeStamp
    MAX-ACCESS  read-only
    STATUS      current
    DESCRIPTION
        "Timestamp of the last change to the tVrrpRtUnknEvtTable
         either from adding a row or removing a row."
    ::= { tmnxVrrpPolicyObjects 10 }

tVrrpRtUnknEvtTable OBJECT-TYPE
    SYNTAX       SEQUENCE OF TVrrpRouteUnknownEventEntry
    MAX-ACCESS   not-accessible
    STATUS       current
    DESCRIPTION  
        "The tVrrpRtUnknEvtTable contains a list of Route 
         Unknown Priority Events."
    ::= { tmnxVrrpPolicyObjects 11 }

tVrrpRtUnknEvtEntry OBJECT-TYPE
    SYNTAX       TVrrpRouteUnknownEventEntry
    MAX-ACCESS   not-accessible
    STATUS       current
    DESCRIPTION 
        "Each row entry in the tVrrpRtUnknEvtTable represents 
         an instance of a Route Unknown Priority Event used to override 
         or adjust the base priority value of a VRRP virtual router 
         instance depending on the operational state of the event.
    
         Entries can be created and deleted via SNMP SET operations 
         using tVrrpRtUnknEvtRowStatus."
    INDEX { tmnxVrrpPolicyId, tVrrpRtUnknEvtPrefixType,
            tVrrpRtUnknEvtPrefix,
            tVrrpRtUnknEvtMaskLen}
    ::= { tVrrpRtUnknEvtTable 1 }

TVrrpRouteUnknownEventEntry ::= 
    SEQUENCE {
        tVrrpRtUnknEvtPrefixType          InetAddressType,
        tVrrpRtUnknEvtPrefix              InetAddress,
        tVrrpRtUnknEvtMaskLen             InetAddressPrefixLength,
        tVrrpRtUnknEvtRowStatus           RowStatus,
        tVrrpRtUnknEvtPriority            TmnxVrrpPriority,
        tVrrpRtUnknEvtType                TmnxEventType,
        tVrrpRtUnknEvtHoldSet             TmnxEventHoldSet,
        tVrrpRtUnknEvtLessSpecific        TruthValue,
        tVrrpRtUnknEvtDefaultAllowed      TruthValue,
        tVrrpRtUnknEvtProtocol            BITS,
        tVrrpRtUnknEvtOperState      TmnxRouteUnknownEventOperState,
        tVrrpRtUnknEvtHoldSetRemaining    TmnxEventHoldSet,
        tVrrpRtUnknEvtPrevState      TmnxRouteUnknownEventOperState,
        tVrrpRtUnknEvtLastTransition      TimeStamp,
        tVrrpRtUnknEvtSetCounter          Counter32,
        tVrrpRtUnknEvtInUse               TruthValue,
        tVrrpRtUnknEvtHoldClear           TmnxEventHoldClear,
        tVrrpRtUnknEvtHoldClearRemaining  TmnxEventHoldClear,
        tVrrpRtUnknEvtLastChgd            TimeStamp
    }

tVrrpRtUnknEvtPrefixType OBJECT-TYPE  
    SYNTAX       InetAddressType  
    MAX-ACCESS   not-accessible  
    STATUS       current  
    DESCRIPTION  
        "The IP address type of tVrrpRtUnknEvtPrefix." 
    ::= { tVrrpRtUnknEvtEntry 1 }   

tVrrpRtUnknEvtPrefix  OBJECT-TYPE
    SYNTAX       InetAddress (SIZE(0|4|16)) 
    MAX-ACCESS   not-accessible
    STATUS       current
    DESCRIPTION 
        "The index value tVrrpRtUnknEvtPrefix identifies the 
         IP prefix of the route whose existence within the routing table 
         is being monitored by this priority control event."
    ::= { tVrrpRtUnknEvtEntry 2 } 

tVrrpRtUnknEvtMaskLen  OBJECT-TYPE
    SYNTAX      InetAddressPrefixLength
    MAX-ACCESS   not-accessible
    STATUS       current
    DESCRIPTION 
        "The index value tVrrpRtUnknEvtMaskLen identifies the 
         prefix mask length of the route whose existence within the routing
         table is being monitored by this priority control event."
    ::= { tVrrpRtUnknEvtEntry 3 } 

tVrrpRtUnknEvtRowStatus  OBJECT-TYPE
    SYNTAX       RowStatus
    MAX-ACCESS   read-create
    STATUS       current
    DESCRIPTION 
        "tVrrpRtUnknEvtRowStatus is used for the creation or 
         deletion of entries in the tVrrpRtUnknEvtTable."
    ::= { tVrrpRtUnknEvtEntry 4 } 

tVrrpRtUnknEvtPriority  OBJECT-TYPE
    SYNTAX       TmnxVrrpPriority
    MAX-ACCESS   read-create
    STATUS       current
    DESCRIPTION 
        "The value of tVrrpRtUnknEvtPriority specifies the 
         priority level associated with this event. When the operational 
         state of the event transitions to one of the 'set' states, this 
         value will either be subtracted from the in-use priority (if the 
         event is a 'delta' event) or the in-use priority will be 
         explicitly overridden by this priority value (if the event is 
         an 'explicit' event)."
    DEFVAL { 0 }
    ::= { tVrrpRtUnknEvtEntry 5 } 

tVrrpRtUnknEvtType  OBJECT-TYPE
    SYNTAX       TmnxEventType
    MAX-ACCESS   read-create
    STATUS       current
    DESCRIPTION 
        "The value of tVrrpRtUnknEvtType specifies whether 
         this event is a 'delta' or an 'explicit' event. When the event 
         is 'set', the value of tVrrpRtUnknEvtPriority will 
         be subtracted from the in-use priority in case of a 'delta' 
         event or the in-use priority will be explicitly overridden by 
         the value of tVrrpRtUnknEvtPriority in case of an
         'explicit' event."
    DEFVAL { delta }
    ::= { tVrrpRtUnknEvtEntry 6 } 

tVrrpRtUnknEvtHoldSet  OBJECT-TYPE
    SYNTAX       TmnxEventHoldSet
    UNITS        "seconds"
    MAX-ACCESS   read-create
    STATUS       current
    DESCRIPTION 
        "The value of tVrrpRtUnknEvtHoldSet specifies the 
         configured Hold Set time associated with the event."
    DEFVAL { 0 }
    ::= { tVrrpRtUnknEvtEntry 7 } 

tVrrpRtUnknEvtLessSpecific  OBJECT-TYPE
    SYNTAX       TruthValue
    MAX-ACCESS   read-create
    STATUS       current
    DESCRIPTION 
        "Setting the value of tVrrpRtUnknEvtLessSpecific 
         to 'true', allows a route with a less specific IP prefix to 
         match the IP prefix associated with the event."
    DEFVAL { false }
    ::= { tVrrpRtUnknEvtEntry 8 } 

tVrrpRtUnknEvtDefaultAllowed  OBJECT-TYPE
    SYNTAX       TruthValue
    MAX-ACCESS   read-create
    STATUS       current
    DESCRIPTION 
        "Setting the value of tVrrpRtUnknEvtDefaultAllowed 
         to 'true', allows the default route to match the IP prefix 
         associated with the event. This value is valid only when
         tVrrpRtUnknEvtLessSpecific is 'true'. If 
         tVrrpRtUnknEvtLessSpecific is 'false' this value
         is ignored."
    DEFVAL { false }
    ::= { tVrrpRtUnknEvtEntry 9 } 

tVrrpRtUnknEvtProtocol  OBJECT-TYPE
    SYNTAX       BITS {
                     bgp(0),
                     ospf(1),
                     isis(2),
                     rip(3),
                     static(4),
                     bgpVpn(5)
                 }
    MAX-ACCESS   read-create
    STATUS       current
    DESCRIPTION 
        "The bits of tVrrpRtUnknEvtProtocol specify the 
         allowed route sources when matching the IP prefix associated 
         with this event with the results of a Route table lookup.
         If the bit corresponding to a protocol is set then the 
         protocol is considered as a route source match constraint."
    DEFVAL { { } }
    ::= { tVrrpRtUnknEvtEntry 10 } 

tVrrpRtUnknEvtOperState  OBJECT-TYPE
    SYNTAX       TmnxRouteUnknownEventOperState
    MAX-ACCESS   read-only
    STATUS       current
    DESCRIPTION 
        "The value of tVrrpRtUnknEvtOperState indicates the 
         current operational state of the event."
    ::= { tVrrpRtUnknEvtEntry 11 } 

tVrrpRtUnknEvtHoldSetRemaining  OBJECT-TYPE
    SYNTAX       TmnxEventHoldSet
    UNITS        "seconds"
    MAX-ACCESS   read-only
    STATUS       current
    DESCRIPTION 
        "The value of tVrrpRtUnknEvtHoldSetRemaining indicates 
         the current value of the hold-set timer i.e. the amount of time 
         remaining before the event will transition into the cleared state."
    ::= { tVrrpRtUnknEvtEntry 12 } 

tVrrpRtUnknEvtPrevState  OBJECT-TYPE
    SYNTAX       TmnxRouteUnknownEventOperState 
    MAX-ACCESS   read-only
    STATUS       current
    DESCRIPTION 
        "The value of tVrrpRtUnknEvtPrevState indicates the 
         previous operational state of the event."
    ::= { tVrrpRtUnknEvtEntry 13 } 

tVrrpRtUnknEvtLastTransition  OBJECT-TYPE
    SYNTAX       TimeStamp
    MAX-ACCESS   read-only
    STATUS       current
    DESCRIPTION 
        "The value of tVrrpRtUnknEvtLastTransition indicates 
         the sysUpTime when the operational state of the event last 
         changed."
    ::= { tVrrpRtUnknEvtEntry 14 } 

tVrrpRtUnknEvtSetCounter  OBJECT-TYPE
    SYNTAX       Counter32
    MAX-ACCESS   read-only
    STATUS       current
    DESCRIPTION 
        "The value of tVrrpRtUnknEvtSetCounter indicates the
         number of times the event has transitioned to one of the 'set' 
         states."
    ::= { tVrrpRtUnknEvtEntry 15 } 

tVrrpRtUnknEvtInUse  OBJECT-TYPE
    SYNTAX       TruthValue
    MAX-ACCESS   read-only
    STATUS       current
    DESCRIPTION 
        "The value of tVrrpRtUnknEvtInUse when set to 'true' indicates that the
         event is currently affecting the in-use priority of some virtual
         router."
    ::= { tVrrpRtUnknEvtEntry 16 } 

tVrrpRtUnknEvtHoldClear  OBJECT-TYPE
    SYNTAX       TmnxEventHoldClear
    UNITS        "seconds"
    MAX-ACCESS   read-create
    STATUS       current
    DESCRIPTION 
        "The value of tVrrpRtUnknEvtHoldClear specifies the
         configured Hold Clear time associated with the event."
    DEFVAL { 0 }
    ::= { tVrrpRtUnknEvtEntry 17 } 

tVrrpRtUnknEvtHoldClearRemaining  OBJECT-TYPE
    SYNTAX       TmnxEventHoldClear
    UNITS        "seconds"
    MAX-ACCESS   read-only
    STATUS       current
    DESCRIPTION 
        "The value of tVrrpRtUnknEvtHoldClearRemaining indicates 
         the current value of the hold-clear timer i.e. the amount of time
         amount of time remaining before the cleared event will have an
         effect on the virtual router instance."
    ::= { tVrrpRtUnknEvtEntry 18 } 

tVrrpRtUnknEvtLastChgd  OBJECT-TYPE
    SYNTAX       TimeStamp
    MAX-ACCESS   read-only
    STATUS       current
    DESCRIPTION 
        "The value of tVrrpRtUnknEvtLastChgd indicates the
         time stamp of the last change to this row of this table."
    ::= { tVrrpRtUnknEvtEntry 19 } 
   

-- ***************************************************************************
-- The Nokia SROS series VRRP Route Unknown Event Next Hop Table (IPv6)
-- ***************************************************************************

tVrrpRtUnknEvtNextHopTblLastChgd OBJECT-TYPE
    SYNTAX      TimeStamp
    MAX-ACCESS  read-only
    STATUS      current
    DESCRIPTION
        "Timestamp of the last change to the tVrrpRtUnknEvtNextHopTable
         either from adding a row or removing a row."
    ::= { tmnxVrrpPolicyObjects 12 }

tVrrpRtUnknEvtNextHopTable OBJECT-TYPE
    SYNTAX       SEQUENCE OF TVrrpRouteUnknownEventNextHopEntry
    MAX-ACCESS   not-accessible
    STATUS       current
    DESCRIPTION  
        "The tVrrpRtUnknEvtNextHopTable contains a list of 
         next-hop IP addresses associated with each Route Unknown 
         Priority Events defined in tVrrpRtUnknEvtTable."
    ::= { tmnxVrrpPolicyObjects 13 }

tVrrpRtUnknEvtNextHopEntry OBJECT-TYPE
    SYNTAX       TVrrpRouteUnknownEventNextHopEntry
    MAX-ACCESS   not-accessible
    STATUS       current
    DESCRIPTION 
        "Each row entry in the tVrrpRtUnknEvtNextHopTable
         represents an instance of a next-hop IP address which is 
         defined as a match criterion for the Route Unknown Priority 
         Event associated with this entry. 
    
         Entries can be created and deleted via SNMP SET operations 
         using tVrrpRtUnknEvtNextHopRowStatus."
    INDEX { tmnxVrrpPolicyId,
            tVrrpRtUnknEvtPrefixType,
            tVrrpRtUnknEvtPrefix,
            tVrrpRtUnknEvtMaskLen,
            tVrrpRtUnknEvtNextHopType,
            tVrrpRtUnknEvtNextHop,
            tVrrpRtUnknEvtNextHopIfName
          }
    ::= { tVrrpRtUnknEvtNextHopTable 1 }

TVrrpRouteUnknownEventNextHopEntry ::= 
    SEQUENCE {
        tVrrpRtUnknEvtNextHopType       InetAddressType,
        tVrrpRtUnknEvtNextHop           InetAddress,
        tVrrpRtUnknEvtNextHopIfName     TNamedItemOrEmpty,
        tVrrpRtUnknEvtNextHopRowStatus  RowStatus,
        tVrrpRtUnknEvtNextHopLastChgd   TimeStamp
    }

tVrrpRtUnknEvtNextHopType OBJECT-TYPE  
    SYNTAX       InetAddressType  
    MAX-ACCESS   not-accessible  
    STATUS       current  
    DESCRIPTION  
        "The IP address type of tVrrpRtUnknEvtNextHop." 
    ::= { tVrrpRtUnknEvtNextHopEntry 1 }   

tVrrpRtUnknEvtNextHop  OBJECT-TYPE
    SYNTAX       InetAddress ( SIZE(4|16|20)) 
    MAX-ACCESS   not-accessible
    STATUS       current
    DESCRIPTION 
        "The index value tVrrpRtUnknEvtNextHop identifies 
         the next-hop IP address which is used to match the route prefix
         being monitored by this priority control event with the results
         of a route table lookup."
    ::= { tVrrpRtUnknEvtNextHopEntry 2 } 

tVrrpRtUnknEvtNextHopIfName  OBJECT-TYPE
    SYNTAX       TNamedItemOrEmpty
    MAX-ACCESS   not-accessible
    STATUS       current
    DESCRIPTION 
        "The value of tVrrpRtUnknEvtNextHopIfName specifies the interface
         name when a link-local address is specified for
         tVrrpRtUnknEvtNextHop. 

         This object is set to empty when tVrrpRtUnknEvtNextHop is not a
         link-local address."
    ::= { tVrrpRtUnknEvtNextHopEntry 3 } 

tVrrpRtUnknEvtNextHopRowStatus  OBJECT-TYPE
    SYNTAX       RowStatus
    MAX-ACCESS   read-create
    STATUS       current
    DESCRIPTION 
        "tVrrpRtUnknEvtNextHopRowStatus is used for the creation or deletion
         of entries in the tVrrpRtUnknEvtNextHopTable."
    ::= { tVrrpRtUnknEvtNextHopEntry 4 } 

tVrrpRtUnknEvtNextHopLastChgd  OBJECT-TYPE
    SYNTAX       TimeStamp
    MAX-ACCESS   read-only
    STATUS       current
    DESCRIPTION 
        "The value of tVrrpRtUnknEvtNextHopLastChgd indicates the
         time stamp of the last change to this row of this table."
    ::= { tVrrpRtUnknEvtNextHopEntry 5 } 

-- --------------------------------------------
-- tVrrpIpv6RouterAdvertTable
-- --------------------------------------------

tVrrpIpv6RouterAdvertTable OBJECT-TYPE
    SYNTAX     SEQUENCE OF TVrrpIpv6RouterAdvertEntry
    MAX-ACCESS not-accessible
    STATUS     current
    DESCRIPTION
           "The table containing information used to construct VRRP specific
           extensions to router advertisements."
    ::= { tmnxVrrpObjects 10 }

tVrrpIpv6RouterAdvertEntry OBJECT-TYPE
    SYNTAX     TVrrpIpv6RouterAdvertEntry
    MAX-ACCESS not-accessible
    STATUS     current
    DESCRIPTION
        "The tVrrpIpv6RouterAdvertEntry provides VRRP specific extension to the
         ipv6RouterAdvertEntry in the IP-MIB.

         Use of AUGMENTS clause implies a one-to-one dependent relationship 
         between the base table, ipv6RouterAdvertTable, and the augmenting
         table, tVrrpIpv6RouterAdvertTable. This in effect extends the
         ipv6RouterAdvertTable with additional columns.
         
         Creation (or deletion) of a row in the ipv6RouterAdvertTable results 
         in the same fate for the row in the tVrrpIpv6RouterAdvertTable."
    AUGMENTS { ipv6RouterAdvertEntry }
    ::= { tVrrpIpv6RouterAdvertTable 1 }

TVrrpIpv6RouterAdvertEntry ::= SEQUENCE {
        tVrrpIpv6RouterAdvertUseVirtualMac      TruthValue
    }

tVrrpIpv6RouterAdvertUseVirtualMac OBJECT-TYPE
    SYNTAX     TruthValue
    MAX-ACCESS read-create
    STATUS     current
    DESCRIPTION
        "The value of tVrrpIpv6RouterAdvertUseVirtualMac specifies whether
        Router Advertisement messages are sent using the VRRP virtual MAC
        address, provided that the virtual router is currently the master.
        
        If the virtual router is not the master, no Router Advertisement
        messages are sent."
    DEFVAL { false }
    ::= { tVrrpIpv6RouterAdvertEntry 1 }

-- ***************************************************************************
-- TIMETRA-VRRP-MIB BFD Interface Table (IPv4/IPv6)
-- ***************************************************************************

tVrrpAssoBfdIntfTblLastChgd OBJECT-TYPE
    SYNTAX      TimeStamp
    MAX-ACCESS  read-only
    STATUS      current
    DESCRIPTION
        "Timestamp of the last change to the tVrrpAssoBfdIntfTable
         either from adding a row or removing a row."
    ::= { tmnxVrrpObjects 11 }

tVrrpAssoBfdIntfTable OBJECT-TYPE
    SYNTAX       SEQUENCE OF TVrrpAssoBfdIntfEntry
    MAX-ACCESS   not-accessible
    STATUS       current
    DESCRIPTION  
        "The tVrrpAssoBfdIntfTable is a read-only table which provides
         a list of the BFD interfaces associated with the corresponding
         VRRP virtual router instance.

         The BFD interface provides a fast mechanism for changing the state
         of an VRRP virtual router instance riding on the same subnet."
    ::= { tmnxVrrpObjects 12 }

tVrrpAssoBfdIntfEntry OBJECT-TYPE
    SYNTAX       TVrrpAssoBfdIntfEntry
    MAX-ACCESS   not-accessible
    STATUS       current
    DESCRIPTION 
        "Each row entry in the tVrrpAssoBfdIntfTable represents the
         BFD interface associated with VRRP virtual router instance
         identified by ifIndex, tVrrpAssoBfdIntfVrIdIpType and vrrpOperVrId."
    INDEX { ifIndex, tVrrpAssoBfdIntfVrIdIpType, vrrpOperVrId,
            tVrrpAssoBfdIntfSvcId,
            tVrrpAssoBfdIntfIfName, tVrrpAssoBfdIntfDestIpType,
            tVrrpAssoBfdIntfDestIp }
    ::= { tVrrpAssoBfdIntfTable 1 }

TVrrpAssoBfdIntfEntry ::= 
    SEQUENCE {
        tVrrpAssoBfdIntfVrIdIpType       InetAddressType,
        tVrrpAssoBfdIntfSvcId            TmnxServId,
        tVrrpAssoBfdIntfIfName           TNamedItem,
        tVrrpAssoBfdIntfDestIpType       InetAddressType,
        tVrrpAssoBfdIntfDestIp           InetAddress,
        tVrrpAssoBfdIntfRowStatus        RowStatus,
        tVrrpAssoBfdIntfLastChgd         TimeStamp,
        tVrrpAssoBfdIntfSrcIpType        InetAddressType,
        tVrrpAssoBfdIntfSrcIp            InetAddress,
        tVrrpAssoBfdIntfSessOperState    TmnxVrrpAssoBfdIntfSessOperState
    }

tVrrpAssoBfdIntfVrIdIpType OBJECT-TYPE
    SYNTAX       InetAddressType
    MAX-ACCESS   not-accessible
    STATUS       current
    DESCRIPTION
        "The value of tVrrpAssoBfdIntfVrIdIpType specifies the address type
         of vrrpOperVrId object."
    ::= { tVrrpAssoBfdIntfEntry 1 }

tVrrpAssoBfdIntfSvcId OBJECT-TYPE
    SYNTAX       TmnxServId
    MAX-ACCESS   not-accessible
    STATUS       current
    DESCRIPTION
        "The value of tVrrpAssoBfdIntfSvcId specifies the service
         ID of the interface running BFD."
    ::= { tVrrpAssoBfdIntfEntry 2 }

tVrrpAssoBfdIntfIfName OBJECT-TYPE
    SYNTAX       TNamedItem
    MAX-ACCESS   not-accessible
    STATUS       current
    DESCRIPTION         
        "The value of tVrrpAssoBfdIntfIfName specifies the name of the
         interface running BFD."
    ::= { tVrrpAssoBfdIntfEntry 3 }

tVrrpAssoBfdIntfDestIpType OBJECT-TYPE
    SYNTAX       InetAddressType
    MAX-ACCESS   not-accessible
    STATUS       current
    DESCRIPTION
        "The value of tVrrpAssoBfdIntfDestIpType specifies the address type
         of tVrrpAssoBfdIntfDestIp object."
    ::= { tVrrpAssoBfdIntfEntry 4 }

tVrrpAssoBfdIntfDestIp OBJECT-TYPE
    SYNTAX       InetAddress (SIZE (0|4|16|20))
    MAX-ACCESS   not-accessible
    STATUS       current
    DESCRIPTION
        "The value of tVrrpAssoBfdIntfDestIp specifies the destination
         IP address on the interface running BFD."
    ::= { tVrrpAssoBfdIntfEntry 5 }

tVrrpAssoBfdIntfRowStatus  OBJECT-TYPE
    SYNTAX       RowStatus
    MAX-ACCESS   read-create
    STATUS       current
    DESCRIPTION 
        "This object tVrrpAssoBfdIntfRowStatus is used for creation or
         deletion of entries in the tVrrpAssoBfdIntfEntry. Deletion of an
         entry in this table will not succeed if it is currently associated
         with any VRRP virtual router instance."
    ::= { tVrrpAssoBfdIntfEntry 6 }    

tVrrpAssoBfdIntfLastChgd  OBJECT-TYPE
    SYNTAX       TimeStamp
    MAX-ACCESS   read-only
    STATUS       current
    DESCRIPTION 
        "The value of tVrrpAssoBfdIntfLastChgd indicates the
         time stamp of the last change to this row of this table."
    ::= { tVrrpAssoBfdIntfEntry 7 } 
   
tVrrpAssoBfdIntfSrcIpType OBJECT-TYPE
    SYNTAX       InetAddressType
    MAX-ACCESS   read-only
    STATUS       current
    DESCRIPTION
        "The value of tVrrpAssoBfdIntfSrcIpType indicates the address type
         of tVrrpAssoBfdIntfSrcIp object."
    ::= { tVrrpAssoBfdIntfEntry 8 }

tVrrpAssoBfdIntfSrcIp OBJECT-TYPE
    SYNTAX       InetAddress (SIZE (0|4|16|20))
    MAX-ACCESS   read-only
    STATUS       current
    DESCRIPTION
        "The value of tVrrpAssoBfdIntfSrcIp indicates the source
         IP address on the interface running BFD."
    ::= { tVrrpAssoBfdIntfEntry 9 }

tVrrpAssoBfdIntfSessOperState OBJECT-TYPE
    SYNTAX       TmnxVrrpAssoBfdIntfSessOperState
    MAX-ACCESS   read-only
    STATUS       current
    DESCRIPTION
        "The value of tVrrpAssoBfdIntfSessOperState indicates the operational
         state of the BFD session the VRRP virtual router instance is relying
         upon for its fast triggering mechanism."
    ::= { tVrrpAssoBfdIntfEntry 10 }

-- ***************************************************************************
-- The Nokia SROS series VRRP MC-IPSEC NON-FWDING Priority Event Table
-- ***************************************************************************

tVrrpPriEvtMcIPsecNoFwdTable OBJECT-TYPE
    SYNTAX       SEQUENCE OF TVrrpPriEvtMcIPsecNoFwdEntry
    MAX-ACCESS   not-accessible
    STATUS       current
    DESCRIPTION  
        "The tVrrpPriEvtMcIPsecNoFwdTable contains a list of multi-chassis
         IPsec non-forwarding priority events for the multi-chassis 
         tunnel-groups."
    ::= { tmnxVrrpPolicyObjects 14 }

tVrrpPriEvtMcIPsecNoFwdEntry OBJECT-TYPE
    SYNTAX       TVrrpPriEvtMcIPsecNoFwdEntry
    MAX-ACCESS   not-accessible
    STATUS       current
    DESCRIPTION 
        "Each row entry in the tVrrpPriEvtMcIPsecNoFwdTable represents 
         an instance of a multi-chassis IPsec tunnel-group Priority Event
         used to override the base priority value of a VRRP virtual router 
         instance depending on the operational state of the event.
    
         Entries can be created and deleted via SNMP SET operations 
         using tVrrpPriEvtMcIPsecNoFwdRowStatus."
    INDEX { tmnxVrrpPolicyId, 
            tVrrpPriEvtMcIPsecNoFwdTnlGrpId }
    ::= { tVrrpPriEvtMcIPsecNoFwdTable 1 }

TVrrpPriEvtMcIPsecNoFwdEntry ::= 
    SEQUENCE {
        tVrrpPriEvtMcIPsecNoFwdTnlGrpId      TmnxTunnelGroupId,
        tVrrpPriEvtMcIPsecNoFwdRowStatus     RowStatus,
        tVrrpPriEvtMcIPsecNoFwdPriority      TmnxVrrpPriority,
        tVrrpPriEvtMcIPsecNoFwdType          TmnxEventType,
        tVrrpPriEvtMcIPsecNoFwdHoldSet       TmnxEventHoldSet,
        tVrrpPriEvtMcIPsecNoFwdOperState     TmnxMcIPsecNoFwdEventOperState,
        tVrrpPriEvtMcIPsecNoFwdHoldSetR      TmnxEventHoldSet,
        tVrrpPriEvtMcIPsecNoFwdPrevState     TmnxMcIPsecNoFwdEventOperState,
        tVrrpPriEvtMcIPsecNoFwdTransTm       TimeStamp,
        tVrrpPriEvtMcIPsecNoFwdSetCntr       Counter32,
        tVrrpPriEvtMcIPsecNoFwdInUse         TruthValue,
        tVrrpPriEvtMcIPsecNoFwdHoldClr       TmnxEventHoldClear,
        tVrrpPriEvtMcIPsecNoFwdHoldClrR      TmnxEventHoldClear
    }

tVrrpPriEvtMcIPsecNoFwdTnlGrpId  OBJECT-TYPE
    SYNTAX       TmnxTunnelGroupId
    MAX-ACCESS   not-accessible
    STATUS       current
    DESCRIPTION 
        "The index value tVrrpPriEvtMcIPsecNoFwdTnlGrpId uniquely identifies 
         the multi-chassis IPSEC tunnel group whose non-forwarding state is
         monitored by this priority control event."
    ::= { tVrrpPriEvtMcIPsecNoFwdEntry 1 } 

tVrrpPriEvtMcIPsecNoFwdRowStatus  OBJECT-TYPE
    SYNTAX       RowStatus
    MAX-ACCESS   read-create
    STATUS       current
    DESCRIPTION 
        "The tVrrpPriEvtMcIPsecNoFwdRowStatus is used for the creation
         or deletion of entries in the tVrrpPriEvtMcIPsecNoFwdTable."
    ::= { tVrrpPriEvtMcIPsecNoFwdEntry 2 } 

tVrrpPriEvtMcIPsecNoFwdPriority  OBJECT-TYPE
    SYNTAX       TmnxVrrpPriority
    MAX-ACCESS   read-create
    STATUS       current
    DESCRIPTION 
        "The value of tVrrpPriEvtMcIPsecNoFwdPriority specifies 
         the priority level associated with this event.
         
         An 'inconsistentValue' error is returned when
         tVrrpPriEvtMcIPsecNoFwdType is set to 'delta' when
         tVrrpPriEvtMcIPsecNoFwdPriority is set to non-zero value."
    DEFVAL { 0 }
    ::= { tVrrpPriEvtMcIPsecNoFwdEntry 3 } 

tVrrpPriEvtMcIPsecNoFwdType  OBJECT-TYPE
    SYNTAX       TmnxEventType
    MAX-ACCESS   read-create
    STATUS       current
    DESCRIPTION 
        "The value of tVrrpPriEvtMcIPsecNoFwdType specifies the type
         of this event.
         
         An 'inconsistentValue' error is returned when
         tVrrpPriEvtMcIPsecNoFwdType is set to 'delta' when
         tVrrpPriEvtMcIPsecNoFwdPriority is set to non-zero value."
    DEFVAL { delta }
    ::= { tVrrpPriEvtMcIPsecNoFwdEntry 4 } 

tVrrpPriEvtMcIPsecNoFwdHoldSet  OBJECT-TYPE
    SYNTAX       TmnxEventHoldSet
    UNITS        "seconds"
    MAX-ACCESS   read-create
    STATUS       current
    DESCRIPTION 
        "The value of tVrrpPriEvtMcIPsecNoFwdHoldSet specifies 
         the configured Hold Set time associated with the event."
    DEFVAL { 0 }
    ::= { tVrrpPriEvtMcIPsecNoFwdEntry 5 } 

tVrrpPriEvtMcIPsecNoFwdOperState  OBJECT-TYPE
    SYNTAX       TmnxMcIPsecNoFwdEventOperState
    MAX-ACCESS   read-only
    STATUS       current
    DESCRIPTION 
        "The value of tVrrpPriEvtMcIPsecNoFwdOperState indicates
         the current operational state of the event."
    ::= { tVrrpPriEvtMcIPsecNoFwdEntry 6 } 

tVrrpPriEvtMcIPsecNoFwdHoldSetR  OBJECT-TYPE
    SYNTAX       TmnxEventHoldSet
    UNITS        "seconds"
    MAX-ACCESS   read-only
    STATUS       current
    DESCRIPTION 
        "The The value of tVrrpPriEvtMcIPsecNoFwdHoldSetR indicates the
         current value of the hold-set timer i.e. the  amount of time
         remaining before the event will transition into the cleared state."
    ::= { tVrrpPriEvtMcIPsecNoFwdEntry 7 } 

tVrrpPriEvtMcIPsecNoFwdPrevState  OBJECT-TYPE
    SYNTAX       TmnxMcIPsecNoFwdEventOperState 
    MAX-ACCESS   read-only
    STATUS       current
    DESCRIPTION 
        "The value of tVrrpPriEvtMcIPsecNoFwdPrevState indicates
         the previous operational state of the event."
    ::= { tVrrpPriEvtMcIPsecNoFwdEntry 8 } 

tVrrpPriEvtMcIPsecNoFwdTransTm  OBJECT-TYPE
    SYNTAX       TimeStamp
    MAX-ACCESS   read-only
    STATUS       current
    DESCRIPTION 
        "The value of tVrrpPriEvtMcIPsecNoFwdTransTm indicates the sysUpTime
         when the operational state of the event last changed."
    ::= { tVrrpPriEvtMcIPsecNoFwdEntry 9 } 

tVrrpPriEvtMcIPsecNoFwdSetCntr  OBJECT-TYPE
    SYNTAX       Counter32
    MAX-ACCESS   read-only
    STATUS       current
    DESCRIPTION 
        "The value of tVrrpPriEvtMcIPsecNoFwdSetCntr indicates
         the number of times the event has transitioned to one of the 
         'set' states."
    ::= { tVrrpPriEvtMcIPsecNoFwdEntry 10 } 

tVrrpPriEvtMcIPsecNoFwdInUse  OBJECT-TYPE
    SYNTAX       TruthValue
    MAX-ACCESS   read-only
    STATUS       current
    DESCRIPTION 
        "If value of tVrrpPriEvtMcIPsecNoFwdInUse is 'true', then 
         the event is currently affecting the in-use priority of some 
         virtual router instance."
    ::= { tVrrpPriEvtMcIPsecNoFwdEntry 11 } 

tVrrpPriEvtMcIPsecNoFwdHoldClr  OBJECT-TYPE
    SYNTAX       TmnxEventHoldClear
    UNITS        "seconds"
    MAX-ACCESS   read-create
    STATUS       current
    DESCRIPTION 
        "The value of tVrrpPriEvtMcIPsecNoFwdHoldClr specifies 
         the configured Hold Clear time associated with the event."
    DEFVAL { 0 }
    ::= { tVrrpPriEvtMcIPsecNoFwdEntry 12 } 

tVrrpPriEvtMcIPsecNoFwdHoldClrR  OBJECT-TYPE
    SYNTAX       TmnxEventHoldClear
    UNITS        "seconds"
    MAX-ACCESS   read-only
    STATUS       current
    DESCRIPTION 
        "The value of tVrrpPriEvtMcIPsecNoFwdHoldClrR indicates the current
         value of the hold-clear timer i.e. the amount of time remaining before
         the cleared event will have an effect on the virtual router instance."
    ::= { tVrrpPriEvtMcIPsecNoFwdEntry 13 } 

-- ***************************************************************************
-- The Nokia SROS series VRRP Number of LAG Weight Down Table
-- ***************************************************************************

tmnxVrrpLagWtDownEventTblLastChg OBJECT-TYPE
    SYNTAX      TimeStamp
    MAX-ACCESS  read-only
    STATUS      current
    DESCRIPTION
        "The tmnxVrrpLagWtDownEventTblLastChg indicates timestamp of the last
         change to the tmnxVrrpLagWtDownEventTable either from adding a row or
         removing a row."
    ::= { tmnxVrrpPolicyObjects 15 }

tmnxVrrpLagWtDownEventTable OBJECT-TYPE
    SYNTAX       SEQUENCE OF TmnxVrrpLagWtDownEventEntry
    MAX-ACCESS   not-accessible
    STATUS       current
    DESCRIPTION  
        "The tmnxVrrpLagWtDownEventTable contains a list of 
         events corresponding to the number of LAG ports that are 
         weighted down within a specific LAG."
    ::= { tmnxVrrpPolicyObjects 16 }

tmnxVrrpLagWtDownEventEntry OBJECT-TYPE
    SYNTAX       TmnxVrrpLagWtDownEventEntry
    MAX-ACCESS   not-accessible
    STATUS       current
    DESCRIPTION 
        "Each tmnxVrrpLagWtDownEventEntry is associated with an entry
         in the tmnxVrrpLagPortDownEventTable. It is used to assign  
         a priority value to the LAG Weight Down Priority Event
         depending on the number of LAG ports that are in the 
         operationally down state.  
         
         Entries can be created and deleted via SNMP SET operations 
         using tmnxVrrpLagWtDownEventRowStatus. When a 
         tmnxVrrpLagPortDownEventEntry is deleted all 
         tmnxVrrpLagWtDownEventTable entries associated with it are 
         also deleted."
    INDEX { tmnxVrrpPolicyId, 
            tmnxVrrpLagPortDownEventLagId,
            tmnxVrrpLagWtDown }
    ::= { tmnxVrrpLagWtDownEventTable 1 }

TmnxVrrpLagWtDownEventEntry ::= 
    SEQUENCE {
        tmnxVrrpLagWtDown                   Unsigned32,
        tmnxVrrpLagWtDownEventRowStatus     RowStatus,
        tmnxVrrpLagWtDownEventPriority      TmnxVrrpPriority,
        tmnxVrrpLagWtDownEventType          TmnxEventType
    }

tmnxVrrpLagWtDown  OBJECT-TYPE
    SYNTAX       Unsigned32
    MAX-ACCESS   not-accessible
    STATUS       current
    DESCRIPTION 
        "The index value tmnxVrrpLagWtDown corresponds to the 
         number of LAG ports that are weighted down for a 
         specific LAG. This value sets a threshold for a LAG Weight
         Down Event."
    ::= { tmnxVrrpLagWtDownEventEntry 1 } 

tmnxVrrpLagWtDownEventRowStatus  OBJECT-TYPE
    SYNTAX       RowStatus
    MAX-ACCESS   read-create
    STATUS       current
    DESCRIPTION 
        "tmnxVrrpLagWtDownEventRowStatus is used for the creation or 
         deletion of entries in the tmnxVrrpLagWtDownEventTable."
    ::= { tmnxVrrpLagWtDownEventEntry 2 } 

tmnxVrrpLagWtDownEventPriority  OBJECT-TYPE
    SYNTAX       TmnxVrrpPriority
    MAX-ACCESS   read-create
    STATUS       current
    DESCRIPTION 
        "The value of tmnxVrrpLagWtDownEventPriority specifies 
         the priority level associated with this event. When the number 
         of LAG ports that are weighted down exceeds the threshold
         defined by tmnxVrrpLagWtDown, this priority value will either
         be subtracted from the in-use priority (if the event is a 'delta' 
         event) or the in-use priority will be explicitly overridden by 
         this priority value (if the event is an 'explicit' event)."
    DEFVAL { 0 }
    ::= { tmnxVrrpLagWtDownEventEntry 3 } 

tmnxVrrpLagWtDownEventType  OBJECT-TYPE
    SYNTAX       TmnxEventType
    MAX-ACCESS   read-create
    STATUS       current
    DESCRIPTION 
        "The value of tmnxVrrpLagWtDownEventType specifies whether 
         this event is a 'delta' or an 'explicit' event. When the number 
         of LAG ports that are weighted down exceeds the threshold 
         defined by tmnxVrrpLagWtDown, the value of 
         tmnxVrrpLagWtDownEventPriority will be subtracted from the 
         in-use priority in case of a 'delta' event or the in-use priority 
         will be explicitly overridden by the value of 
         tmnxVrrpLagWtDownEventPriority in case of an 'explicit' 
         event."
    DEFVAL { delta }
    ::= { tmnxVrrpLagWtDownEventEntry 4 } 

-- ***************************************************************************
-- Notification Information
-- ***************************************************************************
--
-- Trap control objects
--

tmnxVrrpNotifBfdIntfSvcId OBJECT-TYPE
    SYNTAX       TmnxServId
    MAX-ACCESS   accessible-for-notify
    STATUS       current
    DESCRIPTION
        "The value of tmnxVrrpNotifBfdIntfSvcId specifies the service
         ID of the interface running BFD in the notification."
    ::= { tmnxVrrpNotificationObjects 1 }

tmnxVrrpNotifBfdIntfIfName OBJECT-TYPE
    SYNTAX       TNamedItem
    MAX-ACCESS   accessible-for-notify
    STATUS       current
    DESCRIPTION         
        "The value of tmnxVrrpNotifBfdIntfIfName specifies the name of the
         interface running BFD in the notification."
    ::= { tmnxVrrpNotificationObjects 2 }

tmnxVrrpNotifBfdIntfDestIpType OBJECT-TYPE
    SYNTAX       InetAddressType
    MAX-ACCESS   accessible-for-notify
    STATUS       current
    DESCRIPTION
        "The value of tmnxVrrpNotifBfdIntfDestIpType specifies the address type
         of tmnxVrrpNotifBfdIntfDestIp object."
    ::= { tmnxVrrpNotificationObjects 3 }

tmnxVrrpNotifBfdIntfDestIp OBJECT-TYPE
    SYNTAX       InetAddress (SIZE (0|4|16|20))
    MAX-ACCESS   accessible-for-notify
    STATUS       current
    DESCRIPTION
        "The value of tmnxVrrpNotifBfdIntfDestIp specifies the destination
         IP address on the interface running BFD in the notification."
    ::= { tmnxVrrpNotificationObjects 4 }

tmnxVrrpNotifBfdIntfSessState OBJECT-TYPE
    SYNTAX      TmnxVrrpAssoBfdIntfSessOperState
    MAX-ACCESS  accessible-for-notify
    STATUS      current
    DESCRIPTION
        "The value of tmnxVrrpNotifBfdIntfSessState indicates the operational
         state of BFD session on the interface in the notification."
    ::= { tmnxVrrpNotificationObjects 5 }

--
-- Notification Definitions
--

tmnxVrrpIPListMismatch  NOTIFICATION-TYPE
    OBJECTS      { 
                   tmnxVrrpRouterMasterIPListMatch
                 }
    STATUS       current
    DESCRIPTION
         "The tmnxVrrpIPListMismatch trap is generated when the IP address
          list received in the advertisement messages received from the
          current master did not match the configured IP address list.
          
          This is an edge triggered notification. A second trap will not
          be generated for a packet from the same master until this event 
          has been cleared."
    ::= { tmnxVrrpNotifications 1 }

tmnxVrrpIPListMismatchClear  NOTIFICATION-TYPE
    OBJECTS      { 
                   tmnxVrrpRouterMasterIPListMatch
                 }
    STATUS       current
    DESCRIPTION
         "The tmnxVrrpIPListMismatchClear trap is generated when a previously 
          occurring tmnxVrrpIPListMismatch trap has been cleared because
          the IP address list in the advertisement messages received from
          the current master now matches the configured IP address list.
          
          This is an edge triggered notification. A second trap will not
          be generated for a packet from the same master until this event 
          has been set again."
    ::= { tmnxVrrpNotifications 2 }

tmnxVrrpMultipleOwners  NOTIFICATION-TYPE
    OBJECTS      { 
                   tmnxVrrpRouterMasterLastSeen
                 }
    STATUS       current
    DESCRIPTION
         "The tmnxVrrpMultipleOwners trap is generated when a VRRP virtual
          router instance that has been configured as an owner notices that
          that another VRRP instance is also advertising itself as an owner."
    ::= { tmnxVrrpNotifications 3 }

tmnxVrrpBecameBackup  NOTIFICATION-TYPE
    OBJECTS      { 
                   vrrpOperMasterIpAddr
                 }
    STATUS       current
    DESCRIPTION
         "The tmnxVrrpBecameBackup trap is generated when the sending 
          agent has transitioned to 'Backup' state."
    ::= { tmnxVrrpNotifications 4 }

tmnxVrrpBfdIntfSessStateChgd  NOTIFICATION-TYPE
    OBJECTS      { 
                   tmnxVrrpNotifBfdIntfSvcId,
                   tmnxVrrpNotifBfdIntfIfName,
                   tmnxVrrpNotifBfdIntfDestIpType,
                   tmnxVrrpNotifBfdIntfDestIp,
                   tmnxVrrpNotifBfdIntfSessState
                 }
    STATUS       current
    DESCRIPTION
         "The notification tmnxVrrpBfdIntfSessStateChgd is generated when the
          operational state of BFD session of the VRRP instance changes."
    ::= { tmnxVrrpNotifications 5 }

tVrrpBecameBackup  NOTIFICATION-TYPE
    OBJECTS      { 
                   vrrpOperationsMasterIpAddr
                 }
    STATUS       current
    DESCRIPTION
         "The tmnxVrrpBecameBackup trap is generated when the sending 
          agent has transitioned to 'Backup' state."
    ::= { tmnxVrrpNotifications 6 }

tVrrpTrapNewMaster NOTIFICATION-TYPE  
    OBJECTS      { vrrpOperationsMasterIpAddr,  
                   vrrpNewMasterReason  
                 }  
    STATUS       current  
    DESCRIPTION  
        "The tVrrpTrapNewMaster trap indicates that the sending agent  
        has transitioned to 'Master' state."  
    ::= { tmnxVrrpNotifications 7 }  

tVrrpIPListMismatch  NOTIFICATION-TYPE
    OBJECTS      { 
                   tVrrpRtrMasterIPListMatch
                 }
    STATUS       current
    DESCRIPTION
         "The tVrrpIPListMismatch trap is generated when the IPv6 address
          list received in the advertisement messages received from the
          current master did not match the configured IPv6 address list.
          
          This is an edge triggered notification. A second trap will not
          be generated for a packet from the same master until this event 
          has been cleared."
    ::= { tmnxVrrpNotifications 8 }

tVrrpIPListMismatchClear  NOTIFICATION-TYPE
    OBJECTS      { 
                   tVrrpRtrMasterIPListMatch
                 }
    STATUS       current
    DESCRIPTION
         "The tVrrpIPListMismatchClear trap is generated when a previously 
          occurring tVrrpIPListMismatch trap has been cleared because
          the IPv6 address list in the advertisement messages received from
          the current master now matches the configured IPv6 address list.
          
          This is an edge triggered notification. A second trap will not
          be generated for a packet from the same master until this event 
          has been set again."
    ::= { tmnxVrrpNotifications 9 }

tVrrpMultipleOwners  NOTIFICATION-TYPE
    OBJECTS      { 
                   tVrrpRtrMasterLastSeen
                 }
    STATUS       current
    DESCRIPTION
         "The tVrrpMultipleOwners trap is generated when a VRRP virtual
          router instance that has been configured as an owner notices that
          that another VRRP instance is also advertising itself as an owner."
    ::= { tmnxVrrpNotifications 10 }

tVrrpRouterAdvNotActivated  NOTIFICATION-TYPE
    OBJECTS      { 
                   tVrrpOpState
                 }
    STATUS       current
    DESCRIPTION
         "The tVrrpRouterAdvNotActivated trap is generated when the parent
          interface of the IPv6 virtual router instance is either not set
          to send out Router Advertisement or the Router Advertisement is
          not configured to use the virtual MAC address. The virtual router
          instance is not allowed to become operationally 'up'."
    ::= { tmnxVrrpNotifications 11 }

tVrrpRouterAdvNotActivatedClear  NOTIFICATION-TYPE
    OBJECTS      { 
                   tVrrpOpState
                 }
    STATUS       current
    DESCRIPTION
         "The tVrrpRouterAdvNotActivatedClear trap is generated when a
          previously occurring tVrrpRouterAdvNotActivated trap has been cleared.
          
          The tVrrpRouterAdvNotActivatedClear trap is generated when either:

          - the parent interface of the IPv6 virtual router instance is set to
            send out Router Advertisement, and Router Advertisement is
            configured to user virtual MAC, or
            
          - the virtual router instance is no longer attempting to become active
            (e.g. the virtual-router is administratively shutdown)."
    ::= { tmnxVrrpNotifications 12 }

tVrrpOperDownInvalidMac  NOTIFICATION-TYPE
    OBJECTS      {
                   tVrrpOpState
                 }
    STATUS       current
    DESCRIPTION
         "[CAUSE] tVrrpOperDownInvalidMac is generated when the operational
          virtual MAC of an IPv6 VRRP instance conflicts with the MAC of the
          parent interface, or with the operational virtual MAC addresses of
          other VRRP instances under the same interface.

          [EFFECT] The VRRP virtual router instance is not allowed to become
          operationally 'up'.

          [RECOVERY] There is no recovery required for this notification."
    ::= { tmnxVrrpNotifications 13 }

tVrrpOperDownInvalidMacClear  NOTIFICATION-TYPE
    OBJECTS      {
                   tVrrpOpState
                 }
    STATUS       current
    DESCRIPTION
         "[CAUSE] The tVrrpOperDownInvalidMacClear is generated when a
          previously occurring tVrrpOperDownInvalidMac notification has been
          cleared. Operational virtual MAC of an IPv6 VRRP instance does not
          have any conflict with the MAC of the parent interface or with the
          operational virtual MAC addresses of other VRRP instances under the
          same interface.

          [EFFECT] The VRRP virtual router instance is allowed to become
          operationally 'up'.

          [RECOVERY] There is no recovery required for this notification."
    ::= { tmnxVrrpNotifications 14 }

tmnxVrrpOperDownInvalidMac  NOTIFICATION-TYPE
    OBJECTS      {
                   tmnxVrrpOperState
                 }
    STATUS       current
    DESCRIPTION
         "[CAUSE] tmnxVrrpOperDownInvalidMac is generated when the operational
          virtual MAC of an IPv4 VRRP instance conflicts with the MAC of the
          parent interface, or with the operational virtual MAC addresses of
          other VRRP instances under the same interface.

          [EFFECT] The VRRP virtual router instance is not allowed to become
          operationally 'up'.

          [RECOVERY] There is no recovery required for this notification."
    ::= { tmnxVrrpNotifications 15 }

tmnxVrrpOperDownInvalidMacClear  NOTIFICATION-TYPE
    OBJECTS      {
                   tmnxVrrpOperState
                 }
    STATUS       current
    DESCRIPTION
         "[CAUSE] The tmnxVrrpOperDownInvalidMacClear is generated when a
          previously occurring tmnxVrrpOperDownInvalidMac notification has been
          cleared. Operational virtual MAC of an IPv4 VRRP instance does not
          have any conflict with the MAC of the parent interface or with the
          operational virtual MAC addresses of other VRRP instances under the
          same interface.

          [EFFECT] The VRRP virtual router instance is allowed to become
          operationally 'up'.

          [RECOVERY] There is no recovery required for this notification."
    ::= { tmnxVrrpNotifications 16 }

--
--
-- Conformance Information
--
tmnxVrrpCompliances OBJECT IDENTIFIER ::= { tmnxVrrpConformance 1 }
tmnxVrrpGroups      OBJECT IDENTIFIER ::= { tmnxVrrpConformance 2 }

-- compliance statements

-- tmnxVrrpCompliance  MODULE-COMPLIANCE
--    ::= { tmnxVrrpCompliances 1 }

-- tmnxVrrpV3v0Compliance  MODULE-COMPLIANCE
--    ::= { tmnxVrrpCompliances 2 }

tmnxVrrpV4v0Compliance  MODULE-COMPLIANCE
    STATUS  obsolete
    DESCRIPTION
            "The compliance statement for management of extended VRRP
             features on Nokia SROS series systems."
    MODULE  -- this module
        MANDATORY-GROUPS { 
            tmnxVrrpOperV4v0Group,
            tmnxVrrpStatsGroup,
            tmnxVrrpRouteMasterGroup,
            tmnxVrrpPolicyGroup,
            tmnxVrrpPriorityEventsGroup,
            tmnxVrrpNotificationGroup
        }
    ::= { tmnxVrrpCompliances 3 }

tmnxVrrpV5v0Compliance  MODULE-COMPLIANCE
    STATUS  obsolete
    DESCRIPTION
            "The compliance statement for management of extended VRRP
             features on Nokia SROS series systems."
    MODULE  -- this module
        MANDATORY-GROUPS { 
            tmnxVrrpOperV5v0Group,
            tmnxVrrpStatsGroup,
            tmnxVrrpRouteMasterGroup,
            tmnxVrrpPolicyV5v0Group,
            tmnxVrrpPriorityEventsGroup,
            tmnxVrrpNotificationGroup
        }
    ::= { tmnxVrrpCompliances 4 }

tmnxVrrpV6v1Compliance  MODULE-COMPLIANCE
    STATUS  obsolete
    DESCRIPTION
            "The compliance statement for management of extended VRRP
             features on Nokia SROS series systems."
    MODULE  -- this module
        MANDATORY-GROUPS { 
            tmnxVrrpOperV6v1Group,
            tmnxVrrpStatsGroup,
            tmnxVrrpRouteMasterGroup,
            tmnxVrrpBfdGroup,
            tmnxVrrpPolicyV5v0Group,
            tmnxVrrpPriorityEventsGroup,
            tmnxVrrpNotificationV6v1Group
        }
    ::= { tmnxVrrpCompliances 5 }

tmnxVrrp77x0V7v0Compliance  MODULE-COMPLIANCE
    STATUS  obsolete
    DESCRIPTION
            "The compliance statement for management of extended VRRP
             features on Nokia 7750 and 7710 SR series systems."
    MODULE  -- this module
        MANDATORY-GROUPS { 
            tmnxVrrpOperV6v1Group,
            tmnxVrrpStatsGroup,
            tmnxVrrpRouteMasterGroup,
            tmnxVrrpBfdGroup,
            tmnxVrrpPolicyV5v0Group,
            tmnxVrrpPriorityEventsGroup,
            tmnxVrrpNotificationV6v1Group,
            tVrrpNotificationV7v0Group,
            tVrrpHostUnreachableV7v0Group,
            tVrrpOpV7v0Group,
            tVrrpRouteUnknownV7v0Group,
            tVrrpMasterV7v0Group,
            tVrrpStatV7v0Group,
            tVrrpRouterAdverV7v0Group
        }
    ::= { tmnxVrrpCompliances 6 }

tmnxVrrp7450V7v0Compliance  MODULE-COMPLIANCE
    STATUS  obsolete
    DESCRIPTION
            "The compliance statement for management of extended VRRP
             features on Nokia 7450 SR series systems."
    MODULE  -- this module
        MANDATORY-GROUPS { 
            tmnxVrrpOperV6v1Group,
            tmnxVrrpStatsGroup,
            tmnxVrrpRouteMasterGroup,
            tmnxVrrpBfdGroup,
            tmnxVrrpPolicyV5v0Group,
            tmnxVrrpPriorityEventsGroup,
            tmnxVrrpNotificationV6v1Group
            -- tVrrpNotificationV7v0Group,
            -- tVrrpHostUnreachableV7v0Group,
            -- tVrrpOpV7v0Group,
            -- tVrrpRouteUnknownV7v0Group,
            -- tVrrpMasterV7v0Group,
            -- tVrrpStatV7v0Group
            -- tVrrpRouterAdverV7v0Group
        }
    ::= { tmnxVrrpCompliances 7 }

tmnxVrrp77x0V9v0Compliance  MODULE-COMPLIANCE
    STATUS  obsolete
    DESCRIPTION
            "The compliance statement for management of extended VRRP
             features on Nokia 7750 and 7710 SR series systems."
    MODULE  -- this module
        MANDATORY-GROUPS { 
            tmnxVrrpOperV6v1Group,
            tmnxVrrpStatsGroup,
            tmnxVrrpRouteMasterGroup,
            tmnxVrrpPolicyV5v0Group,
            tmnxVrrpPriorityEventsGroup,
            tmnxVrrpNotificationV6v1Group,
            tVrrpNotificationV7v0Group,
            tVrrpHostUnreachableV7v0Group,
            tVrrpOpV7v0Group,
            tVrrpRouteUnknownV7v0Group,
            tVrrpMasterV7v0Group,
            tVrrpStatV7v0Group,
            tVrrpRouterAdverV7v0Group,
            tVrrpBfdV9v0Group
        }
    ::= { tmnxVrrpCompliances 8 }

tmnxVrrp7450V9v0Compliance  MODULE-COMPLIANCE
    STATUS  current
    DESCRIPTION
            "The compliance statement for management of extended VRRP
             features on Nokia 7450 SR series systems."
    MODULE  -- this module
        MANDATORY-GROUPS { 
            tmnxVrrpOperV6v1Group,
            tmnxVrrpStatsGroup,
            tmnxVrrpRouteMasterGroup,
            tVrrpBfdV9v0Group,
            tmnxVrrpPolicyV5v0Group,
            tmnxVrrpPriorityEventsGroup,
            tmnxVrrpNotificationV6v1Group
            -- tVrrpNotificationV7v0Group,
            -- tVrrpHostUnreachableV7v0Group,
            -- tVrrpOpV7v0Group,
            -- tVrrpRouteUnknownV7v0Group,
            -- tVrrpMasterV7v0Group,
            -- tVrrpStatV7v0Group
            -- tVrrpRouterAdverV7v0Group
        }
    ::= { tmnxVrrpCompliances 9 }

tmnxVrrp77x0V10v0Compliance  MODULE-COMPLIANCE
    STATUS  obsolete
    DESCRIPTION
            "The compliance statement for management of extended VRRP
             features on Nokia 7750 and 7710 SR series systems."
    MODULE  -- this module
        MANDATORY-GROUPS { 
            tmnxVrrpOperV6v1Group,
            tmnxVrrpStatsGroup,
            tmnxVrrpRouteMasterGroup,
            tmnxVrrpPolicyV5v0Group,
            tmnxVrrpPriorityEventsGroup,
            tmnxVrrpNotificationV6v1Group,
            tVrrpNotificationV7v0Group,
            tVrrpHostUnreachableV7v0Group,
            tVrrpOpV7v0Group,
            tVrrpRouteUnknownV7v0Group,
            tVrrpMasterV7v0Group,
            tVrrpStatV7v0Group,
            tVrrpRouterAdverV7v0Group,
            tVrrpBfdV9v0Group,
            tVrrpHostUnreachGroup,
            tVrrpMcIPsecGroup
        }
    ::= { tmnxVrrpCompliances 10 }

tmnxVrrp77x0V12v0Compliance  MODULE-COMPLIANCE
    STATUS  obsolete
    DESCRIPTION
            "The compliance statement for management of extended VRRP
             features on Nokia 7750 and 7710 SR series systems."
    MODULE  -- this module
        MANDATORY-GROUPS { 
            tmnxVrrpOperV6v1Group,
            tmnxVrrpStatsGroup,
            tmnxVrrpRouteMasterGroup,
            tmnxVrrpPolicyV5v0Group,
            tmnxVrrpPriorityEventsGroup,
            tmnxVrrpNotificationV6v1Group,
            tVrrpNotificationV7v0Group,
            tVrrpHostUnreachableV7v0Group,
            tVrrpOpV7v0Group,
            tVrrpRouteUnknownV7v0Group,
            tVrrpMasterV7v0Group,
            tVrrpStatV7v0Group,
            tVrrpRouterAdverV7v0Group,
            tVrrpBfdV9v0Group,
            tVrrpHostUnreachGroup,
            tVrrpMcIPsecGroup,
            tmnxVrrpLagWtDnEvtGroup,
            tmnxVrrpOperV10v0Group,
            tVrrpNotificationV10v0Group
        }
    ::= { tmnxVrrpCompliances 11 }

tmnxVrrp77x0V13v0Compliance  MODULE-COMPLIANCE
    STATUS  current
    DESCRIPTION
            "The compliance statement for management of extended VRRP
             features on Nokia 7750 and 7710 SR series systems."
    MODULE  -- this module
        MANDATORY-GROUPS { 
            tmnxVrrpOperV6v1Group,
            tmnxVrrpStatsGroup,
            tmnxVrrpRouteMasterGroup,
            tmnxVrrpPolicyV5v0Group,
            tmnxVrrpPriorityEventsGroup,
            tmnxVrrpNotificationV6v1Group,
            tVrrpNotificationV7v0Group,
            tVrrpHostUnreachableV7v0Group,
            tVrrpOpV7v0Group,
            tVrrpRouteUnknownV7v0Group,
            tVrrpMasterV7v0Group,
            tVrrpStatV7v0Group,
            tVrrpRouterAdverV7v0Group,
            tVrrpBfdV9v0Group,
            tVrrpHostUnreachGroup,
            tVrrpMcIPsecGroup,
            tmnxVrrpLagWtDnEvtGroup,
            tmnxVrrpOperV10v0Group,
            tVrrpNotificationV10v0Group,
tmnxVrrpPolicyAdminGroup
        }
    ::= { tmnxVrrpCompliances 12 }

tmnxVrrp77x0V14v0Compliance  MODULE-COMPLIANCE
    STATUS  current
    DESCRIPTION
            "The compliance statement for management of extended VRRP
             features on Nokia 7750 and 7710 SR series systems."
    MODULE  -- this module
        MANDATORY-GROUPS { 
            tmnxVrrpOperV140v0Group
        }
    ::= { tmnxVrrpCompliances 13 }
tmnxVrrp77x0V15v0Compliance  MODULE-COMPLIANCE
    STATUS  current
    DESCRIPTION
            "The compliance statement for management of extended VRRP
             features on Nokia 7750 and 7710 SR series systems."
    MODULE  -- this module
        MANDATORY-GROUPS { 
            tmnxVrrpOperV150v0Group
        }
    ::= { tmnxVrrpCompliances 14 }
-- units of conformance

-- tmnxVrrpOperGroup     OBJECT-GROUP
--    ::= { tmnxVrrpGroups 1 }

tmnxVrrpStatsGroup     OBJECT-GROUP
    OBJECTS {   tmnxVrrpStatsAdvertiseSent,
                tmnxVrrpStatsPreemptEvents,
                tmnxVrrpStatsPreemptedEvents,
                tmnxVrrpStatsMasterChanges,
                tmnxVrrpStatsAdvertiseIntervalDiscards,
                tmnxVrrpStatsAddressListDiscards,
                tmnxVrrpStatsTotalDiscards
            }
    STATUS      current
    DESCRIPTION
        "The group of objects supporting management of extended VRRP 
         statistics on Nokia SROS series systems."
    ::= { tmnxVrrpGroups 2 }

tmnxVrrpRouteMasterGroup     OBJECT-GROUP
    OBJECTS {   tmnxVrrpRouterMasterLastSeen,
                tmnxVrrpRouterMasterMessageCount,
                tmnxVrrpRouterMasterAuthSequence,
                tmnxVrrpRouterMasterIPListMatch      
            }
    STATUS      current
    DESCRIPTION
        "The group of objects supporting management of extended VRRP 
         route masters on Nokia SROS series systems."
    ::= { tmnxVrrpGroups 3 }

tmnxVrrpPolicyGroup     OBJECT-GROUP
    OBJECTS {   tmnxVrrpPolicyRowStatus,
                tmnxVrrpPolicyDescription,
                tmnxVrrpPolicyDeltaInUseLimit,
                tmnxVrrpPolicyReferenceCount,
                tmnxVrrpPolicyCurrentExplicit,
                tmnxVrrpPolicyCurrentDeltaSum
            }
    STATUS      obsolete
    DESCRIPTION
        "The group of objects supporting management of extended VRRP 
         policies on Nokia SROS series systems."
    ::= { tmnxVrrpGroups 4 }

tmnxVrrpPriorityEventsGroup     OBJECT-GROUP
    OBJECTS {   tmnxVrrpPortDownEventRowStatus,
                tmnxVrrpPortDownEventPriority,
                tmnxVrrpPortDownEventType,
                tmnxVrrpPortDownEventHoldSet,
                tmnxVrrpPortDownEventOperState,
                tmnxVrrpPortDownEventHoldSetRemaining,
                tmnxVrrpPortDownEventPrevState,
                tmnxVrrpPortDownEventLastTransition,
                tmnxVrrpPortDownEventSetCounter,
                tmnxVrrpPortDownEventInUse,
                tmnxVrrpPortDownEventHoldClear,
                tmnxVrrpPortDownEventHoldClearRemaining,
                tmnxVrrpLagPortDownEventRowStatus,
                tmnxVrrpLagPortDownEventHoldSet,
                tmnxVrrpLagPortDownEventOperState,
                tmnxVrrpLagPortDownEventHoldSetRemaining,
                tmnxVrrpLagPortDownEventPrevState,
                tmnxVrrpLagPortDownEventLastTransition,
                tmnxVrrpLagPortDownEventSetCounter,
                tmnxVrrpLagPortDownEventInUse ,
                tmnxVrrpLagPortDownEventHoldClear,
                tmnxVrrpLagPortDownEventHoldClearRemaining,
                tmnxVrrpLagNumberDownEventRowStatus,
                tmnxVrrpLagNumberDownEventPriority,
                tmnxVrrpLagNumberDownEventType,
                tmnxVrrpHostUnreachableEventRowStatus,
                tmnxVrrpHostUnreachableEventPriority,
                tmnxVrrpHostUnreachableEventType,
                tmnxVrrpHostUnreachableEventHoldSet,
                tmnxVrrpHostUnreachableEventInterval,
                tmnxVrrpHostUnreachableEventTimeout,
                tmnxVrrpHostUnreachableEventDropCount,
                tmnxVrrpHostUnreachableEventOperState,
                tmnxVrrpHostUnreachableEventHoldSetRemaining,
                tmnxVrrpHostUnreachableEventPrevState,
                tmnxVrrpHostUnreachableEventLastTransition,
                tmnxVrrpHostUnreachableEventSetCounter,
                tmnxVrrpHostUnreachableEventInUse,
                tmnxVrrpHostUnreachableEventHoldClear,
                tmnxVrrpHostUnreachableEventHoldClearRemaining,
                tmnxVrrpRouteUnknownEventRowStatus,
                tmnxVrrpRouteUnknownEventPriority,
                tmnxVrrpRouteUnknownEventType,
                tmnxVrrpRouteUnknownEventHoldSet,
                tmnxVrrpRouteUnknownEventLessSpecific,
                tmnxVrrpRouteUnknownEventDefaultAllowed,
                tmnxVrrpRouteUnknownEventProtocol,
                tmnxVrrpRouteUnknownEventOperState,
                tmnxVrrpRouteUnknownEventHoldSetRemaining,
                tmnxVrrpRouteUnknownEventPrevState,
                tmnxVrrpRouteUnknownEventLastTransition,
                tmnxVrrpRouteUnknownEventSetCounter,
                tmnxVrrpRouteUnknownEventInUse,
                tmnxVrrpRouteUnknownEventHoldClear,
                tmnxVrrpRouteUnknownEventHoldClearRemaining,
                tmnxVrrpRouteUnknownEventNextHopRowStatus
            }
    STATUS      current
    DESCRIPTION
        "The group of objects supporting management of extended VRRP 
         priority events on Nokia SROS series systems."
    ::= { tmnxVrrpGroups 5 }

tmnxVrrpBfdGroup     OBJECT-GROUP
    OBJECTS {
        tmnxVrrpAssoBfdIntfTblLastChgd,
        tmnxVrrpAssoBfdIntfRowStatus,
        tmnxVrrpAssoBfdIntfLastChgd,
        tmnxVrrpAssoBfdIntfSrcIpType,
        tmnxVrrpAssoBfdIntfSrcIp,
        tmnxVrrpAssoBfdIntfSessOperState      
        }
    STATUS      obsolete
    DESCRIPTION
        "The group of objects supporting management of VRRP scaling feature
         on Nokia SROS series systems."
    ::= { tmnxVrrpGroups 6 }

--tmnxVrrpNotifyObjsGroup   OBJECT-GROUP
--    OBJECTS {   
--            }
--    STATUS        current
--    DESCRIPTION
--        "The group of objects supporting extended VRRP notifications 
--         on Nokia SROS series systems."
--    ::= { tmnxVrrpGroups 6 }

tmnxVrrpNotificationGroup NOTIFICATION-GROUP
    NOTIFICATIONS   {   tmnxVrrpIPListMismatch,
                        tmnxVrrpIPListMismatchClear,
                        tmnxVrrpMultipleOwners,
                        tmnxVrrpBecameBackup
                    }
    STATUS      obsolete
    DESCRIPTION
        "The group of notifications supporting the extended VRRP feature
         on Nokia SROS series systems."
    ::= { tmnxVrrpGroups 7 }

-- tmnxVrrpOperV3v0Group     OBJECT-GROUP
--    ::= { tmnxVrrpGroups 8 }

tmnxVrrpOperV4v0Group     OBJECT-GROUP
    OBJECTS {   tmnxVrrpOperState,
                tmnxVrrpOperVirtualMacAddr,
                tmnxVrrpOperMismatchDiscard,
                tmnxVrrpOperPingReply,
                tmnxVrrpOperTelnetReply,
                tmnxVrrpOperSshReply,
                tmnxVrrpOperPolicyId,
                tmnxVrrpOperInUsePriority,
                tmnxVrrpOperMasterSince,
                tmnxVrrpOperMasterPriority,
                tmnxVrrpOperOwner,
                tmnxVrrpOperMasterDownInterval,
                tmnxVrrpOperMasterDownTimer,
                tmnxVrrpOperAdvIntervalInherit,
                tmnxVrrpOperInUseAdvInterval,
                tmnxVrrpOperTracerouteReply,
                tmnxVrrpOperStandbyFwding
            }
    STATUS      obsolete
    DESCRIPTION
        "The group of objects supporting management of extended VRRP 
         operations on Nokia SROS series systems."
    ::= { tmnxVrrpGroups 9 }

tmnxVrrpPolicyV5v0Group     OBJECT-GROUP
    OBJECTS {   tmnxVrrpPolicyRowStatus,
                tmnxVrrpPolicyDescription,
                tmnxVrrpPolicyDeltaInUseLimit,
                tmnxVrrpPolicyReferenceCount,
                tmnxVrrpPolicyCurrentExplicit,
                tmnxVrrpPolicyCurrentDeltaSum,
                tmnxVrrpPolicySvcContext
            }
    STATUS      current
    DESCRIPTION
        "The group of objects supporting management of extended VRRP 
         policies on Nokia SROS series systems."
    ::= { tmnxVrrpGroups 10 }


tmnxVrrpOperV5v0Group     OBJECT-GROUP
    OBJECTS {   tmnxVrrpOperState,
                tmnxVrrpOperVirtualMacAddr,
                tmnxVrrpOperMismatchDiscard,
                tmnxVrrpOperPingReply,
                tmnxVrrpOperTelnetReply,
                tmnxVrrpOperSshReply,
                tmnxVrrpOperPolicyId,
                tmnxVrrpOperInUsePriority,
                tmnxVrrpOperMasterSince,
                tmnxVrrpOperMasterPriority,
                tmnxVrrpOperOwner,
                tmnxVrrpOperMasterDownInterval,
                tmnxVrrpOperMasterDownTimer,
                tmnxVrrpOperAdvIntervalInherit,
                tmnxVrrpOperInUseAdvInterval,
                tmnxVrrpOperTracerouteReply,
                tmnxVrrpOperStandbyFwding,
                tmnxVrrpOperAdvIntervalMilSec,
                tmnxVrrpOperInUseAdvIntlMilSec,
                tmnxVrrpOperInitDelay
            }
    STATUS      obsolete
    DESCRIPTION
        "The group of objects supporting management of extended VRRP 
         operations on Nokia SROS series systems."
    ::= { tmnxVrrpGroups 11 }

tmnxVrrpNotificationV6v1Group NOTIFICATION-GROUP
    NOTIFICATIONS   {   tmnxVrrpIPListMismatch,
                        tmnxVrrpIPListMismatchClear,
                        tmnxVrrpMultipleOwners,
                        tmnxVrrpBecameBackup,
                        tmnxVrrpBfdIntfSessStateChgd
                    }
    STATUS      current
    DESCRIPTION
        "The group of notifications supporting the extended VRRP feature
         on Nokia SROS series systems for 6.1 release."
    ::= { tmnxVrrpGroups 12 }

tmnxVrrpOperV6v1Group     OBJECT-GROUP
    OBJECTS {   tmnxVrrpOperState,
                tmnxVrrpOperVirtualMacAddr,
                tmnxVrrpOperMismatchDiscard,
                tmnxVrrpOperPingReply,
                tmnxVrrpOperTelnetReply,
                tmnxVrrpOperSshReply,
                tmnxVrrpOperPolicyId,
                tmnxVrrpOperInUsePriority,
                tmnxVrrpOperMasterSince,
                tmnxVrrpOperMasterPriority,
                tmnxVrrpOperOwner,
                tmnxVrrpOperMasterDownInterval,
                tmnxVrrpOperMasterDownTimer,
                tmnxVrrpOperAdvIntervalInherit,
                tmnxVrrpOperInUseAdvInterval,
                tmnxVrrpOperTracerouteReply,
                tmnxVrrpOperStandbyFwding,
                tmnxVrrpOperAdvIntervalMilSec,
                tmnxVrrpOperInUseAdvIntlMilSec,
                tmnxVrrpOperInitDelay,
                tmnxVrrpOperInitTimer
            }
    STATUS      current
    DESCRIPTION
        "The group of objects supporting management of extended VRRP 
         operations on Nokia SROS series systems."
    ::= { tmnxVrrpGroups 13 }

tmnxVrrpNotificationObjV6v1Group OBJECT-GROUP
    OBJECTS {
               tmnxVrrpNotifBfdIntfSvcId,
               tmnxVrrpNotifBfdIntfIfName,
               tmnxVrrpNotifBfdIntfDestIpType,
               tmnxVrrpNotifBfdIntfDestIp,
               tmnxVrrpNotifBfdIntfSessState
            }
    STATUS        current
    DESCRIPTION
        "The group of objects supporting management of notification objects
         on Nokia SROS 6.1 series systems."
    ::= { tmnxVrrpGroups 14 }

-- ----------------------
-- VRRPv3 IPv6 groups
-- ----------------------

tVrrpHostUnreachableV7v0Group     OBJECT-GROUP
    OBJECTS {
            tVrrpHstUnrchEvtDropCount,
            tVrrpHstUnrchEvtHoldClear,
            tVrrpHstUnrchEvtHldClrRemain,
            tVrrpHstUnrchEvtHoldSet,
            tVrrpHstUnrchEvtHoldSetRemaining,
            tVrrpHstUnrchEvtInUse,
            tVrrpHstUnrchEvtInterval,
            tVrrpHstUnrchEvtLastTransition,
            tVrrpHstUnrchEvtOperState,
            tVrrpHstUnrchEvtPrevState,
            tVrrpHstUnrchEvtPriority,
            tVrrpHstUnrchEvtRowStatus,
            tVrrpHstUnrchEvtSetCounter,
            tVrrpHstUnrchEvtTimeout,
            tVrrpHstUnrchEvtType,
            tVrrpHstUnrchEvtLastChgd,
            tVrrpHstUnrchEvtTblLastChgd
            }
    STATUS      current
    DESCRIPTION
        "The group of objects supporting management of extended VRRP 
         Host Unreachable Events on Nokia SROS series systems."
    ::= { tmnxVrrpGroups 15 }

tVrrpOpV7v0Group     OBJECT-GROUP
    OBJECTS {
            tVrrpOpAdvIntervalInherit,
            tVrrpOpInUseAdvInterval,
            tVrrpOpInUsePriority,
            tVrrpOpInitDelay,
            tVrrpOpInitTimer,
            tVrrpOpMasterDownInterval,
            tVrrpOpMasterDownTimer,
            tVrrpOpMasterPriority,
            tVrrpOpMasterSince,
            tVrrpOpOwner,
            tVrrpOpPingReply,
            tVrrpOpPolicyId,
            tVrrpOpStandbyFwding,
            tVrrpOpState,
            tVrrpOpTelnetReply,
            tVrrpOpTracerouteReply,
            tVrrpOpVirtualMacAddr,
            tVrrpOpOperDownReason,
            tVrrpOpLastChgd,
            tVrrpOpTblLastChgd
            }
    STATUS      current
    DESCRIPTION
        "The group of objects supporting management of extended VRRP 
         operations for IPv6 on Nokia SROS series systems."
    ::= { tmnxVrrpGroups 16 }

tVrrpRouteUnknownV7v0Group     OBJECT-GROUP
    OBJECTS {
            tVrrpRtUnknEvtDefaultAllowed,
            tVrrpRtUnknEvtHoldClear,
            tVrrpRtUnknEvtHoldClearRemaining,
            tVrrpRtUnknEvtHoldSet,
            tVrrpRtUnknEvtHoldSetRemaining,
            tVrrpRtUnknEvtInUse,
            tVrrpRtUnknEvtLastTransition,
            tVrrpRtUnknEvtLessSpecific,
            tVrrpRtUnknEvtNextHopRowStatus,
            tVrrpRtUnknEvtOperState,
            tVrrpRtUnknEvtPrevState,
            tVrrpRtUnknEvtPriority,
            tVrrpRtUnknEvtProtocol,
            tVrrpRtUnknEvtRowStatus,
            tVrrpRtUnknEvtSetCounter,
            tVrrpRtUnknEvtType,
            tVrrpRtUnknEvtLastChgd,
            tVrrpRtUnknEvtNextHopLastChgd,
            tVrrpRtUnknEvtNextHopTblLastChgd,
            tVrrpRtUnknEvtTblLastChgd 
            }
    STATUS      current
    DESCRIPTION
        "The group of objects supporting management of extended VRRP 
         Route Unknown events on Nokia SROS series systems."
    ::= { tmnxVrrpGroups 17 }

tVrrpMasterV7v0Group     OBJECT-GROUP
    OBJECTS {
            tVrrpRtrMasterAuthSequence,
            tVrrpRtrMasterIPListMatch,
            tVrrpRtrMasterLastSeen,
            tVrrpRtrMasterMessageCount
            }
    STATUS      current
    DESCRIPTION
        "The group of objects supporting management of extended VRRP 
         Master table for IPv6 on Nokia SROS series systems."
    ::= { tmnxVrrpGroups 18 }

tVrrpStatV7v0Group     OBJECT-GROUP
    OBJECTS {
            tVrrpStatAdvIntvlDiscards,
            tVrrpStatAdvertiseSent,
            tVrrpStatMasterChanges,
            tVrrpStatPreemptEvents,
            tVrrpStatPreemptedEvents,
            tVrrpStatTotalDiscards
            }
    STATUS      current
    DESCRIPTION
        "The group of objects supporting management of extended VRRP 
         statistics for IPv6 on Nokia SROS series systems."
    ::= { tmnxVrrpGroups 19 }

tVrrpRouterAdverV7v0Group     OBJECT-GROUP
    OBJECTS {
            tVrrpIpv6RouterAdvertUseVirtualMac
            }
    STATUS      current
    DESCRIPTION
        "The group of objects supporting management of extended Router
         Advertisement features for IPv6 on Nokia SROS series systems."
    ::= { tmnxVrrpGroups 20 }

-- ------------------------------------------
-- VRRP notifications
-- ------------------------------------------

tVrrpNotificationV7v0Group NOTIFICATION-GROUP
    NOTIFICATIONS   {
                        tVrrpBecameBackup,
                        tVrrpTrapNewMaster,
                        tVrrpIPListMismatch,
                        tVrrpIPListMismatchClear,
                        tVrrpMultipleOwners,
                        tVrrpRouterAdvNotActivated,
                        tVrrpRouterAdvNotActivatedClear
                    }
    STATUS      current
    DESCRIPTION
        "The group of notifications supporting the extended VRRP feature
         on Nokia SROS series systems for 7.0 release."
    ::= { tmnxVrrpGroups 21 }

tVrrpBfdV9v0Group     OBJECT-GROUP
    OBJECTS {
       tVrrpAssoBfdIntfLastChgd,  
       tVrrpAssoBfdIntfRowStatus,  
       tVrrpAssoBfdIntfSessOperState,  
       tVrrpAssoBfdIntfSrcIp,  
       tVrrpAssoBfdIntfSrcIpType,  
       tVrrpAssoBfdIntfTblLastChgd
    }
    STATUS      current
    DESCRIPTION
        "The group of objects supporting management of BFD on extended VRRP 
         for Nokia SROS series systems."
    ::= { tmnxVrrpGroups 22 }

tmnxVrrpObsoletedV9v0Group OBJECT-GROUP
    OBJECTS {
       tmnxVrrpAssoBfdIntfLastChgd,
       tmnxVrrpAssoBfdIntfRowStatus,
       tmnxVrrpAssoBfdIntfSessOperState,
       tmnxVrrpAssoBfdIntfSrcIp,
       tmnxVrrpAssoBfdIntfSrcIpType,
       tmnxVrrpAssoBfdIntfTblLastChgd
    }
    STATUS      current
    DESCRIPTION
        "The group of objects supporting VRRP feature objects obsoleted in
         release 9.0 of Nokia SROS series systems."
    ::= { tmnxVrrpGroups 23 }

tVrrpMcIPsecGroup     OBJECT-GROUP
    OBJECTS {
        tVrrpPriEvtMcIPsecNoFwdRowStatus,
        tVrrpPriEvtMcIPsecNoFwdPriority,
        tVrrpPriEvtMcIPsecNoFwdType,
        tVrrpPriEvtMcIPsecNoFwdHoldSet,
        tVrrpPriEvtMcIPsecNoFwdOperState,
        tVrrpPriEvtMcIPsecNoFwdHoldSetR,
        tVrrpPriEvtMcIPsecNoFwdPrevState,
        tVrrpPriEvtMcIPsecNoFwdTransTm,
        tVrrpPriEvtMcIPsecNoFwdSetCntr,
        tVrrpPriEvtMcIPsecNoFwdInUse,
        tVrrpPriEvtMcIPsecNoFwdHoldClr,
        tVrrpPriEvtMcIPsecNoFwdHoldClrR
    }
    STATUS      current
    DESCRIPTION
        "The group of objects supporting management of multi-chassis IPsec on
         extended VRRP for Nokia SROS series systems."
    ::= { tmnxVrrpGroups 24 }

tVrrpHostUnreachGroup OBJECT-GROUP
    OBJECTS {
        tmnxVrrpHostUnreachableEvtSize,
        tVrrpHstUnrchEvtSize 
    }
    STATUS      current
    DESCRIPTION
        "The group of additional objects supporting management of
         host-unreachable VRRP event for Nokia SROS series systems."
    ::= { tmnxVrrpGroups 25 }

tmnxVrrpLagWtDnEvtGroup OBJECT-GROUP
    OBJECTS {
        tmnxVrrpLagWtDownEventTblLastChg,
        tmnxVrrpLagWtDownEventRowStatus,
        tmnxVrrpLagWtDownEventPriority,
        tmnxVrrpLagWtDownEventType
    }
    STATUS      current
    DESCRIPTION
        "The group of objects supporting management of VRRP lag weight-down
         event for Nokia SROS series systems."
    ::= { tmnxVrrpGroups 26 }

tmnxVrrpOperV10v0Group     OBJECT-GROUP
    OBJECTS {
        tmnxVrrpOperDownReason
    }
    STATUS      current
    DESCRIPTION
        "The group of objects supporting management of extended VRRP 
         operations on Nokia SROS series systems."
    ::= { tmnxVrrpGroups 27 }

tVrrpNotificationV10v0Group NOTIFICATION-GROUP
    NOTIFICATIONS   {
                        tVrrpOperDownInvalidMac,
                        tVrrpOperDownInvalidMacClear,
                        tmnxVrrpOperDownInvalidMac,
                        tmnxVrrpOperDownInvalidMacClear
    }
    STATUS      current
    DESCRIPTION
        "The group of notifications supporting the extended VRRP feature
         on Nokia SROS series systems for 10.0 release."
    ::= { tmnxVrrpGroups 28 }

tmnxVrrpPolicyAdminGroup     OBJECT-GROUP
    OBJECTS {
        tmnxVrrpPolicyAdminState
    }
    STATUS      current
    DESCRIPTION
        "The group of objects supporting management of extended VRRP 
         policy adminstrative objects on Nokia SROS series systems."
    ::= { tmnxVrrpGroups 29 }

tmnxVrrpOperV140v0Group     OBJECT-GROUP
    OBJECTS {
        tmnxVrrpOperPassive,
        tmnxVrrpOperRowStatus,
        tVrrpOpRowStatus,
        tVrrpOpPassive
    }
    STATUS      current
    DESCRIPTION
        "The group of objects supporting management of extended VRRP 
         policy adminstrative objects on Nokia SROS series systems."
    ::= { tmnxVrrpGroups 30 }

tmnxVrrpOperV150v0Group      OBJECT-GROUP
    OBJECTS {
        tmnxVrrpOperGroupName,
        tVrrpOpOperGroupName
    }
    STATUS      current
    DESCRIPTION
        "The group of objects supporting management of operation groups in VRRP
        on Nokia SROs series systems."
    ::= { tmnxVrrpGroups 31 }
END
