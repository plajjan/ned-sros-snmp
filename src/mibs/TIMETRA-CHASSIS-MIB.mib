TIMETRA-CHASSIS-MIB DEFINITIONS ::= BEGIN

IMPORTS
    SnmpAdminString
                                                         FROM SNMP-FRAMEWORK-MIB
    MODULE-COMPLIANCE, NOTIFICATION-GROUP,
    OBJECT-GROUP
                                                         FROM SNMPv2-CONF
    Counter32, Counter64, Gauge32,
    Integer32, MODULE-IDENTITY,
    NOTIFICATION-TYPE, OBJECT-TYPE,
    Unsigned32
                                                         FROM SNMPv2-SMI
    DateAndTime, DisplayString, MacAddress,
    RowPointer, RowStatus,
    TEXTUAL-CONVENTION, TimeInterval,
    TimeStamp, TruthValue
                                                         FROM SNMPv2-TC
    timetraSRMIBModules, tmnxSRConfs,
    tmnxSRNotifyPrefix, tmnxSRObjs
                                                         FROM TIMETRA-GLOBAL-MIB
    THPolCIRRateOverride,
    THPolPIRRateOverride,
    THsmdaPIRMRateOverride,
    THsmdaWeightOverride, TIngPolicerId,
    TItemDescription, TLevel, TNamedItem,
    TNamedItemOrEmpty, TPerPacketOffsetOvr,
    TPlcrBurstSizeBytesOverride,
    TmnxActionType, TmnxAdminState,
    TmnxAdminStateOld, TmnxEnabledDisabled,
    TmnxIngPolicerStatMode,
    TmnxIngPolicerStatModeOverride,
    TmnxInternalSchedWeightMode,
    TmnxIpSecIsaOperFlags, TmnxOperState,
    TmnxPortID, TmnxUuid
                                                         FROM TIMETRA-TC-MIB
    ;

tmnxChassisMIBModule             MODULE-IDENTITY
    LAST-UPDATED "201601010000Z"
    ORGANIZATION "Nokia"
    CONTACT-INFO
        "Nokia SROS Support
         Web: http://www.nokia.com"
    DESCRIPTION
        "This document is the SNMP MIB module to manage and provision the
         hardware components of the Nokia 7x50 device.

         Copyright 2003-2017 Nokia.  All rights reserved.
         Reproduction of this document is authorized on the condition that
         the foregoing copyright notice is included.

         This SNMP MIB module (Specification) embodies Nokia's
         proprietary intellectual property.  Nokia retains
         all title and ownership in the Specification, including any
         revisions.

         Nokia grants all interested parties a non-exclusive license to use and
         distribute an unmodified copy of this Specification in connection with
         management of Nokia products, and without fee, provided this copyright
         notice and license appear on all copies.

         This Specification is supplied 'as is', and Nokia makes no warranty,
         either express or implied, as to the use, operation, condition, or
         performance of the Specification."

    REVISION    "201601010000Z"
    DESCRIPTION
        "Rev 14.0               01 Jan 2016 00:00
         14.0 release of the TIMETRA-CHASSIS-MIB."

    REVISION    "201501010000Z"
    DESCRIPTION
        "Rev 13.0               01 Jan 2015 00:00
         13.0 release of the TIMETRA-CHASSIS-MIB."

    REVISION    "201401010000Z"
    DESCRIPTION
        "Rev 12.0               01 Jan 2014 00:00
         12.0 release of the TIMETRA-CHASSIS-MIB."

    REVISION    "201102010000Z"
    DESCRIPTION
        "Rev 9.0                01 Feb 2011 00:00
         9.0 release of the TIMETRA-CHASSIS-MIB."

    REVISION    "200902280000Z"
    DESCRIPTION
        "Rev 7.0                28 Feb 2009 00:00
         7.0 release of the TIMETRA-CHASSIS-MIB."

    REVISION    "200807010000Z"
    DESCRIPTION
        "Rev 6.1                01 Jul 2008 00:00
         6.1 release of the TIMETRA-CHASSIS-MIB."

    REVISION    "200801010000Z"
    DESCRIPTION
        "Rev 6.0                01 Jan 2008 00:00
         6.0 release of the TIMETRA-CHASSIS-MIB."

    REVISION    "200701010000Z"
    DESCRIPTION
        "Rev 5.0                01 Jan 2007 00:00
         5.0 release of the TIMETRA-CHASSIS-MIB."

    REVISION    "200603160000Z"
    DESCRIPTION
        "Rev 4.0                16 Mar 2006 00:00
         4.0 release of the TIMETRA-CHASSIS-MIB."

    REVISION    "200508310000Z"
    DESCRIPTION
        "Rev 3.0                31 Aug 2005 00:00
         3.0 release of the TIMETRA-CHASSIS-MIB."

    REVISION    "200501240000Z"
    DESCRIPTION
        "Rev 2.1                24 Jan 2005 00:00
         2.1 release of the TIMETRA-CHASSIS-MIB."

    REVISION    "200401150000Z"
    DESCRIPTION
        "Rev 2.0                15 Jan 2004 00:00
         2.0 release of the TIMETRA-CHASSIS-MIB."

    REVISION    "200308150000Z"
    DESCRIPTION
        "Rev 1.2                15 Aug 2003 00:00
         1.2 release of the TIMETRA-CHASSIS-MIB."

    REVISION    "200301200000Z"
    DESCRIPTION
        "Rev 1.0                20 Jan 2003 00:00
         Release 1.0 of the TIMETRA-HW-MIB."

    REVISION    "200008140000Z"
    DESCRIPTION
        "Rev 0.1                14 Aug 2000 00:00
         Initial version of the TIMETRA-HW-MIB."

    ::= { timetraSRMIBModules 2 }

TmnxAlarmState                   ::= TEXTUAL-CONVENTION
    STATUS      current
    DESCRIPTION
        "The TmnxAlarmState is an enumerated integer whose value indicates the
         current alarm state of a physical or logical component in the Nokia
         SROS series system."
    SYNTAX      INTEGER {
        unknown      (0),
        alarmActive  (1),
        alarmCleared (2)
    }

TmnxChassisIndex                 ::= TEXTUAL-CONVENTION
    STATUS      current
    DESCRIPTION
        "The TmnxChassisIndex is a unique index that identifies a chassis
         within an Nokia SROS system.  Note that initial releases will
         support only one chassis in a system."
    SYNTAX      Integer32 (1..32)

TmnxChassisIndexOrZero           ::= TEXTUAL-CONVENTION
    STATUS      current
    DESCRIPTION
        "The TmnxChassisIndexOrZero can be either a nonzero TmnxChassisIndex,
         or the value zero."
    SYNTAX      Integer32 (0..32)

TmnxPhysChassisIndex             ::= TEXTUAL-CONVENTION
    STATUS      current
    DESCRIPTION
        "The TmnxPhysChassisIndex is a unique index that identifies a physical
         chassis within Nokia SROS system."
    SYNTAX      Integer32 (1..100)

TmnxPhysChassisIndexOrZero       ::= TEXTUAL-CONVENTION
    STATUS      current
    DESCRIPTION
        "The TmnxPhysChassisIndexOrZero can be either a nonzero
         TmnxPhysChassisIndex, or the value zero."
    SYNTAX      Integer32 (0..100)

TmnxHwIndex                      ::= TEXTUAL-CONVENTION
    STATUS      current
    DESCRIPTION
        "The TmnxHwIndex is a unique integer index that identifies an Nokia
         SROS series manufactured hardware component, such as an IOM, CPM,
         Fabric or MDA card."
    SYNTAX      Integer32 (1..2147483647)

TmnxHwIndexOrZero                ::= TEXTUAL-CONVENTION
    STATUS      current
    DESCRIPTION
        "The TmnxHwIndexOrZero is a unique integer index that identifies an
         Nokia SROS series manufactured hardware component, such as an IOM,
         CPM, Fabric or MDA card. Also TmnxHwIndexOrZero can be zero."
    SYNTAX      Integer32 (0..2147483647)

TmnxHwClass                      ::= TEXTUAL-CONVENTION
    STATUS      current
    DESCRIPTION
        "TmnxHwClass is an enumerated integer that identifies the general
         hardware type of a component in the tmnxHwTable."
    SYNTAX      INTEGER {
        other            (1),
        unknown          (2),
        physChassis      (3),
        container        (4),
        powerSupply      (5),
        fan              (6),
        sensor           (7),
        ioModule         (8),
        cpmModule        (9),
        fabricModule     (10),
        mdaModule        (11),
        flashDiskModule  (12),
        port             (13),
        mcm              (14),
        ccm              (15),
        oesCard          (16),
        oesControlCard   (17),
        oesUserPanel     (18),
        alarmInputModule (19)
    }

TmnxPhysChassisClass             ::= TEXTUAL-CONVENTION
    STATUS      current
    DESCRIPTION
        "TmnxPhysChassisClass is an enumerated integer that identifies the
         general physical chassis class in the tmnxPhysChassisTable. It is also
         used to indicate a sub-class of the TmnxHwClass type in a tmnxHwIndex.
         A value of 0 instead of 'routerChassis (3)' is used in tmnxHwIndex to
         represent router chassis.

         Values:
            other         (1) - Other chassis class
            unknown       (2) - Unknown chassis class
            routerChassis (3) - Router chassis class
            oesChassis    (4) - Optical Extension Shelf chassis class
            ethSatChassis (5) - Ethernet Satellite chassis class
            tdmSatChassis (6) - Time Division Multiplexing Satellite
                                chassis class
            "
    SYNTAX      INTEGER {
        other         (1),
        unknown       (2),
        routerChassis (3),
        oesChassis    (4),
        ethSatChassis (5),
        tdmSatChassis (6)
    }

TmnxPhysChassisRole              ::= TEXTUAL-CONVENTION
    STATUS      current
    DESCRIPTION
        "The TmnxPhysChassisRole is an enumerated integer that indicates the
         general Physical Chassis role an individual physical chassis is
         provisioned to support.

         Values:
            standalone     (1)  - A chassis that is operating in a system
                                  with no more than one router chassis (note
                                  the system may contain other non-router
                                  chassis such as OES)
            master         (2)  - The master router chassis in a 7950 XRS-40
                                  system
            extension      (3)  - An extension router chassis a 7950 XRS-40
                                  system
            oes-master     (4)  - The master OES chassis in an OES complex
                                   managed by the router
            oes-subtending (5)  - A subtending OES chassis in the OES complex
                                   managed by the router
            sat-ethernet   (6)  - An Ethernet satellite chassis
            sat-tdm        (7)  - A Time Division Multiplexing satellite chassis
            "
    SYNTAX      INTEGER {
        standalone     (1),
        master         (2),
        extension      (3),
        oes-master     (4),
        oes-subtending (5),
        sat-ethernet   (6),
        sat-tdm        (7),
        reserved8      (8),
        reserved9      (9)
    }

TmnxCardType                     ::= TEXTUAL-CONVENTION
    STATUS      current
    DESCRIPTION
        "TmnxCardType is an index into the tmnxCardTypeTable used to identify a
         specific type of card."
    SYNTAX      Unsigned32

TmnxCardSuppType                 ::= TEXTUAL-CONVENTION
    STATUS      current
    DESCRIPTION
        "The TmnxCardSuppType is a bit-mask specifying the valid card types
         supported for a specific card slot.

         When multiple bits are set, it can be used to identify a set or list
         of card types used in the tmnxCardTable and tmnxCpmCardTable to
         indicate supported cards within a specific chassis slot. Some example
         card types might be:

                    sfm-400g  -- 400g CPM/SF module
                    sfm-200g  -- 200g CPM/SF module
                    iom-20g   -- 2 x 10-Gig MDA IOM Card"
    SYNTAX      BITS {
        invalid-card-type (0),
        unassigned        (1),
        supp-card-type-2  (2),
        supp-card-type-3  (3),
        supp-card-type-4  (4),
        supp-card-type-5  (5),
        supp-card-type-6  (6),
        supp-card-type-7  (7),
        supp-card-type-8  (8),
        supp-card-type-9  (9),
        supp-card-type-10 (10),
        supp-card-type-11 (11),
        supp-card-type-12 (12),
        supp-card-type-13 (13),
        supp-card-type-14 (14),
        supp-card-type-15 (15),
        supp-card-type-16 (16),
        supp-card-type-17 (17),
        supp-card-type-18 (18),
        supp-card-type-19 (19),
        supp-card-type-20 (20),
        supp-card-type-21 (21),
        supp-card-type-22 (22),
        supp-card-type-23 (23),
        supp-card-type-24 (24),
        supp-card-type-25 (25),
        supp-card-type-26 (26),
        supp-card-type-27 (27),
        supp-card-type-28 (28),
        supp-card-type-29 (29),
        supp-card-type-30 (30),
        supp-card-type-31 (31),
        supp-card-type-32 (32),
        supp-card-type-33 (33),
        supp-card-type-34 (34),
        supp-card-type-35 (35),
        supp-card-type-36 (36),
        supp-card-type-37 (37),
        supp-card-type-38 (38),
        supp-card-type-39 (39),
        supp-card-type-40 (40),
        supp-card-type-41 (41),
        supp-card-type-42 (42),
        supp-card-type-43 (43),
        supp-card-type-44 (44),
        supp-card-type-45 (45),
        supp-card-type-46 (46),
        supp-card-type-47 (47),
        supp-card-type-48 (48),
        supp-card-type-49 (49),
        supp-card-type-50 (50),
        supp-card-type-51 (51),
        supp-card-type-52 (52),
        supp-card-type-53 (53),
        supp-card-type-54 (54),
        supp-card-type-55 (55),
        supp-card-type-56 (56),
        supp-card-type-57 (57),
        supp-card-type-58 (58),
        supp-card-type-59 (59),
        supp-card-type-60 (60),
        supp-card-type-61 (61),
        supp-card-type-62 (62),
        supp-card-type-63 (63),
        supp-card-type-64 (64),
        supp-card-type-65 (65),
        supp-card-type-66 (66),
        supp-card-type-67 (67),
        supp-card-type-68 (68),
        supp-card-type-69 (69),
        supp-card-type-70 (70),
        supp-card-type-71 (71),
        supp-card-type-72 (72),
        supp-card-type-73 (73),
        supp-card-type-74 (74),
        supp-card-type-75 (75),
        supp-card-type-76 (76),
        supp-card-type-77 (77),
        supp-card-type-78 (78),
        supp-card-type-79 (79),
        supp-card-type-80 (80),
        supp-card-type-81 (81),
        supp-card-type-82 (82),
        supp-card-type-83 (83),
        supp-card-type-84 (84),
        supp-card-type-85 (85),
        supp-card-type-86 (86),
        supp-card-type-87 (87)
    }

TmnxPEQType                      ::= TEXTUAL-CONVENTION
    STATUS      current
    DESCRIPTION
        "TmnxPEQType is an index into the tmnxPEQTypeTable used to identify a
         specific type of PEQ"
    SYNTAX      Unsigned32

TmnxPEQSuppType                  ::= TEXTUAL-CONVENTION
    STATUS      current
    DESCRIPTION
        "The TmnxPEQSuppType is a bit-mask specifying the PEQ type supported
         for a specific PEQ slot.

         When multiple bits are set, it can be used to identify a set or
         list of PEQ types that can be used in the tmnxChassisPEQTable to
         indicate supported PEQs within a specific chassis PEQ slot.
         An example of a PEQ type is:
            apeq2000 -- apeq-dc-2000."
    SYNTAX      BITS {
        invalidPEQType (0),
        unassigned     (1),
        suppPEQType2   (2),
        suppPEQType3   (3),
        suppPEQType4   (4),
        suppPEQType5   (5),
        suppPEQType6   (6),
        suppPEQType7   (7),
        suppPEQType8   (8),
        suppPEQType9   (9),
        suppPEQType10  (10),
        suppPEQType11  (11),
        suppPEQType12  (12),
        suppPEQType13  (13),
        suppPEQType14  (14),
        suppPEQType15  (15)
    }

TmnxFabricType                   ::= TEXTUAL-CONVENTION
    STATUS      current
    DESCRIPTION
        "The TmnxFabricType data type is an integer that specifies an Nokia
         SROS series fabric card type.

         A TmnxFabricType value is valid when there is a corresponding row in
         the tmnxFabricTypeTable."
    SYNTAX      Unsigned32

TmnxFabricSuppType               ::= TEXTUAL-CONVENTION
    STATUS      current
    DESCRIPTION
        "The TmnxFabricSuppType is a bit-mask specifying the valid fabric card
         types supported for a specific card slot.

         When multiple bits are set, it can be used to identify a set or list
         of card types used in the tmnxFabricTable to indicate supported fabric
         cards within a specific chassis slot. Some example card types might
         be:

                    integrated -- the CPM/SF Module consists of an integrated
                                  fabric card."
    SYNTAX      BITS {
        invalidCardType (0),
        unassigned      (1),
        suppCardType2   (2),
        suppCardType3   (3),
        suppCardType4   (4),
        suppCardType5   (5),
        suppCardType6   (6),
        suppCardType7   (7),
        suppCardType8   (8),
        suppCardType9   (9),
        suppCardType10  (10),
        suppCardType11  (11),
        suppCardType12  (12),
        suppCardType13  (13),
        suppCardType14  (14),
        suppCardType15  (15),
        suppCardType16  (16),
        suppCardType17  (17),
        suppCardType18  (18),
        suppCardType19  (19),
        suppCardType20  (20),
        suppCardType21  (21),
        suppCardType22  (22),
        suppCardType23  (23),
        suppCardType24  (24),
        suppCardType25  (25),
        suppCardType26  (26),
        suppCardType27  (27),
        suppCardType28  (28),
        suppCardType29  (29),
        suppCardType30  (30),
        suppCardType31  (31),
        suppCardType32  (32),
        suppCardType33  (33),
        suppCardType34  (34),
        suppCardType35  (35),
        suppCardType36  (36),
        suppCardType37  (37),
        suppCardType38  (38),
        suppCardType39  (39),
        suppCardType40  (40),
        suppCardType41  (41),
        suppCardType42  (42),
        suppCardType43  (43),
        suppCardType44  (44),
        suppCardType45  (45),
        suppCardType46  (46),
        suppCardType47  (47),
        suppCardType48  (48),
        suppCardType49  (49),
        suppCardType50  (50),
        suppCardType51  (51),
        suppCardType52  (52),
        suppCardType53  (53),
        suppCardType54  (54),
        suppCardType55  (55),
        suppCardType56  (56),
        suppCardType57  (57),
        suppCardType58  (58),
        suppCardType59  (59),
        suppCardType60  (60),
        suppCardType61  (61),
        suppCardType62  (62),
        suppCardType63  (63),
        suppCardType64  (64),
        suppCardType65  (65),
        suppCardType66  (66),
        suppCardType67  (67),
        suppCardType68  (68),
        suppCardType69  (69),
        suppCardType70  (70),
        suppCardType71  (71),
        suppCardType72  (72),
        suppCardType73  (73),
        suppCardType74  (74),
        suppCardType75  (75),
        suppCardType76  (76),
        suppCardType77  (77),
        suppCardType78  (78),
        suppCardType79  (79)
    }

TmnxCardRebootType               ::= TEXTUAL-CONVENTION
    STATUS      current
    DESCRIPTION
        "The TmnxCardRebootType is an enumerated integer that describes the
         values used to support reboot operation style commands.

         GETs and GETNEXTs on a variable of this type always returns
         'not-applicable (2)'."
    SYNTAX      INTEGER {
        cardReset      (1),
        notApplicable  (2),
        cardPowerCycle (3)
    }

TmnxChassisType                  ::= TEXTUAL-CONVENTION
    STATUS      current
    DESCRIPTION
        "TmnxChassisType is an index into the tmnxChassisTypeTable used to
         identify a specific type of chassis."
    SYNTAX      Unsigned32

TmnxDeviceState                  ::= TEXTUAL-CONVENTION
    STATUS      current
    DESCRIPTION
        "The TmnxDeviceState data type is an enumerated integer that describes
         the values used to identify states of chassis components such as fans
         and power supplies."
    SYNTAX      INTEGER {
        deviceStateUnknown      (1),
        deviceNotEquipped       (2),
        deviceStateOk           (3),
        deviceStateFailed       (4),
        deviceStateOutOfService (5),
        deviceNotProvisioned    (6)
    }

TmnxLEDState                     ::= TEXTUAL-CONVENTION
    STATUS      current
    DESCRIPTION
        "The TmnxLEDState data type is an enumerated integer that describes the
         values used to identify state LEDs on Nokia SROS series cards."
    SYNTAX      INTEGER {
        ledNotApplicable (0),
        ledOff           (1),
        ledRed           (2),
        ledAmber         (3),
        ledYellow        (4),
        ledGreen         (5),
        ledAmberBlink    (6),
        ledYellowBlink   (7),
        ledGreenBlink    (8),
        ledRedBlink      (9)
    }

TmnxMdaType                      ::= TEXTUAL-CONVENTION
    STATUS      current
    DESCRIPTION
        "TmnxMdaType is an index into the tmnxMdaTypeTable used to identify a
         specific type of MDA."
    SYNTAX      Unsigned32

TmnxMDASuppType                  ::= TEXTUAL-CONVENTION
    STATUS      current
    DESCRIPTION
        "The TmnxMDASuppType data type is a SNMP BIT that is used to identify
         the kind of Media Dependent Adapter (MDA) supported on a card.

         When multiple bits are set, it can be used to identify a set or list
         of supported MDAs within a specific card slot. The MDA types are
         defined in the tmnxMdaTypeTable."
    SYNTAX      BITS {
        invalid-MDA-type  (0),
        unassigned        (1),
        supp-MDA-type-2   (2),
        supp-MDA-type-3   (3),
        supp-MDA-type-4   (4),
        supp-MDA-type-5   (5),
        supp-MDA-type-6   (6),
        supp-MDA-type-7   (7),
        supp-MDA-type-8   (8),
        supp-MDA-type-9   (9),
        supp-MDA-type-10  (10),
        supp-MDA-type-11  (11),
        supp-MDA-type-12  (12),
        supp-MDA-type-13  (13),
        supp-MDA-type-14  (14),
        supp-MDA-type-15  (15),
        supp-MDA-type-16  (16),
        supp-MDA-type-17  (17),
        supp-MDA-type-18  (18),
        supp-MDA-type-19  (19),
        supp-MDA-type-20  (20),
        supp-MDA-type-21  (21),
        supp-MDA-type-22  (22),
        supp-MDA-type-23  (23),
        supp-MDA-type-24  (24),
        supp-MDA-type-25  (25),
        supp-MDA-type-26  (26),
        supp-MDA-type-27  (27),
        supp-MDA-type-28  (28),
        supp-MDA-type-29  (29),
        supp-MDA-type-30  (30),
        supp-MDA-type-31  (31),
        supp-MDA-type-32  (32),
        supp-MDA-type-33  (33),
        supp-MDA-type-34  (34),
        supp-MDA-type-35  (35),
        supp-MDA-type-36  (36),
        supp-MDA-type-37  (37),
        supp-MDA-type-38  (38),
        supp-MDA-type-39  (39),
        supp-MDA-type-40  (40),
        supp-MDA-type-41  (41),
        supp-MDA-type-42  (42),
        supp-MDA-type-43  (43),
        supp-MDA-type-44  (44),
        supp-MDA-type-45  (45),
        supp-MDA-type-46  (46),
        supp-MDA-type-47  (47),
        supp-MDA-type-48  (48),
        supp-MDA-type-49  (49),
        supp-MDA-type-50  (50),
        supp-MDA-type-51  (51),
        supp-MDA-type-52  (52),
        supp-MDA-type-53  (53),
        supp-MDA-type-54  (54),
        supp-MDA-type-55  (55),
        supp-MDA-type-56  (56),
        supp-MDA-type-57  (57),
        supp-MDA-type-58  (58),
        supp-MDA-type-59  (59),
        supp-MDA-type-60  (60),
        supp-MDA-type-61  (61),
        supp-MDA-type-62  (62),
        supp-MDA-type-63  (63),
        supp-MDA-type-64  (64),
        supp-MDA-type-65  (65),
        supp-MDA-type-66  (66),
        supp-MDA-type-67  (67),
        supp-MDA-type-68  (68),
        supp-MDA-type-69  (69),
        supp-MDA-type-70  (70),
        supp-MDA-type-71  (71),
        supp-MDA-type-72  (72),
        supp-MDA-type-73  (73),
        supp-MDA-type-74  (74),
        supp-MDA-type-75  (75),
        supp-MDA-type-76  (76),
        supp-MDA-type-77  (77),
        supp-MDA-type-78  (78),
        supp-MDA-type-79  (79),
        supp-MDA-type-80  (80),
        supp-MDA-type-81  (81),
        supp-MDA-type-82  (82),
        supp-MDA-type-83  (83),
        supp-MDA-type-84  (84),
        supp-MDA-type-85  (85),
        supp-MDA-type-86  (86),
        supp-MDA-type-87  (87),
        supp-MDA-type-88  (88),
        supp-MDA-type-89  (89),
        supp-MDA-type-90  (90),
        supp-MDA-type-91  (91),
        supp-MDA-type-92  (92),
        supp-MDA-type-93  (93),
        supp-MDA-type-94  (94),
        supp-MDA-type-95  (95),
        supp-MDA-type-96  (96),
        supp-MDA-type-97  (97),
        supp-MDA-type-98  (98),
        supp-MDA-type-99  (99),
        supp-MDA-type-100 (100),
        supp-MDA-type-101 (101),
        supp-MDA-type-102 (102),
        supp-MDA-type-103 (103),
        supp-MDA-type-104 (104),
        supp-MDA-type-105 (105),
        supp-MDA-type-106 (106),
        supp-MDA-type-107 (107),
        supp-MDA-type-108 (108),
        supp-MDA-type-109 (109),
        supp-MDA-type-110 (110),
        supp-MDA-type-111 (111),
        supp-MDA-type-112 (112),
        supp-MDA-type-113 (113),
        supp-MDA-type-114 (114),
        supp-MDA-type-115 (115),
        supp-MDA-type-116 (116),
        supp-MDA-type-117 (117),
        supp-MDA-type-118 (118),
        supp-MDA-type-119 (119),
        supp-MDA-type-120 (120),
        supp-MDA-type-121 (121),
        supp-MDA-type-122 (122),
        supp-MDA-type-123 (123),
        supp-MDA-type-124 (124),
        supp-MDA-type-125 (125),
        supp-MDA-type-126 (126),
        supp-MDA-type-127 (127),
        supp-MDA-type-128 (128),
        supp-MDA-type-129 (129),
        supp-MDA-type-130 (130),
        supp-MDA-type-131 (131),
        supp-MDA-type-132 (132),
        supp-MDA-type-133 (133),
        supp-MDA-type-134 (134),
        supp-MDA-type-135 (135),
        supp-MDA-type-136 (136),
        supp-MDA-type-137 (137),
        supp-MDA-type-138 (138),
        supp-MDA-type-139 (139),
        supp-MDA-type-140 (140),
        supp-MDA-type-141 (141),
        supp-MDA-type-142 (142),
        supp-MDA-type-143 (143),
        supp-MDA-type-144 (144),
        supp-MDA-type-145 (145),
        supp-MDA-type-146 (146),
        supp-MDA-type-147 (147),
        supp-MDA-type-148 (148),
        supp-MDA-type-149 (149),
        supp-MDA-type-150 (150),
        supp-MDA-type-151 (151),
        supp-MDA-type-152 (152),
        supp-MDA-type-153 (153),
        supp-MDA-type-154 (154),
        supp-MDA-type-155 (155),
        supp-MDA-type-156 (156),
        supp-MDA-type-157 (157),
        supp-MDA-type-158 (158),
        supp-MDA-type-159 (159),
        supp-MDA-type-160 (160),
        supp-MDA-type-161 (161),
        supp-MDA-type-162 (162),
        supp-MDA-type-163 (163),
        supp-MDA-type-164 (164),
        supp-MDA-type-165 (165),
        supp-MDA-type-166 (166),
        supp-MDA-type-167 (167),
        supp-MDA-type-168 (168),
        supp-MDA-type-169 (169),
        supp-MDA-type-170 (170),
        supp-MDA-type-171 (171),
        supp-MDA-type-172 (172),
        supp-MDA-type-173 (173),
        supp-MDA-type-174 (174),
        supp-MDA-type-175 (175),
        supp-MDA-type-176 (176),
        supp-MDA-type-177 (177),
        supp-MDA-type-178 (178),
        supp-MDA-type-179 (179),
        supp-MDA-type-180 (180),
        supp-MDA-type-181 (181),
        supp-MDA-type-182 (182),
        supp-MDA-type-183 (183)
    }

TmnxMDAChanType                  ::= TEXTUAL-CONVENTION
    STATUS      current
    DESCRIPTION
        "The TmnxMDAChanType data type indicates the type of channel that can
         be created on an MDA."
    SYNTAX      INTEGER {
        unknown     (0),
        sonetSts768 (1),
        sonetSts192 (2),
        sonetSts48  (3),
        sonetSts12  (4),
        sonetSts3   (5),
        sonetSts1   (6),
        sdhTug3     (7),
        sonetVtg    (8),
        sonetVt15   (9),
        sonetVt2    (10),
        sonetVt3    (11),
        sonetVt6    (12),
        pdhTu3      (13),
        pdhDs3      (14),
        pdhE3       (15),
        pdhDs1      (16),
        pdhE1       (17),
        pdhDs0Grp   (18)
    }

TmnxMdaAtmMode                   ::= TEXTUAL-CONVENTION
    STATUS      current
    DESCRIPTION
        "TmnxMdaAtmMode is an enumerated integer whose value specifies the
         maximum number of Virtual Circuits for an ATM-capable Media Dependent
         Adapter (MDA)."
    SYNTAX      INTEGER {
        notApplicable (0),
        max8kVc       (1),
        max16kVc      (2)
    }

TmnxCcmType                      ::= TEXTUAL-CONVENTION
    STATUS      current
    DESCRIPTION
        "The TmnxCcmType data type is bit-mask field that describes
         the values used to identify the kind of Chassis Control
         module (CCM) installed on the chassis.  A TmnxCcmType bit
         value specifies the index value for the entry in the
         tmnxCcmTypeTable used to identify a specific type of CCM
         manufactured by Nokia.  When multiple bits are set, it can
         be used to identify a set or list of CCM types used in the
         tmnxCcmTable to indicate supported CCMs within a specific
         chassis slot.  Some example CCM types are:

                    unknown            -- unknown/uninstalled
                    ccm-v1             -- Chassis Control Module version 1"
    SYNTAX      Unsigned32

TmnxMcmType                      ::= TEXTUAL-CONVENTION
    STATUS      current
    DESCRIPTION
        "The TmnxMcmType data type is bit-mask field that describes
         the values used to identify the kind of MDA Carrier
         module (MCM) installed on the chassis.  A TmnxMcmType bit
         value specifies the index value for the entry in the
         tmnxMcmTypeTable used to identify a specific type of MCM
         manufactured by Nokia.  When multiple bits are set, it can
         be used to identify a set or list of MCM types used in the
         tmnxMcmTable to indicate supported MCMs within a specific
         card slot."
    SYNTAX      Unsigned32

TmnxSlotNum                      ::= TEXTUAL-CONVENTION
    STATUS      current
    DESCRIPTION
        "The TmnxSlotNum data type is an integer that specifies a slot in an
         Nokia SROS series chassis."
    SYNTAX      Integer32 (1..128)

TmnxSlotNumOrZero                ::= TEXTUAL-CONVENTION
    STATUS      current
    DESCRIPTION
        "The TmnxSlotNumOrZero data type is an integer that specifies a slot in
         an Nokia SROS series chassis or zero."
    SYNTAX      Integer32 (0..128)

TmnxPortAdminStatus              ::= TEXTUAL-CONVENTION
    STATUS      current
    DESCRIPTION
        "The desired administrative status of this port."
    SYNTAX      INTEGER {
        noop         (1),
        inService    (2),
        outOfService (3),
        diagnose     (4)
    }

TmnxChassisMode                  ::= TEXTUAL-CONVENTION
    STATUS      current
    DESCRIPTION
        "The TmnxChassisMode data type is an enumerated integer that specifies
         the values used to identify which set of scaling numbers and features
         are effective for an Nokia SROS series chassis. 'modeD' corresponds to
         the scaling and features that come with iom3-xp/imm modules or newer
         modules."
    SYNTAX      INTEGER {
        modeD (4)
    }

TmnxSETSRefSource                ::= TEXTUAL-CONVENTION
    STATUS      current
    DESCRIPTION
        "The TmnxSETSRefSource data type is an enumerated integer that
         describes the values used to identify the Synchronous Equipment Timing
         Source (SETS) timing reference source."
    SYNTAX      INTEGER {
        otherCPM    (0),
        reference1  (1),
        reference2  (2),
        bits        (3),
        bits2       (4),
        ptp         (5),
        noReference (6)
    }

TmnxSETSRefQualified             ::= TEXTUAL-CONVENTION
    STATUS      current
    DESCRIPTION
        "The TmnxSETSRefQualified data type is an enumerated integer that
         describes the values used to identify whether the reference is
         'qualified' or 'not-qualified' for use by SETS."
    SYNTAX      INTEGER {
        qualified     (1),
        not-qualified (2)
    }

TmnxSETSRefAlarm                 ::= TEXTUAL-CONVENTION
    STATUS      current
    DESCRIPTION
        "The TmnxSETSRefAlarm data type is a bitmap that describes the values
         used to identify the alarms on the SETS timing reference source if the
         source is 'not-qualified'.

         'los'    - loss of signal
         'oof'    - out of frequency range
         'oopir'  - out of pull in range."
    SYNTAX      BITS {
        los   (0),
        oof   (1),
        oopir (2)
    }

TmnxSETSStatus                   ::= TEXTUAL-CONVENTION
    STATUS      current
    DESCRIPTION
        "The TmnxSETSStatus textual convention specifies the status of the
         Synchronous Timing Equipment Source (SETS)."
    SYNTAX      INTEGER {
        notPresent     (1),
        masterFreerun  (2),
        masterHoldover (3),
        masterLocked   (4),
        slave          (5),
        acquiring      (6)
    }

TmnxBITSIfType                   ::= TEXTUAL-CONVENTION
    STATUS      current
    DESCRIPTION
        "The TmnxBITSIfType data type is an enumerated integer that describes
         the values used to identify the interface and framing types of a BITS
         (Building Integrated Timing Supply) interface."
    REFERENCE
        "G.703, 'Physical/Electrical Characteristics of Hierarchical Digital
         Interfaces', Section 13, November 2001."
    SYNTAX      INTEGER {
        none         (0),
        t1-esf       (1),
        t1-sf        (2),
        e1-pcm30crc  (3),
        e1-pcm31crc  (4),
        g703-2048khz (5)
    }

TmnxSSMQualityLevel              ::= TEXTUAL-CONVENTION
    STATUS      current
    DESCRIPTION
        "The TmnxSSMQualityLevel is an enumerated integer that describes the
         values used to identify the SSM Quality level of received SSM
         messages."
    SYNTAX      INTEGER {
        unknown (0),
        prs     (1),
        stu     (2),
        st2     (3),
        tnc     (4),
        st3e    (5),
        st3     (6),
        smc     (7),
        st4     (8),
        dus     (9),
        prc     (10),
        ssua    (11),
        ssub    (12),
        sec     (13),
        dnu     (14),
        inv     (15),
        pno     (16),
        eec1    (17),
        eec2    (18),
        failed  (19)
    }

TmnxRefInState                   ::= TEXTUAL-CONVENTION
    STATUS      current
    DESCRIPTION
        "The TmnxRefInState is an enumerated integer that describes the values
         used to identify the state of system timing reference.

         A value of 'ptpAdminDisabled (17)' means that the PTP timing reference
         is not in use because 'tmnxPtpClockAdminState' is 'outOfService (3)'.
         This value only applies to the PTP timing reference.

         A value of 'ptpOperDown (18)' means that the PTP timing reference is
         not in use because 'tmnxPtpClockOperState' is 'outOfService (3)'. This
         value only applies to the PTP timing reference.

         A value of 'ptpNoParentClock (19)' means that the PTP timing reference
         is not in use because the local PTP clock has not selected a remote
         master clock to be the parent clock.  This value only applies to the
         PTP timing reference.

         A value of 'operSpeedNotSupported (20)' means that the timing
         reference is not in use because the copper based port is operating at
         10 Mbps where recovered timing is not supported.

         A value of 'cpmUnsupBITS2048khz (21)' means that the timing reference
         is not in use because the CPM does not meet the specifications for the
         2048kHz BITS output signal under G.703."
    REFERENCE
        "IEEE Std 1588-2008 'IEEE Standard for a Precision Clock Synchronization
         Protocol for Networked Measurement and Control Systems'.
         G.703, 'Physical/Electrical Characteristics of Hierarchical Digital
         Interfaces', Section 13, November 2001."
    SYNTAX      INTEGER {
        disabled              (0),
        unqualified           (1),
        standby               (2),
        up                    (3),
        previousFailure       (4),
        lowQuality            (5),
        lof                   (6),
        ais                   (7),
        ghost                 (8),
        validating            (9),
        reserved-10           (10),
        reserved-11           (11),
        reserved-12           (12),
        fer                   (13),
        reserved-14           (14),
        reserved-15           (15),
        reserved-16           (16),
        ptpAdminDisabled      (17),
        ptpOperDown           (18),
        ptpNoParentClock      (19),
        operSpeedNotSupported (20),
        cpmUnsupBITS2048khz   (21)
    }

TmnxBITSOutSource                ::= TEXTUAL-CONVENTION
    STATUS      current
    DESCRIPTION
        "The TmnxBITSOutSource is an enumerated integer that describes the
         values used to identity the source of the BITS (Building Integrated
         Timing Supply) output.

         When TmnxBITSOutSource is 'lineRef (1)', the BITS output timing is
         selected from either the one of the timing input references, without
         any filtering.  Either the first or second line reference, or the PTP
         timing input reference may be selected to be transmitted in this
         manner.  The BITS timing input is never selected in this mode.

         When TmnxBITSOutSource is 'internalClock (2)', the BITS output timing
         is driven from the system timing."
    REFERENCE
        "ITU-T G.8264/Y.1364 Distribution of timing through packet networks,
         Section A.7."
    SYNTAX      INTEGER {
        lineRef       (1),
        internalClock (2)
    }

TmnxCcagId                       ::= TEXTUAL-CONVENTION
    STATUS      current
    DESCRIPTION
        "TmnxCcagId is an integer specifying the cross connect aggregation
         group. The value '0' is used when a ccag is not defined and is not a
         valid value when TmnxCcagId is used as an index."
    SYNTAX      Integer32 (0..8)

TmnxCcagRate                     ::= TEXTUAL-CONVENTION
    STATUS      current
    DESCRIPTION
        "TmnxCcagRate is an integer specifying the rate for a CCAG member in
         Kbps.  The range of TmnxCcagRate is from 0 Kbps to 100Gbps. The value
         '-1' is used for maximum rate available."
    SYNTAX      Integer32 (-1..100000000)

TmnxCcagRateOption               ::= TEXTUAL-CONVENTION
    STATUS      current
    DESCRIPTION
        "TmnxCcagRateOption specifies how the defined rate is
         applied to active Cross Connect Adaptors (CCAs).
         aggregate (1) -  the defined rate is equally divided among the CCAs in
                          the CCAG member list based on the number of active
                          CCAs.
         cca       (2) -  the defined rate is applied to all CCAs in the CCAG
                          member list."
    SYNTAX      INTEGER {
        aggregate (1),
        cca       (2)
    }

TmnxChassisPemType               ::= TEXTUAL-CONVENTION
    STATUS      current
    DESCRIPTION
        "TmnxChassisPemType specifies what Power Entry Module (PEM) type is
         installed in the Chassis.
         not-applicable (0) - Chassis does not support an installed PEM.
         unknown (1)        - Unknown kind of PEM installed.
         pem (2)            - First generation of the PEM module.
         pem-3 (3)          - Second generation of the PEM module capable of
                              supporting the IOM3/IMM modules.
         peq (4)            - Power Equalizer."
    SYNTAX      INTEGER {
        not-applicable (0),
        unknown        (1),
        pem            (2),
        pem-3          (3),
        peq            (4)
    }

TmnxCardSlotBitMap               ::= TEXTUAL-CONVENTION
    STATUS      current
    DESCRIPTION
        "TmnxCardSlotBitMap specifies a bitmap of card slots. A bit value set
         to '1' indicates the slot is used by the object."
    SYNTAX      BITS {
        slot1  (0),
        slot2  (1),
        slot3  (2),
        slot4  (3),
        slot5  (4),
        slot6  (5),
        slot7  (6),
        slot8  (7),
        slot9  (8),
        slot10 (9),
        slot11 (10),
        slot12 (11),
        slot13 (12),
        slot14 (13),
        slot15 (14),
        slot16 (15),
        slot17 (16),
        slot18 (17),
        slot19 (18),
        slot20 (19),
        slot21 (20),
        slot22 (21),
        slot23 (22),
        slot24 (23)
    }

TmnxTunnelGroupId                ::= TEXTUAL-CONVENTION
    STATUS      current
    DESCRIPTION
        "TmnxTunnelGroupId is an integer specifying the ISA tunnel-group."
    SYNTAX      Unsigned32 (1..16)

TmnxTunnelGroupIdOrZero          ::= TEXTUAL-CONVENTION
    STATUS      current
    DESCRIPTION
        "TmnxTunnelGroupIdOrZero is an integer specifying the ISA tunnel-group
         A value of zero is used when the tunnel-group is not defined."
    SYNTAX      Unsigned32 (0..16)

TmnxPowerSupAssignType           ::= TEXTUAL-CONVENTION
    STATUS      current
    DESCRIPTION
        "TmnxPowerSupAssignType specifies the type of power supply that is
         assigned for a platform."
    SYNTAX      INTEGER {
        none       (0),
        dc         (1),
        acSingle   (2),
        acMultiple (3),
        default    (4)
    }

TmnxFpGeneration                 ::= TEXTUAL-CONVENTION
    STATUS      current
    DESCRIPTION
        "TmnxFpGeneration specifies the Forwarding Plane (FP) network processor
         generation."
    SYNTAX      INTEGER {
        not-applicable (0),
        fp2            (1),
        fp3            (2),
        fp4            (3)
    }

tmnxHwObjs                       OBJECT IDENTIFIER ::= { tmnxSRObjs 2 }

tmnxChassisObjs                  OBJECT IDENTIFIER ::= { tmnxHwObjs 1 }

tmnxChassisTotalNumber           OBJECT-TYPE
    SYNTAX      Integer32 (1..32)
    MAX-ACCESS  read-only
    STATUS      current
    DESCRIPTION
        "The number of chassis installed in this system.  For the first
         release of the Nokia 7x50 series product, there is only
         1 chassis per system.  A multi-chassis system model is supported
         to allow for future product expansion."
    ::= { tmnxChassisObjs 1 }

tmnxChassisLastChange            OBJECT-TYPE
    SYNTAX      TimeStamp
    MAX-ACCESS  read-only
    STATUS      current
    DESCRIPTION
        "The value of tmnxChassisLastChange indicates the time, since system
         startup, when tmnxChassisTable last changed."
    ::= { tmnxChassisObjs 2 }

tmnxChassisTable                 OBJECT-TYPE
    SYNTAX      SEQUENCE OF TmnxChassisEntry
    MAX-ACCESS  not-accessible
    STATUS      current
    DESCRIPTION
        "tmnxChassisTable contains Nokia 7x50 system level information."
    ::= { tmnxChassisObjs 3 }

tmnxChassisEntry                 OBJECT-TYPE
    SYNTAX      TmnxChassisEntry
    MAX-ACCESS  not-accessible
    STATUS      current
    DESCRIPTION
        "tmnxChassisEntry consists of the system level information pertaining
         to the hardware present in the system.

         Only one entry is created and maintained by the system, which is
         assigned the tmnxChassisIndex value '1'. Once this entry is created,
         it cannot be destroyed. Additional entries cannot be manually created
         or destroyed.

         Support of multiple chassis' are managed through the use of
         tmnxPhysChassisTable."
    INDEX       { tmnxChassisIndex }
    ::= { tmnxChassisTable 1 }

TmnxChassisEntry                 ::= SEQUENCE
{
    tmnxChassisIndex                 TmnxChassisIndex,
    tmnxChassisRowStatus             RowStatus,
    tmnxChassisName                  TNamedItemOrEmpty,
    tmnxChassisType                  TmnxChassisType,
    tmnxChassisLocation              TItemDescription,
    tmnxChassisCoordinates           TItemDescription,
    tmnxChassisNumSlots              Unsigned32,
    tmnxChassisNumPorts              Unsigned32,
    tmnxChassisNumPwrSupplies        Unsigned32,
    tmnxChassisNumFanTrays           Unsigned32,
    tmnxChassisNumFans               Unsigned32,
    tmnxChassisCriticalLEDState      TmnxLEDState,
    tmnxChassisMajorLEDState         TmnxLEDState,
    tmnxChassisMinorLEDState         TmnxLEDState,
    tmnxChassisBaseMacAddress        MacAddress,
    tmnxChassisCLLICode              DisplayString,
    tmnxChassisReboot                TmnxActionType,
    tmnxChassisUpgrade               TmnxActionType,
    tmnxChassisAdminMode             TmnxChassisMode,
    tmnxChassisOperMode              TmnxChassisMode,
    tmnxChassisModeForce             TmnxActionType,
    tmnxChassisUpdateWaitTime        Unsigned32,
    tmnxChassisUpdateTimeLeft        Unsigned32,
    tmnxChassisOverTempState         INTEGER,
    tmnxChassisMixedModeIomAdminMode TmnxEnabledDisabled,
    tmnxChassisMixedModeIomUpgrList  BITS,
    tmnxChassisRedForcedSingleSfm    TruthValue,
    tmnxChassisOperNumSlots          Unsigned32,
    tmnxChassisOperTopology          INTEGER,
    tmnxChassisFabricSpeed           INTEGER,
    tmnxChassisPortIdScheme          INTEGER,
    tmnxChassisVsrCongestionMgmt     TruthValue,
    tmnxChassisAlarmLEDState         TmnxLEDState,
    tmnxChassisFPGenerationFP2       TruthValue,
    tmnxChassisFPGenerationFP3       TruthValue,
    tmnxChassisFPGenerationFP4       TruthValue
}

tmnxChassisIndex                 OBJECT-TYPE
    SYNTAX      TmnxChassisIndex
    MAX-ACCESS  not-accessible
    STATUS      current
    DESCRIPTION
        "The value of tmnxChassisIndex specifies a system identifier. The value
         of this object cannot be changed. The only supported value is '1'.

         Different values of TmnxPhysChassisIndex are used to identify
         different physical chassis (e.g. in an XRS-40 system) in
         tmnxPhysChassisTable."
    ::= { tmnxChassisEntry 1 }

tmnxChassisRowStatus             OBJECT-TYPE
    SYNTAX      RowStatus
    MAX-ACCESS  read-create
    STATUS      current
    DESCRIPTION
        "The value of tmnxChassisRowStatus specifies the row status of the
         system."
    ::= { tmnxChassisEntry 2 }

tmnxChassisName                  OBJECT-TYPE
    SYNTAX      TNamedItemOrEmpty
    MAX-ACCESS  read-create
    STATUS      current
    DESCRIPTION
        "The value of tmnxChassisName specifies the administrative name
         that is assigned to the system.  Setting tmnxChassisName to the
         empty string, ''H, resets tmnxChassisName to the TiMOS default value."
    DEFVAL      { "" }
    ::= { tmnxChassisEntry 3 }

tmnxChassisType                  OBJECT-TYPE
    SYNTAX      TmnxChassisType
    MAX-ACCESS  read-only
    STATUS      current
    DESCRIPTION
        "The value of tmnxChassisType indicates the type of chassis used in
         this Nokia SROS system.  The value of this object is the
         tmnxChassisTypeIndex for the entry in the tmnxChassisTypeTable that
         represents the Nokia SROS series chassis model for this
         system.  Chassis types are distinguished by their backplane type."
    ::= { tmnxChassisEntry 4 }

tmnxChassisLocation              OBJECT-TYPE
    SYNTAX      TItemDescription
    MAX-ACCESS  read-create
    STATUS      current
    DESCRIPTION
        "The value of tmnxChassisLocation specifies the site location of this
         system. This could be used for a Common Language Location Identifier,
         CLLI, code string if desired.

         A CLLI code is an 11-character standardized geographic identifier that
         uniquely identifies the geographic location of places and certain
         functional categories of equipment unique to the telecommunications
         industry.

         All valid CLLI codes are created, updated and maintained in the
         Central Location Online Entry System (CLONES) database."
    DEFVAL      { "" }
    ::= { tmnxChassisEntry 5 }

tmnxChassisCoordinates           OBJECT-TYPE
    SYNTAX      TItemDescription
    MAX-ACCESS  read-create
    STATUS      current
    DESCRIPTION
        "The value of tmnxChassisCoordinates specifies the Global Positioning
         System (GPS) coordinates for the location of the system.

            N 45 58 23, W 34 56 12
            N37 37' 00 latitude, W122 22' 00 longitude
            N36*39.246'  W121*40.121'

         Two-dimensional GPS positioning offers latitude and longitude
         information as a four dimensional vector:

            <Direction, hours, minutes, seconds>

         where Direction is one of the four basic values: N, S, W, E; hours
         ranges from 0 to 180 (for latitude) and 0 to 90 for longitude, and,
         finally, minutes and seconds range from 0 to 60.

         Thus <W, 122, 56, 89> is an example of longitude and <N, 85, 66, 43>
         is an example of latitude.

         Four bytes of addressing space (one byte for each of the four
         dimensions) are necessary to store latitude and four bytes are also
         sufficient to store longitude. Thus eight bytes total are necessary
         to address the whole surface of earth with precision down to 0.1
         mile!  Notice that if we desired precision down to 0.001 mile (1.8
         meters) then we would need just five bytes for each component, or ten
         bytes together for the full address (as military versions provide)."
    DEFVAL      { "" }
    ::= { tmnxChassisEntry 6 }

tmnxChassisNumSlots              OBJECT-TYPE
    SYNTAX      Unsigned32
    MAX-ACCESS  read-only
    STATUS      current
    DESCRIPTION
        "The value of tmnxChassisNumSlots indicates the maximum number of slots
         that can be made available for plug-in cards if the maximum number of
         physical router chassis are populated. This includes both CPM and
         IOM/IMM/XCM slots. For systems that support only a single physical
         chassis, tmnxChassisNumSlots and tmnxChassisOperNumSlots are the same
         value and are equal to the number of physical slots in the chassis.
         Also see tmnxChassisOperNumSlots."
    ::= { tmnxChassisEntry 7 }

tmnxChassisNumPorts              OBJECT-TYPE
    SYNTAX      Unsigned32
    MAX-ACCESS  read-only
    STATUS      current
    DESCRIPTION
        "The value of tmnxChassisNumPorts indicates the total number of ports
         currently installed for all of the physical router chassis in the
         system. This count does not include the Ethernet ports on the CPM
         cards that are used for management access."
    ::= { tmnxChassisEntry 8 }

tmnxChassisNumPwrSupplies        OBJECT-TYPE
    SYNTAX      Unsigned32
    MAX-ACCESS  read-only
    STATUS      current
    DESCRIPTION
        "The value of tmnxChassisNumPwrSupplies indicates the total number of
         power supplies installed for all of the physical router chassis in the
         system."
    ::= { tmnxChassisEntry 9 }

tmnxChassisNumFanTrays           OBJECT-TYPE
    SYNTAX      Unsigned32
    MAX-ACCESS  read-only
    STATUS      current
    DESCRIPTION
        "The value of tmnxChassisNumFanTrays indicates the total number of fan
         trays installed for all of the physical router chassis in the system."
    ::= { tmnxChassisEntry 10 }

tmnxChassisNumFans               OBJECT-TYPE
    SYNTAX      Unsigned32
    MAX-ACCESS  read-only
    STATUS      current
    DESCRIPTION
        "The value of tmnxChassisNumFans indicates the total number of fans
         installed for all of the physical router chassis in the system."
    ::= { tmnxChassisEntry 11 }

tmnxChassisCriticalLEDState      OBJECT-TYPE
    SYNTAX      TmnxLEDState
    MAX-ACCESS  read-only
    STATUS      current
    DESCRIPTION
        "The value of tmnxChassisCriticalLEDState indicates the current state
         of the Critical LED in the system."
    ::= { tmnxChassisEntry 12 }

tmnxChassisMajorLEDState         OBJECT-TYPE
    SYNTAX      TmnxLEDState
    MAX-ACCESS  read-only
    STATUS      current
    DESCRIPTION
        "The value of tmnxChassisMajorLEDState indicates the current state of
         the Major LED in the system."
    ::= { tmnxChassisEntry 13 }

tmnxChassisMinorLEDState         OBJECT-TYPE
    SYNTAX      TmnxLEDState
    MAX-ACCESS  read-only
    STATUS      current
    DESCRIPTION
        "The value of tmnxChassisMinorLEDState indicates the current state of
         the Minor LED in the system."
    ::= { tmnxChassisEntry 14 }

tmnxChassisBaseMacAddress        OBJECT-TYPE
    SYNTAX      MacAddress
    MAX-ACCESS  read-only
    STATUS      current
    DESCRIPTION
        "The value of tmnxChassisBaseMacAddress indicates the base system
         ethernet MAC address. Special purpose MAC addresses used by the system
         software are constructed as offsets from this base address."
    ::= { tmnxChassisEntry 15 }

tmnxChassisCLLICode              OBJECT-TYPE
    SYNTAX      DisplayString
    MAX-ACCESS  read-create
    STATUS      current
    DESCRIPTION
        "The value of tmnxChassisCLLICode specifies the Common Language
         Location Identifier (CLLI) code for the system. A CLLI code is an
         11-character standardized geographic identifier that uniquely
         identifies the geographic location of places and certain functional
         categories of equipment unique to the telecommunications industry.

         If the set on this object specifies a non-null string, the string will
         automatically be truncated or padded (with spaces) to 11 characters."
    ::= { tmnxChassisEntry 16 }

tmnxChassisReboot                OBJECT-TYPE
    SYNTAX      TmnxActionType
    MAX-ACCESS  read-create
    STATUS      current
    DESCRIPTION
        "The value of tmnxChassisReboot specifies if the system will perform a
         reboot.

         Setting the value of this object to 'doAction' causes a soft-reboot of
         the entire system including all the CPM and IOM cards for each
         physical chassis.

         Note that the reboot action is likely to occur before the SNMP SET
         response can be transmitted."
    DEFVAL      { notApplicable }
    ::= { tmnxChassisEntry 17 }

tmnxChassisUpgrade               OBJECT-TYPE
    SYNTAX      TmnxActionType
    MAX-ACCESS  read-create
    STATUS      current
    DESCRIPTION
        "The value of tmnxChassisUpgrade specifies if the system will perform
         an upgrade of all firmware as well as a reboot of the entire system
         including all the CPM and IOM cards for each physical chassis.

         CAUTION: This upgrade and reboot may take several minutes to
         complete.  The chassis MUST NOT be reset or powered down,
         nor cards inserted or removed, during this process.  Any of
         these prohibited actions may cause the cards to be rendered
         inoperable.

         tmnxChassisUpgrade and tmnxChassisReboot must be set together in the
         same SNMP SET request PDU or else the SET request will fail with an
         inconsistentValue error.

         Note that the reboot action is likely to occur before the SNMP SET
         response can be transmitted."
    DEFVAL      { notApplicable }
    ::= { tmnxChassisEntry 18 }

tmnxChassisAdminMode             OBJECT-TYPE
    SYNTAX      TmnxChassisMode
    MAX-ACCESS  read-create
    STATUS      current
    DESCRIPTION
        "The value of tmnxChassisAdminMode specifies the scaling and feature
         set for all of the IOM cards in the system. Setting
         tmnxChassisAdminMode to a particular mode corresponds to the scaling
         and feature sets supported on that IOM card type."
    DEFVAL      { modeD }
    ::= { tmnxChassisEntry 19 }

tmnxChassisOperMode              OBJECT-TYPE
    SYNTAX      TmnxChassisMode
    MAX-ACCESS  read-only
    STATUS      current
    DESCRIPTION
        "The value of tmnxChassisOperMode indicates the operational scaling and
         feature set for all IOM cards in the system for each physical router
         chassis. Changing the value of tmnxChassisAdminMode from a greater
         mode to a lesser mode (downgrade) will result in tmnxChassisAdminMode
         indicating the new mode while tmnxChassisOperMode indicates previous
         mode until the configuration is saved and the system rebooted, at
         which point, the actual downgrade will take effect and both
         tmnxChassisAdminMode and tmnxChassisOperMode will indicate the new
         mode.

         Upgrading from a lesser mode to a greater mode (e.g. From 'modeA' to
         'modeB') will take effect immediately and the tmnxChassisOperMode will
         indicate the same mode as that of tmnxChassisAdminMode."
    ::= { tmnxChassisEntry 20 }

tmnxChassisModeForce             OBJECT-TYPE
    SYNTAX      TmnxActionType
    MAX-ACCESS  read-create
    STATUS      current
    DESCRIPTION
        "The value of tmnxChassisModeForce specifies the force mode of the
         system. Setting the value of this object to 'doAction' in the same
         SNMP SET request where tmnxChassisAdminMode is set to a greater mode
         than the current mode (e.g. New mode 'modeB', while current is
         'modeA') allows each physical chassis in the system to be upgraded to
         the new mode even if there are IOM cards in the physical chassis with
         a tmnxCardAssignedType value that does not support the new mode.

         An attempt to set tmnxChassisModeForce to 'doAction' without also
         setting tmnxChassisAdminMode, in the same SNMP SET request will fail
         with an inconsistentValue error."
    DEFVAL      { notApplicable }
    ::= { tmnxChassisEntry 21 }

tmnxChassisUpdateWaitTime        OBJECT-TYPE
    SYNTAX      Unsigned32 (15..600)
    UNITS       "seconds"
    MAX-ACCESS  read-create
    STATUS      obsolete
    DESCRIPTION
        "The value of tmnxChassisUpdateWaitTime specifies the time to wait
         before rebooting IOM cards running older software versions following a
         software upgrade or downgrade activity switchover. This object was
         obsoleted in release 5.0."
    DEFVAL      { 15 }
    ::= { tmnxChassisEntry 22 }

tmnxChassisUpdateTimeLeft        OBJECT-TYPE
    SYNTAX      Unsigned32
    UNITS       "seconds"
    MAX-ACCESS  read-only
    STATUS      current
    DESCRIPTION
        "Following a software upgrade or downgrade activity switchover, the
         value of tmnxChassisUpdateTimeLeft indicates the time remaining before
         IOM cards or MDAs running older software versions will be rebooted."
    ::= { tmnxChassisEntry 23 }

tmnxChassisOverTempState         OBJECT-TYPE
    SYNTAX      INTEGER {
        stateOk       (1),
        stateOverTemp (2)
    }
    MAX-ACCESS  read-only
    STATUS      current
    DESCRIPTION
        "The value of tmnxChassisOverTempState indicates the over temperature
         state for the system.

         stateOk         Indicates all physical router chassis are below the
                         temperature threshold.
         stateOverTemp   Indicates at least one physical router chassis is
                         above the temperature threshold."
    ::= { tmnxChassisEntry 24 }

tmnxChassisMixedModeIomAdminMode OBJECT-TYPE
    SYNTAX      TmnxEnabledDisabled
    MAX-ACCESS  read-create
    STATUS      current
    DESCRIPTION
        "The value of tmnxChassisMixedModeIomAdminMode specifies if the system
         should allow functionally to run with a mixture of forwarding
         hardware.

         When 'enabled(1)' on a 7450 chassis it allows SR functionality to be
         configured. SR functionality is a superset of ESS functionality. Once
         tmnxChassisMixedModeIomAdminMode is enabled, additional IOMs can be
         converted to SR functionality by setting the tmnxCardCapability field
         of the corresponding tmnxCardEntry.

         When 'enabled(1)' on a 7750 chassis it allows allows IPv6
         functionality without requiring chassis mode C or better.

         tmnxChassisMixedModeIomAdminMode is only applicable when
         tmnxChassisType indicates the chassis type is 7450 ESS-6, 7450 ESS-6v,
         7450 ESS-7, 7450 ESS-12, 7750 SR-7 or 7750 SR-12."
    DEFVAL      { disabled }
    ::= { tmnxChassisEntry 25 }

tmnxChassisMixedModeIomUpgrList  OBJECT-TYPE
    SYNTAX      BITS {
        iomSlot1  (0),
        iomSlot2  (1),
        iomSlot3  (2),
        iomSlot4  (3),
        iomSlot5  (4),
        iomSlot6  (5),
        iomSlot7  (6),
        iomSlot8  (7),
        iomSlot9  (8),
        iomSlot10 (9)
    }
    MAX-ACCESS  read-create
    STATUS      current
    DESCRIPTION
        "The value of tmnxChassisMixedModeIomUpgrList specifies the list of IOM
         slots which are to operate with SR functionality on the 7450 chassis.

         tmnxChassisMixedModeIomUpgrList is only applicable when
         tmnxChassisType indicates the chassis type is 7450 ESS-7 or 7450
         ESS-12, and should only be set when enabling mixed-mode.

         tmnxChassisMixedModeIomUpgrList is a bitmap, with a bit for each IOM
         slot on the chassis.  If the bit for a particular IOM slot is '1', the
         SR functionality will be enabled on the IOM when enabling mixed-mode.
         If the bit is set to '0', the IOM will continue to operate with ESS
         functionality.

         To set a particular bit to '1':
         1.  The IOM slot must have a configured type of iom3-xp, or any type of
             IMM.
         2.  The installed IOM/IMM must be a 7750 IOM/IMM.  The platform type
             for an IOM/IMM can be read using tmnxHwEquippedPlatform.
         3.  tmnxChassisMixedModeIomAdminMode must be set to 'enabled (1)' in
             the same Set request packet."
    DEFVAL      { {} }
    ::= { tmnxChassisEntry 26 }

tmnxChassisRedForcedSingleSfm    OBJECT-TYPE
    SYNTAX      TruthValue
    MAX-ACCESS  read-create
    STATUS      current
    DESCRIPTION
        "The value of tmnxChassisRedForcedSingleSfm specifies whether or not
         the IGP single-SFM-overload state is forced to 'overload' in the
         router instances where the value of the object
         TIMETRA-VRTR-MIB::vRtrSingleSfmOverloadAdminState is equal to
         'inService'."
    DEFVAL      { false }
    ::= { tmnxChassisEntry 27 }

tmnxChassisOperNumSlots          OBJECT-TYPE
    SYNTAX      Unsigned32
    MAX-ACCESS  read-only
    STATUS      current
    DESCRIPTION
        "The value of tmnxChassisOperNumSlots indicates the number of slots
         that are available for plug-in cards of all the physical router
         chassis configured in the system. This includes both CPM and
         IOM/IMM/XCM slots. For systems that support multiple chassis, this
         value will change depending on how many chassis the system is
         configured to be operating with."
    ::= { tmnxChassisEntry 29 }

tmnxChassisOperTopology          OBJECT-TYPE
    SYNTAX      INTEGER {
        standalone (1),
        extended   (2)
    }
    MAX-ACCESS  read-only
    STATUS      current
    DESCRIPTION
        "The value of tmnxChassisOperTopology indicates the inter-chassis
         topology mode in which the system is operating. It indicates how
         multiple chassis are arranged and operate together as a single system.

         A value of 'standalone (1)' indicates that the system is comprised of
         a single physical router chassis.

         A value of 'extended(2)' in a 7950 XRS based system indicates that two
         router chassis are connected together in a 'back-to-back' topology
         with no additional switch fabric chassis. An extended chassis topology
         is comprised of two XRS-20 chassis and is also known as an XRS-40
         system."
    ::= { tmnxChassisEntry 30 }

tmnxChassisFabricSpeed           OBJECT-TYPE
    SYNTAX      INTEGER {
        notApplicable (0),
        speed6g       (1),
        speed10g      (2)
    }
    MAX-ACCESS  read-only
    STATUS      current
    DESCRIPTION
        "The value of tmnxChassisFabricSpeed indicates the system fabric speed.

         On systems that do not calculate the system fabric speed the value
         'notApplicable (0)' is returned."
    ::= { tmnxChassisEntry 31 }

tmnxChassisPortIdScheme          OBJECT-TYPE
    SYNTAX      INTEGER {
        schemeA (1),
        schemeB (2),
        schemeC (3)
    }
    MAX-ACCESS  read-only
    STATUS      current
    DESCRIPTION
        "The value of tmnxChassisPortIdScheme indicates the port mapping scheme
         used by the system for physical ports and channels as represented by
         the TIMETRA-TC-MIB::TmnxPortID textual convention.

         Slots, MDAs (if present), ports, and channels are numbered starting
         with 1.

         Scheme A:
            32 30 | 29 26 | 25 22 | 21 16 | 15  1 |
            +-----+-------+-------+-------+-------+
            |000  |  slot |  mda  | port  |  zero | Physical Port
            +-----+-------+-------+-------+-------+

            32 30 | 29 26 | 25 22 | 21 16 | 15  1 |
            +-----+-------+-------+-------+-------+
            |001  |  slot |  mda  | port  |channel| Channel
            +-----+-------+-------+-------+-------+

         Scheme B:
            32 29 | 28 24 | 23 19 | 18 15 | 14  11 | 10 4 | 3  1 |
            +-----+-------+-------+-------+--------+------+------+
            |0110 |  zero |  slot |  mda  |  zero  | port | zero | Physical Port
            +-----+-------+-------+-------+--------+------+------+

            32 29 | 28 24 | 23 19 | 18 15 | 14  11 | 10 4 | 3  1 |
            +-----+-------+-------+-------+--------+------+------+
            |0111 |  zero |  slot |  mda  |  zero  | port | zero | Channel (*)
            +-----+-------+-------+-------+--------+------+------+
         (*) The encoding does not specify a value for channel since it is
             implicitly channel 1.

         Scheme C:
            32 30 | 29 26 | 25    24 | 23 22 | 21   16 | 15  1 |
            +-----+-------+----------+-------+---------+-------+
            |000  |  slot |  port-hi |  mda  | port-lo |  zero | Physical Port
            +-----+-------+----------+-------+---------+-------+

            32 30 | 29 26 | 25    24 | 23 22 | 21   16 | 15  1 |
            +-----+-------+----------+-------+---------+-------+
            |001  |  slot |  port-hi |  mda  | port-lo |channel| Channel
            +-----+-------+----------+-------+---------+-------+
         (*) 'port-hi' and 'port-lo' are combined make a port."
    ::= { tmnxChassisEntry 32 }

tmnxChassisVsrCongestionMgmt     OBJECT-TYPE
    SYNTAX      TruthValue
    MAX-ACCESS  read-create
    STATUS      current
    DESCRIPTION
        "The value of tmnxChassisVsrCongestionMgmt specifies whether Virtual
         Service Router congestion management is turned on."
    DEFVAL      { false }
    ::= { tmnxChassisEntry 33 }

tmnxChassisAlarmLEDState         OBJECT-TYPE
    SYNTAX      TmnxLEDState
    MAX-ACCESS  read-only
    STATUS      current
    DESCRIPTION
        "On systems that have a single alarm LED, the value of
         tmnxChassisAlarmLEDState indicates the current state of the alarm LED
         in the system."
    ::= { tmnxChassisEntry 34 }

tmnxChassisFPGenerationFP2       OBJECT-TYPE
    SYNTAX      TruthValue
    MAX-ACCESS  read-only
    STATUS      current
    DESCRIPTION
        "The value of tmnxChassisFPGenerationFP2 indicates whether the system
         contains at least one FP2 based line card."
    ::= { tmnxChassisEntry 35 }

tmnxChassisFPGenerationFP3       OBJECT-TYPE
    SYNTAX      TruthValue
    MAX-ACCESS  read-only
    STATUS      current
    DESCRIPTION
        "The value of tmnxChassisFPGenerationFP3 indicates whether the system
         contains at least one FP3 based line card."
    ::= { tmnxChassisEntry 36 }

tmnxChassisFPGenerationFP4       OBJECT-TYPE
    SYNTAX      TruthValue
    MAX-ACCESS  read-only
    STATUS      current
    DESCRIPTION
        "The value of tmnxChassisFPGenerationFP4 indicates whether the system
         contains at least one FP4 based line card."
    ::= { tmnxChassisEntry 37 }

tmnxChassisFanTable              OBJECT-TYPE
    SYNTAX      SEQUENCE OF TmnxChassisFanEntry
    MAX-ACCESS  not-accessible
    STATUS      obsolete
    DESCRIPTION
        "This table contains information about fan trays.

         This table was made obsolete in release 15.0."
    ::= { tmnxChassisObjs 4 }

tmnxChassisFanEntry              OBJECT-TYPE
    SYNTAX      TmnxChassisFanEntry
    MAX-ACCESS  not-accessible
    STATUS      obsolete
    DESCRIPTION
        "Contains information regarding a fan tray.

         This entry was made obsolete in release 15.0."
    INDEX       {
        tmnxChassisIndex,
        tmnxChassisFanIndex
    }
    ::= { tmnxChassisFanTable 1 }

TmnxChassisFanEntry              ::= SEQUENCE
{
    tmnxChassisFanIndex              Unsigned32,
    tmnxChassisFanOperStatus         TmnxDeviceState,
    tmnxChassisFanSpeed              INTEGER,
    tmnxChassisFanRevision           INTEGER,
    tmnxChassisFanSpeedPercent       Unsigned32
}

tmnxChassisFanIndex              OBJECT-TYPE
    SYNTAX      Unsigned32 (1..31)
    MAX-ACCESS  not-accessible
    STATUS      obsolete
    DESCRIPTION
        "The unique value which identifies a specific fan tray in the chassis.

         This object was made obsolete in release 15.0."
    ::= { tmnxChassisFanEntry 1 }

tmnxChassisFanOperStatus         OBJECT-TYPE
    SYNTAX      TmnxDeviceState
    MAX-ACCESS  read-only
    STATUS      obsolete
    DESCRIPTION
        "Current status of the Fan tray.

         This object was made obsolete in release 15.0."
    ::= { tmnxChassisFanEntry 2 }

tmnxChassisFanSpeed              OBJECT-TYPE
    SYNTAX      INTEGER {
        notApplicable (0),
        unknown       (1),
        halfSpeed     (2),
        fullSpeed     (3)
    }
    MAX-ACCESS  read-only
    STATUS      obsolete
    DESCRIPTION
        "The value of tmnxChassisFanSpeed indicates if the fans in this fan
         tray are running at 'halfSpeed' or 'fullSpeed'.

         This object was made obsolete in release 15.0."
    ::= { tmnxChassisFanEntry 3 }

tmnxChassisFanRevision           OBJECT-TYPE
    SYNTAX      INTEGER {
        unknown (0),
        fan1    (1),
        hfFan2  (2)
    }
    MAX-ACCESS  read-only
    STATUS      obsolete
    DESCRIPTION
        "The value of tmnxChassisFanRevision indicates the fan tray revision.
         fan1   - represents the original fan tray.
         hfFan2 - represents the high-flow fan tray; second revision.

         This object was made obsolete in release 15.0."
    ::= { tmnxChassisFanEntry 4 }

tmnxChassisFanSpeedPercent       OBJECT-TYPE
    SYNTAX      Unsigned32 (0..100)
    UNITS       "percent"
    MAX-ACCESS  read-only
    STATUS      obsolete
    DESCRIPTION
        "The value of tmnxChassisFanSpeedPercent indicates the speed of the fan
         as a percentage of maximum speed.

         This object was made obsolete in release 15.0."
    ::= { tmnxChassisFanEntry 6 }

tmnxChassisPowerSupplyTable      OBJECT-TYPE
    SYNTAX      SEQUENCE OF TmnxChassisPowerSupplyEntry
    MAX-ACCESS  not-accessible
    STATUS      obsolete
    DESCRIPTION
        "This table contains information about power supply trays, also known
         as PEMs (Power Entry Modules).

         This table was made obsolete in release 15.0."
    ::= { tmnxChassisObjs 5 }

tmnxChassisPowerSupplyEntry      OBJECT-TYPE
    SYNTAX      TmnxChassisPowerSupplyEntry
    MAX-ACCESS  not-accessible
    STATUS      obsolete
    DESCRIPTION
        "Contains information regarding a power supply tray.

         This entry was made obsolete in release 15.0."
    INDEX       {
        tmnxChassisIndex,
        tmnxChassisPowerSupplyId
    }
    ::= { tmnxChassisPowerSupplyTable 1 }

TmnxChassisPowerSupplyEntry      ::= SEQUENCE
{
    tmnxChassisPowerSupplyId         Unsigned32,
    tmnxChassisPowerSupplyACStatus   TmnxDeviceState,
    tmnxChassisPowerSupplyDCStatus   TmnxDeviceState,
    tmnxChassisPowerSupplyTempStatus TmnxDeviceState,
    tmnxChassisPowerSupplyTempThreshold Integer32,
    tmnxChassisPowerSupply1Status    TmnxDeviceState,
    tmnxChassisPowerSupply2Status    TmnxDeviceState,
    tmnxChassisPowerSupplyAssignedType TmnxPowerSupAssignType,
    tmnxChassisPowerSupplyInputStatus TmnxDeviceState,
    tmnxChassisPowerSupplyOutputStatus TmnxDeviceState,
    tmnxChassisPowerSupplyPemType    TmnxChassisPemType,
    tmnxChassisPowerSupplyPemACRect  BITS,
    tmnxChassisPowerSupplyInFeedDown BITS,
    tmnxChassisPowerSupplyFanDir     INTEGER
}

tmnxChassisPowerSupplyId         OBJECT-TYPE
    SYNTAX      Unsigned32 (1..31)
    MAX-ACCESS  not-accessible
    STATUS      obsolete
    DESCRIPTION
        "The unique identifier index for a power supply tray in the chassis.

         This object was made obsolete in release 15.0."
    ::= { tmnxChassisPowerSupplyEntry 1 }

tmnxChassisPowerSupplyACStatus   OBJECT-TYPE
    SYNTAX      TmnxDeviceState
    MAX-ACCESS  read-only
    STATUS      obsolete
    DESCRIPTION
        "If the value of tmnxChassisPowerSupplyACStatus is 'deviceStateOk',
         the input AC voltage is within range.  If the value is
         'deviceStateFailed', an AC voltage out of range condition has been
         detected. A value of 'deviceNotEquipped' indicates that the AC
         power supply is not present.

         This object was made obsolete in release 15.0."
    ::= { tmnxChassisPowerSupplyEntry 2 }

tmnxChassisPowerSupplyDCStatus   OBJECT-TYPE
    SYNTAX      TmnxDeviceState
    MAX-ACCESS  read-only
    STATUS      obsolete
    DESCRIPTION
        "If the value of tmnxChassisPowerSupplyDCStatus is 'deviceStateOk',
         the output DC voltage is within range.  If the value is
         'deviceStateFailed', a DC voltage out of range condition has been
         detected. A value of 'deviceNotEquipped' indicates that the power
         supply is not present or the equipped power supply does not support the
         reporting of this status.

         This object was made obsolete in release 15.0."
    ::= { tmnxChassisPowerSupplyEntry 3 }

tmnxChassisPowerSupplyTempStatus OBJECT-TYPE
    SYNTAX      TmnxDeviceState
    MAX-ACCESS  read-only
    STATUS      obsolete
    DESCRIPTION
        "If the value of tmnxChassisPowerSupplyTempStatus is 'deviceStateOk',
         the current temperature is within acceptable range. If the value is
         'deviceStateFailed', a temperature too high condition has been
         detected.

         This object was made obsolete in release 15.0."
    ::= { tmnxChassisPowerSupplyEntry 4 }

tmnxChassisPowerSupplyTempThreshold OBJECT-TYPE
    SYNTAX      Integer32
    UNITS       "degrees celsius"
    MAX-ACCESS  read-only
    STATUS      obsolete
    DESCRIPTION
        "The temperature threshold for this power supply tray in degrees
         celsius.  When the temperature raises above
         tmnxChassisPowerSupplyTempThreshold, a 'temperature too high'
         event will be generated.

         This object was made obsolete in release 15.0."
    ::= { tmnxChassisPowerSupplyEntry 5 }

tmnxChassisPowerSupply1Status    OBJECT-TYPE
    SYNTAX      TmnxDeviceState
    MAX-ACCESS  read-only
    STATUS      obsolete
    DESCRIPTION
        "The overall status of an equipped power supply. For AC multiple power
         supplies, this represents the overall status of the first power supply
         in the tray (or shelf). For any other type, this represents the
         overall status of the power supply. If tmnxChassisPowerSupply1Status
         is 'deviceStateOk', then all monitored statuses are 'deviceStateOk'. A
         value of 'deviceStateFailed' represents a condition where at least one
         monitored status is in a failed state.

         This object was made obsolete in release 15.0."
    ::= { tmnxChassisPowerSupplyEntry 6 }

tmnxChassisPowerSupply2Status    OBJECT-TYPE
    SYNTAX      TmnxDeviceState
    MAX-ACCESS  read-only
    STATUS      obsolete
    DESCRIPTION
        "The overall status of an equipped power supply. For AC multiple power
         supplies, this represents the overall status of the second power
         supply in the tray (or shelf). For any other type, this field is
         unused and set to 'deviceNotEquipped'. If
         tmnxChassisPowerSupply2Status is 'deviceStateOk', then all monitored
         statuses are 'deviceStateOk'. A value of 'deviceStateFailed'
         represents a condition where at least one monitored status is in a
         failed state.

         This object was made obsolete in release 15.0."
    ::= { tmnxChassisPowerSupplyEntry 7 }

tmnxChassisPowerSupplyAssignedType OBJECT-TYPE
    SYNTAX      TmnxPowerSupAssignType
    MAX-ACCESS  read-create
    STATUS      obsolete
    DESCRIPTION
        "tmnxChassisPowerSupplyAssignedType configures the type of power supply
         for a platform. Based on the value assigned to this object, various
         power supply monitoring signals will be interpreted. For example, if a
         platform is provisioned to use DC power supplies, then the signal that
         indicates an AC power supply is missing can be ignored. The
         configuration of this object away from 'default (4)' is required for
         proper generation of traps and LED management.

         This object was made obsolete in release 15.0."
    DEFVAL      { default }
    ::= { tmnxChassisPowerSupplyEntry 8 }

tmnxChassisPowerSupplyInputStatus OBJECT-TYPE
    SYNTAX      TmnxDeviceState
    MAX-ACCESS  read-only
    STATUS      obsolete
    DESCRIPTION
        "If the value of tmnxChassisPowerSupplyInputStatus is 'deviceStateOk',
         the input voltage of the power supply is within range.  If the value
         is 'deviceStateFailed', an input voltage out of range condition has
         been detected. A value of 'deviceNotEquipped' indicates that the power
         supply is not present.

         This object was made obsolete in release 15.0."
    ::= { tmnxChassisPowerSupplyEntry 9 }

tmnxChassisPowerSupplyOutputStatus OBJECT-TYPE
    SYNTAX      TmnxDeviceState
    MAX-ACCESS  read-only
    STATUS      obsolete
    DESCRIPTION
        "If the value of tmnxChassisPowerSupplyOutputStatus is 'deviceStateOk',
         the output voltage of the power supply is within range.  If the value
         is 'deviceStateFailed', an output voltage out of range condition has
         been detected. A value of 'deviceNotEquipped' indicates that the power
         supply is not present.

         This object was made obsolete in release 15.0."
    ::= { tmnxChassisPowerSupplyEntry 10 }

tmnxChassisPowerSupplyPemType    OBJECT-TYPE
    SYNTAX      TmnxChassisPemType
    MAX-ACCESS  read-only
    STATUS      obsolete
    DESCRIPTION
        "The tmnxChassisPowerSupplyPemType indicates the Power Entry Module
         (PEM) type installed in the PEM slot.

         This object was made obsolete in release 15.0."
    ::= { tmnxChassisPowerSupplyEntry 11 }

tmnxChassisPowerSupplyPemACRect  OBJECT-TYPE
    SYNTAX      BITS {
        acRect1 (0),
        acRect2 (1)
    }
    MAX-ACCESS  read-only
    STATUS      obsolete
    DESCRIPTION
        "The value of tmnxChassisPowerSupplyPemACRect indicates which Power
         Entry Module AC rectifiers installed in the PEM slot are in a failed
         state or are missing.

         acRect1 (0) : The 1st PEM AC rectifier has failed or is missing.
         acRect2 (1) : The 2nd PEM AC rectifier has failed or is missing.

         This object was made obsolete in release 15.0."
    ::= { tmnxChassisPowerSupplyEntry 12 }

tmnxChassisPowerSupplyInFeedDown OBJECT-TYPE
    SYNTAX      BITS {
        inputFeedA (0),
        inputFeedB (1)
    }
    MAX-ACCESS  read-only
    STATUS      obsolete
    DESCRIPTION
        "The value of tmnxChassisPowerSupplyInFeedDown indicates which input
         feeds are not supplying power.

         inputFeedA (0) : Input feed A is not supplying power.
         inputFeedB (1) : Input feed B is not supplying power.

         This object was made obsolete in release 15.0."
    ::= { tmnxChassisPowerSupplyEntry 13 }

tmnxChassisPowerSupplyFanDir     OBJECT-TYPE
    SYNTAX      INTEGER {
        unknown     (0),
        frontToBack (1),
        backToFront (2)
    }
    MAX-ACCESS  read-only
    STATUS      obsolete
    DESCRIPTION
        "The value of tmnxChassisPowerSupplyFanDir indicates if the fan
         direction is 'frontToBack' or 'backToFront'.

         This object was made obsolete in release 15.0."
    ::= { tmnxChassisPowerSupplyEntry 14 }

tmnxChassisTypeTable             OBJECT-TYPE
    SYNTAX      SEQUENCE OF TmnxChassisTypeEntry
    MAX-ACCESS  not-accessible
    STATUS      current
    DESCRIPTION
        "The chassis type table has an entry for each chassis model supported
         by the platform. Some example chassis types are: '7750 SR-12', '7950
         XRS-20'."
    ::= { tmnxChassisObjs 6 }

tmnxChassisTypeEntry             OBJECT-TYPE
    SYNTAX      TmnxChassisTypeEntry
    MAX-ACCESS  not-accessible
    STATUS      current
    DESCRIPTION
        "Each row entry represents an Nokia SROS series Chassis
         model.  Rows in this table are created by the agent at initialization
         and cannot be created or destroyed by SNMP Get or Set requests."
    INDEX       { tmnxChassisTypeIndex }
    ::= { tmnxChassisTypeTable 1 }

TmnxChassisTypeEntry             ::= SEQUENCE
{
    tmnxChassisTypeIndex             TmnxChassisType,
    tmnxChassisTypeName              TNamedItemOrEmpty,
    tmnxChassisTypeDescription       TItemDescription,
    tmnxChassisTypeStatus            TruthValue
}

tmnxChassisTypeIndex             OBJECT-TYPE
    SYNTAX      TmnxChassisType
    MAX-ACCESS  not-accessible
    STATUS      current
    DESCRIPTION
        "The unique index value which identifies this type of Nokia SROS series
         chassis model."
    ::= { tmnxChassisTypeEntry 1 }

tmnxChassisTypeName              OBJECT-TYPE
    SYNTAX      TNamedItemOrEmpty
    MAX-ACCESS  read-only
    STATUS      current
    DESCRIPTION
        "The administrative name that identifies this type of Nokia
         SROS series chassis model.  This name string may be used in
         CLI commands to specify a particular chassis model type."
    ::= { tmnxChassisTypeEntry 2 }

tmnxChassisTypeDescription       OBJECT-TYPE
    SYNTAX      TItemDescription
    MAX-ACCESS  read-only
    STATUS      current
    DESCRIPTION
        "A detailed description of this Nokia SROS series chassis model."
    ::= { tmnxChassisTypeEntry 3 }

tmnxChassisTypeStatus            OBJECT-TYPE
    SYNTAX      TruthValue
    MAX-ACCESS  read-only
    STATUS      current
    DESCRIPTION
        "When tmnxChassisTypeStatus has a value of 'true' it indicates that
         this chassis model is supported in this revision of the management
         software.  When it has a value of 'false' there is no support."
    ::= { tmnxChassisTypeEntry 4 }

tmnxHwLastChange                 OBJECT-TYPE
    SYNTAX      TimeStamp
    MAX-ACCESS  read-only
    STATUS      current
    DESCRIPTION
        "The value of sysUpTime when the tmnxHwTable was last changed."
    ::= { tmnxChassisObjs 7 }

tmnxHwTable                      OBJECT-TYPE
    SYNTAX      SEQUENCE OF TmnxHwEntry
    MAX-ACCESS  not-accessible
    STATUS      current
    DESCRIPTION
        "The tmnxHwTable has an entry for each managed hardware component
         in the Nokia SROS series system's chassis.  Examples of
         these hardware component types are IOM, Fabric, and CPM cards,
         MCM and CCM, and MDA modules.  Similar information for physical ports
         is in the tmnxPortObjs."
    ::= { tmnxChassisObjs 8 }

tmnxHwEntry                      OBJECT-TYPE
    SYNTAX      TmnxHwEntry
    MAX-ACCESS  not-accessible
    STATUS      current
    DESCRIPTION
        "Each row entry represents an Nokia SROS series manufactured
         hardware component.  Entries cannot be created and deleted via
         SNMP SET operations.  When an entry is created in one of the
         card tables, IOM, CPM, Fabric or MDA, a tmnxHwEntry is created
         for the common hardware management information for that card
         in that chassis.  When the card  is removed from the chassis,
         its corresponding tmnxHwEntry is deleted.

         The tmnxHwIndex is bitmapped. The tmnxPhysChassisClass is used to
         indicate a sub-class of a TmnxHwClass type. A value of 0 instead of
         'routerChassis (3)' is used to represent router chassis:

         | 32       25 | 24                17 | 16        9 | 8         1 |
         +-------------+----------------------+-------------+-------------+
         | TmnxHwClass | TmnxPhysChassisClass |     Slot    |     number  |
         +-------------+----------------------+-------------+-------------+

         The Slot field is only used for components on cards in slots. It is
         zero for all others.

         The number field starts from 1 and indicates which component. E.g.
         Power supply 1 or 2."
    INDEX       {
        tmnxChassisIndex,
        tmnxHwIndex
    }
    ::= { tmnxHwTable 1 }

TmnxHwEntry                      ::= SEQUENCE
{
    tmnxHwIndex                      TmnxHwIndex,
    tmnxHwID                         RowPointer,
    tmnxHwMfgString                  SnmpAdminString,
    tmnxHwMfgBoardNumber             OCTET STRING,
    tmnxHwSerialNumber               SnmpAdminString,
    tmnxHwManufactureDate            SnmpAdminString,
    tmnxHwClass                      TmnxHwClass,
    tmnxHwName                       TNamedItemOrEmpty,
    tmnxHwAlias                      TNamedItemOrEmpty,
    tmnxHwAssetID                    SnmpAdminString,
    tmnxHwCLEI                       SnmpAdminString,
    tmnxHwIsFRU                      TruthValue,
    tmnxHwContainedIn                Integer32,
    tmnxHwParentRelPos               Integer32,
    tmnxHwAdminState                 INTEGER,
    tmnxHwOperState                  INTEGER,
    tmnxHwTempSensor                 TruthValue,
    tmnxHwTemperature                Integer32,
    tmnxHwTempThreshold              Integer32,
    tmnxHwBootCodeVersion            DisplayString,
    tmnxHwSoftwareCodeVersion        DisplayString,
    tmnxHwSwLastBoot                 DateAndTime,
    tmnxHwSwState                    INTEGER,
    tmnxHwAlarmState                 TmnxAlarmState,
    tmnxHwLastAlarmEvent             RowPointer,
    tmnxHwClearAlarms                TmnxActionType,
    tmnxHwSwImageSource              INTEGER,
    tmnxHwMfgDeviations              SnmpAdminString,
    tmnxHwBaseMacAddress             MacAddress,
    tmnxHwFailureReason              DisplayString,
    tmnxHwEquippedPlatform           INTEGER,
    tmnxHwMfgAssemblyNumber          SnmpAdminString,
    tmnxHwFirmwareCodeVersion        DisplayString,
    tmnxHwPowerZone                  Unsigned32,
    tmnxHwFirmwareRevisionStatus     INTEGER
}

tmnxHwIndex                      OBJECT-TYPE
    SYNTAX      TmnxHwIndex
    MAX-ACCESS  not-accessible
    STATUS      current
    DESCRIPTION
        "The value of tmnxHwIndex is a unique index that identifies common
         management information for Nokia SROS series manufactured hardware
         components within the specified chassis."
    ::= { tmnxHwEntry 1 }

tmnxHwID                         OBJECT-TYPE
    SYNTAX      RowPointer
    MAX-ACCESS  read-only
    STATUS      current
    DESCRIPTION
        "The value of tmnxHwID is an object identifier that points to the table
         and row entry with additional management information specific to this
         hardware component's class. If there is no additional information
         specific to such component then the the tmnxHwID is set to 0.0."
    ::= { tmnxHwEntry 2 }

tmnxHwMfgString                  OBJECT-TYPE
    SYNTAX      SnmpAdminString (SIZE (0..253))
    MAX-ACCESS  read-only
    STATUS      obsolete
    DESCRIPTION
        "The tmnxHwMfgString contains unspecified Nokia SROS series
         manufacturing information and includes the Nokia vendor information.

         This object was made obsolete in release 11.0."
    ::= { tmnxHwEntry 3 }

tmnxHwMfgBoardNumber             OBJECT-TYPE
    SYNTAX      OCTET STRING (SIZE (0..32))
    MAX-ACCESS  read-only
    STATUS      current
    DESCRIPTION
        "The tmnxHwMfgBoardNumber contains the part number information."
    ::= { tmnxHwEntry 4 }

tmnxHwSerialNumber               OBJECT-TYPE
    SYNTAX      SnmpAdminString (SIZE (0..32))
    MAX-ACCESS  read-only
    STATUS      current
    DESCRIPTION
        "The unique Nokia SROS series serial number of the hardware component."
    ::= { tmnxHwEntry 5 }

tmnxHwManufactureDate            OBJECT-TYPE
    SYNTAX      SnmpAdminString (SIZE (8))
    MAX-ACCESS  read-only
    STATUS      current
    DESCRIPTION
        "The manufacturing date of the hardware component in 'mmddyyyy' ascii
         format."
    ::= { tmnxHwEntry 6 }

tmnxHwClass                      OBJECT-TYPE
    SYNTAX      TmnxHwClass
    MAX-ACCESS  read-only
    STATUS      current
    DESCRIPTION
        "The value of tmnxHwClass  indicates the general hardware type of this
         component.  If no appropriate enumeration exists for this hardware
         identify this hardware component then the value 'unknown (2)' is
         used."
    ::= { tmnxHwEntry 7 }

tmnxHwName                       OBJECT-TYPE
    SYNTAX      TNamedItemOrEmpty
    MAX-ACCESS  read-only
    STATUS      current
    DESCRIPTION
        "The value of tmnxHwName is the name of the component as assigned by
         the system software itself and is suitable for use in CLI commands.
         This may be a text name such as 'console' or a port ID such as '2/2'.

         If there is no predefined name then a zero length string is returned.

         Note that the value of tmnxHwName for two component entries will
         be the same if the CLI does not distinguish between them, e.g.  the
         chassis slot-1 and the card in slot-1."
    ::= { tmnxHwEntry 8 }

tmnxHwAlias                      OBJECT-TYPE
    SYNTAX      TNamedItemOrEmpty
    MAX-ACCESS  read-write
    STATUS      current
    DESCRIPTION
        "The value of tmnxHwAlias is the administrative name assigned to this
         hardware component by the CLI user or network manager.  It is saved
         across re-initializations and reboots of the system.

         The object tmnxHwAlias is not supported on rows where the tmnxHwClass
         is set to 'flashDiskModule (12)'. Attempts to set the tmnxHwAlias
         object on rows where it is not supported will result in an
         inconsistentValue error."
    DEFVAL      { "" }
    ::= { tmnxHwEntry 9 }

tmnxHwAssetID                    OBJECT-TYPE
    SYNTAX      SnmpAdminString
    MAX-ACCESS  read-write
    STATUS      current
    DESCRIPTION
        "The value of tmnxHwAssetID is an administratively assigned asset
         tracking identifier for this hardware component.  It is saved across
         re-initializations and reboots of the system.  If no asset tracking
         information is associated with this hardware component, a zero-length
         string is returned to an SNMP get request.

         The object tmnxHwAssetID is not supported on rows where the
         tmnxHwClass is set to 'flashDiskModule (12)'. Attempts to set the
         tmnxHwAssetID object on rows where it is not supported will result in
         an inconsistentValue error.

         Some hardware components do not have asset tracking identifiers.
         Components for which tmnxHwIsFRU has a value of 'false' do not
         need their own unique asset tracking identifier.  In this case, the
         agent denies write access to this object and returns a zero-length
         string to an SNMP get request."
    DEFVAL      { "" }
    ::= { tmnxHwEntry 10 }

tmnxHwCLEI                       OBJECT-TYPE
    SYNTAX      SnmpAdminString (SIZE (10))
    MAX-ACCESS  read-only
    STATUS      current
    DESCRIPTION
        "The Common Language Equipment Identifier, CLEI, code is a unique
         10-character identifier, that is fixed by the manufacturer.  It
         consists of ten alphanumeric characters.  The first seven characters
         present a concise summary of an equipment entity's circuit or
         transport capabilities, e.g., functional, electrical, bandwidth, etc.
         CLEI codes for plug-in or portable equipment with the same first
         seven characters (CLEI-7) are considered bidirectionally
         interchangeable and group under a G level record.  Most licensees
         plug-in inventories and records are controlled at the group level.
         The eighth character denotes the reference source used for coding
         the item, and the last two characters denote manufacturing vintage
         or version, and other complementary information.

         A ten-character CLEI code that is developed for a specific piece of
         equipment is unique within the CLEI code universe and is used in A
         level records; the code is not assigned to any other equipment piece.
         Equipment is coded to a first or major application. When the same
         equipment is usable in another application or system, it is not
         recorded nor are additional codes developed for that purpose."
    REFERENCE
        "Bellcore (Telcordia Technologies) GR-485."
    ::= { tmnxHwEntry 11 }

tmnxHwIsFRU                      OBJECT-TYPE
    SYNTAX      TruthValue
    MAX-ACCESS  read-only
    STATUS      current
    DESCRIPTION
        "The value of tmnxHwIsFRU indicates whether or not this hardware
         component is a Field Replaceable Unit (FRU) or not.  Those components
         that are permanently contained within a FRU have a value of 'false'."
    ::= { tmnxHwEntry 12 }

tmnxHwContainedIn                OBJECT-TYPE
    SYNTAX      Integer32 (0..2147483647)
    MAX-ACCESS  read-only
    STATUS      current
    DESCRIPTION
        "The value of tmnxHwContainedIn is the tmnxHwIndex value for the row
         entry of the hardware component that contains this component. A value
         of zero indicates that this component is not contained in any other
         component."
    ::= { tmnxHwEntry 13 }

tmnxHwParentRelPos               OBJECT-TYPE
    SYNTAX      Integer32 (-1..2147483647)
    MAX-ACCESS  read-only
    STATUS      current
    DESCRIPTION
        "The value of tmnxHwParentRelPos indicates the relative position of
         this hardware component among all its 'sibling' components.  A sibling
         component shares the same instance values for tmnxHwContainedIn and
         tmnxHwClass objects.

         If the associated value of tmnxHwContainedIn is zero, then the value
         -1 is returned."
    ::= { tmnxHwEntry 14 }

tmnxHwAdminState                 OBJECT-TYPE
    SYNTAX      INTEGER {
        noop          (1),
        inService     (2),
        outOfService  (3),
        diagnose      (4),
        operateSwitch (5)
    }
    MAX-ACCESS  read-write
    STATUS      current
    DESCRIPTION
        "The desired administrative status of this hardware component.  Write
         access will be denied for those components that do not have
         administrative status.  An attempt to set tmnxHwAdminState to
         'operateSwitch (5)' will fail if the hardware component is not part
         of a redundant pair.  Some examples of redundant hardware are the
         CPM cards and fabric cards."
    DEFVAL      { noop }
    ::= { tmnxHwEntry 15 }

tmnxHwOperState                  OBJECT-TYPE
    SYNTAX      INTEGER {
        unknown            (1),
        inService          (2),
        outOfService       (3),
        diagnosing         (4),
        failed             (5),
        booting            (6),
        empty              (7),
        provisioned        (8),
        unprovisioned      (9),
        upgrade            (10),
        downgrade          (11),
        inServiceUpgrade   (12),
        inServiceDowngrade (13),
        resetPending       (14),
        softReset          (15),
        preExtension       (16)
    }
    MAX-ACCESS  read-only
    STATUS      current
    DESCRIPTION
        "The actual operational status of this hardware component.

         unknown (1)                Status cannot be determined

         inService (2)              Online - If tmnxHwClass has a value of
                                    'ioModule (8)' or 'cpmModule (9), the
                                    card is present, booted, configured,
                                    and running.

         outOfService (3)           Ready - The hardware component is OK
                                    but is down because tmnxHwAdminState has
                                    a value of 'outOfService (3)'.

         diagnosing (4)             Not implemented.

         failed (5)                 This hardware component has failed.  The
                                    value of tmnxHwFailureReason indicates
                                    the type of failure.  If tmnxHwClass has
                                    a value of 'ioModule(8)' or 'cpmModule(9)',
                                    there is a card in the slot but it has
                                    failed.

         booting (6)                A card is in the transitional startup state.

         empty (7)                  There is no card in the slot and it has
                                    not been pre-configured.

         provisioned (8)            There is no card in the slot but it has
                                    been pre-configured.

         unprovisioned (9)          There is a card in the slot but it is not
                                    configured.

         upgrade (10)               Card software version is compatible with
                                    and newer than that running on the current
                                    active CPM.

         downgrade (11)             Card software version is compatible with
                                    and older than that running on the current
                                    active CPM.

         inServiceUpgrade (12)      Card is inService and the card software
                                    version is compatible with and newer than
                                    that running on the current active CPM.
                                    This state applies only to a standby CPM
                                    card. This enumeration is no longer
                                    supported as of release 5.0.

         inServiceDowngrade (13)    Card is inService and the card software
                                    is compatible with and older than that
                                    running on the current active CPM.  This
                                    state applies only to a standby CPM card.
                                    This enumeration is no longer supported
                                    as of release 5.0.

         resetPending (14)          Card is awaiting reset following an
                                    upgrade or downgrade activity switch.
                                    The card software version is upgrade
                                    or downgrade compatible but will be reset
                                    in order to update it to match the active
                                    CPM software.  The value of
                                    tmnxChassisUpdateWaitTime indicates the
                                    how long the system will wait following
                                    an upgrade or downgrade activity switch
                                    before it resets IOM cards.  This state
                                    applies only to IOM cards. This
                                    enumeration is no longer supported as of
                                    release 5.0.

         softReset (15)             Card is performing a soft reset. The
                                    data path is active, but control path
                                    transitional changes are suspended until
                                    the card leaves this state.

         preExtension (16)           State assigned to an unprovisioned hardware
                                    component associated with, or contained in,
                                    an (potentially non-existant) extension
                                    chassis in a 7950 XRS system that is
                                    operating in XRS-20 mode (i.e.
                                    tmnxChassisOperTopology is 'standalone(1)').
                                    The extension chassis and/or hardware
                                    component may or may not be physically
                                    present and connected to the master
                                    chassis. The system does not monitor
                                    extension chassis equipment when
                                    tmnxChassisOperTopology is 'standalone(1)'.
                                    In this case, for unprovisioned extension
                                    chassis equipment, a value of
                                    'preExtension(16)' is assigned.
                                   "
    ::= { tmnxHwEntry 16 }

tmnxHwTempSensor                 OBJECT-TYPE
    SYNTAX      TruthValue
    MAX-ACCESS  read-only
    STATUS      current
    DESCRIPTION
        "The value of tmnxHwTempSensor indicates whether or not this hardware
         component contains a temperature sensor."
    ::= { tmnxHwEntry 17 }

tmnxHwTemperature                OBJECT-TYPE
    SYNTAX      Integer32
    UNITS       "degrees celsius"
    MAX-ACCESS  read-only
    STATUS      current
    DESCRIPTION
        "The current temperature reading in degrees celsius from this hardware
         component's temperature sensor.  If this component does not contain
         a temperature sensor, then the value -1 is returned."
    ::= { tmnxHwEntry 18 }

tmnxHwTempThreshold              OBJECT-TYPE
    SYNTAX      Integer32
    UNITS       "degrees celsius"
    MAX-ACCESS  read-only
    STATUS      current
    DESCRIPTION
        "The temperature threshold for this hardware component in degrees
         celsius.  When the value of tmnxHwTemperature raises above
         tmnxHwTempThreshold, a 'temperature too high' event will
         be generated."
    ::= { tmnxHwEntry 19 }

tmnxHwBootCodeVersion            OBJECT-TYPE
    SYNTAX      DisplayString
    MAX-ACCESS  read-only
    STATUS      current
    DESCRIPTION
        "The version number of boot eprom on the card in this slot.

         If no specific software program is associated with this hardware
         component then this object will contain a zero length string."
    ::= { tmnxHwEntry 20 }

tmnxHwSoftwareCodeVersion        OBJECT-TYPE
    SYNTAX      DisplayString
    MAX-ACCESS  read-only
    STATUS      current
    DESCRIPTION
        "The software product release version number for the software image
         currently running on this IOM or CPM card.

         If no specific software program is associated with this hardware
         component then this object will contain a zero length string."
    ::= { tmnxHwEntry 21 }

tmnxHwSwLastBoot                 OBJECT-TYPE
    SYNTAX      DateAndTime
    MAX-ACCESS  read-only
    STATUS      current
    DESCRIPTION
        "The date and time the software running on this IOM or CPM card was
         last rebooted.

         If this row entry represents a standby CPM card, the date and time
         indicated is when the standby completed its initial synchronization
         process and became ready to take over in case the active card fails or
         a manual switchover command is issued."
    ::= { tmnxHwEntry 22 }

tmnxHwSwState                    OBJECT-TYPE
    SYNTAX      INTEGER {
        unknown       (0),
        hwFailure     (1),
        swFailure     (2),
        hwInitting    (3),
        swDownloading (4),
        swInitting    (5),
        swInitted     (6),
        swRunning     (7)
    }
    MAX-ACCESS  read-only
    STATUS      obsolete
    DESCRIPTION
        "The state of the software running on this IOM or CPM card.

         The tmnxHwSwState object is obsolete.  The Nokia 7x50 platform
         cannot distinguish software status separate from the hardware
         status.  Instead of using this object, additional operational
         states have been added to tmnxHwOperState.

         If no specific software program is associated with this hardware
         component then this object will contain a zero."
    ::= { tmnxHwEntry 23 }

tmnxHwAlarmState                 OBJECT-TYPE
    SYNTAX      TmnxAlarmState
    MAX-ACCESS  read-only
    STATUS      current
    DESCRIPTION
        "The value of tmnxHwAlarmState indicates the current alarm state for
         this hardware component."
    ::= { tmnxHwEntry 24 }

tmnxHwLastAlarmEvent             OBJECT-TYPE
    SYNTAX      RowPointer
    MAX-ACCESS  read-only
    STATUS      current
    DESCRIPTION
        "The value of tmnxHwLastAlarmEvent indicates the object name
         and instance value that points to the row entry in the ALARM-MIB
         containing the most recent alarm associated with this hardware
         component.  If tmnxHwAlarmState has a value of 'alarmCleared(2)', the
         most recent alarm event will be in the cleared alarm table.  If it has
         a value of 'alarmActive(1)', the most recent alarm event will be in
         the active alarm table.  If the value of tmnxHwLastAlarmEvent is
         '0.0', either no hardware component alarm events have occurred since
         the system was last booted, or the last hardware component alarm event
         has aged out and its entry is no longer available in the ALARM-MIB
         tables."
    ::= { tmnxHwEntry 25 }

tmnxHwClearAlarms                OBJECT-TYPE
    SYNTAX      TmnxActionType
    MAX-ACCESS  read-write
    STATUS      current
    DESCRIPTION
        "Setting this action variable causes all the active alarms associated
         with this hardware component to be moved from the ALARM-MIB
         nlmActiveAlarmTable to the nlmClearedAlarmTable.  This action button
         is primarily meant for use as a code development aid.  This object may
         be removed from the TIMETRA-CHASSIS-MIB before product release."
    DEFVAL      { notApplicable }
    ::= { tmnxHwEntry 26 }

tmnxHwSwImageSource              OBJECT-TYPE
    SYNTAX      INTEGER {
        unknown   (0),
        primary   (1),
        secondary (2),
        tertiary  (3)
    }
    MAX-ACCESS  read-only
    STATUS      current
    DESCRIPTION
        "The value of tmnxHwSwImageSource indicates the location in the Boot
         Options File (BOF) where the software image file was found when the
         system last rebooted."
    ::= { tmnxHwEntry 27 }

tmnxHwMfgDeviations              OBJECT-TYPE
    SYNTAX      SnmpAdminString
    MAX-ACCESS  read-only
    STATUS      current
    DESCRIPTION
        "tmnxHwMfgDeviations contains a record of changes done by the
         manufacturing to the hardware or software and which is outside the
         normal revision control process."
    ::= { tmnxHwEntry 28 }

tmnxHwBaseMacAddress             OBJECT-TYPE
    SYNTAX      MacAddress
    MAX-ACCESS  read-only
    STATUS      current
    DESCRIPTION
        "tmnxHwBaseMacAddress contains the base MAC address of the hardware
         component. It is applicable only if tmnxHwClass is of type 'chassis',
         'ioModule', 'cpmModule' or 'mdaModule'."
    ::= { tmnxHwEntry 29 }

tmnxHwFailureReason              OBJECT-TYPE
    SYNTAX      DisplayString
    MAX-ACCESS  read-only
    STATUS      current
    DESCRIPTION
        "tmnxHwFailureReason indicates the reason why a hardware component
         'failed' as indicated in tmnxHwOperState."
    ::= { tmnxHwEntry 30 }

tmnxHwEquippedPlatform           OBJECT-TYPE
    SYNTAX      INTEGER {
        pfUnknown (0),
        pf7750    (1),
        pf7450    (2),
        pf7710    (3),
        pf7950    (4)
    }
    MAX-ACCESS  read-only
    STATUS      current
    DESCRIPTION
        "The value of tmnxHwEquippedPlatform indicates the platform type
         of the installed hardware component, as read from the component's
         EEPROM.  For example, 'pf7750' is returned for an installed 7750
         iom3-xp.  pfUnknown is returned if the component's EEPROM is
         unreadable, or in the case of an empty slot."
    ::= { tmnxHwEntry 31 }

tmnxHwMfgAssemblyNumber          OBJECT-TYPE
    SYNTAX      SnmpAdminString (SIZE (0..32))
    MAX-ACCESS  read-only
    STATUS      current
    DESCRIPTION
        "The value of tmnxHwMfgAssemblyNumber may contain an assembly number
         which indicates manufacturing differences for a given part number."
    ::= { tmnxHwEntry 32 }

tmnxHwFirmwareCodeVersion        OBJECT-TYPE
    SYNTAX      DisplayString
    MAX-ACCESS  read-only
    STATUS      current
    DESCRIPTION
        "The software product release version number associated with the
         firmware version currently programmed on this card.

         If no specific software release is associated with this hardware
         component then this object will contain a zero length string."
    ::= { tmnxHwEntry 33 }

tmnxHwPowerZone                  OBJECT-TYPE
    SYNTAX      Unsigned32 (0..32)
    MAX-ACCESS  read-only
    STATUS      current
    DESCRIPTION
        "The value of tmnxHwPowerZone indicates the managed power-zone on an
         SROS series system that this device resides. Devices on differing
         power-zones are managed separately. That is, if power is restricted on
         one power-zone, higher priority devices may be forcefully powered off,
         while a power-zone without a power restriction may have low-priority
         devices boot up. This object maps the corresponding device with a row
         in the tmnxChassisPowerMgmtTable.

         A value of zero (0) indicates that this device does not use system
         power resources and thus does not reside in a power-zone."
    ::= { tmnxHwEntry 34 }

tmnxHwFirmwareRevisionStatus     OBJECT-TYPE
    SYNTAX      INTEGER {
        notApplicable        (0),
        acceptable           (1),
        notAcceptable        (2),
        upgradePending       (3),
        upgrading            (4),
        upgradeNextHardReset (5)
    }
    MAX-ACCESS  read-only
    STATUS      current
    DESCRIPTION
        "The value of tmnxHwFirmwareRevisionStatus indicates the firmware/FPGA
         revision status for the device. A device that does not support a
         firmware/FPGA revision status will always return 'notApplicable (0)'.

         The possible values of tmnxHwFirmwareRevisionStatus are:
             notApplicable (0)        - The device does not support this object
                                        or the device does support this object
                                        but the current firmware revision is
                                        not yet known (e.g. the device is
                                        currently initializing).

             acceptable (1)           - The device has a firmware revision that
                                        is acceptable with the current system
                                        configuration.

             notAcceptable (2)        - The device has a firmware revision that
                                        is not acceptable with the current
                                        system configuration.

             upgradePending (3)       - The device has a firmware revision that
                                        is not acceptable with the current
                                        system configuration; an upgrade will
                                        be issued on the device's firmware to
                                        bring it to an acceptable state.

             upgrading (4)            - The device's firmware is currently
                                        being upgraded to the latest revision
                                        acceptable with the current system
                                        configuration.

             upgradeNextHardReset (5) - The device's firmware is acceptable
                                        but a new revision is available and
                                        the card will be upgraded to this new
                                        revision on the next hard reset."
    ::= { tmnxHwEntry 35 }

tmnxHwContainsTable              OBJECT-TYPE
    SYNTAX      SEQUENCE OF TmnxHwContainsEntry
    MAX-ACCESS  not-accessible
    STATUS      current
    DESCRIPTION
        "The tmnxHwContainsTable shows the container/containee relationship
         between entries in the tmnxHwTable.  The hardware component
         containment tree can be constructed from information in the
         tmnxHwTable, but this table provides the information in a more
         convenient format for the manager system to use."
    ::= { tmnxChassisObjs 9 }

tmnxHwContainsEntry              OBJECT-TYPE
    SYNTAX      TmnxHwContainsEntry
    MAX-ACCESS  not-accessible
    STATUS      current
    DESCRIPTION
        "Each row entry represents a single container/containee relationship.
         Entries cannot be created and deleted via SNMP SET operations."
    INDEX       {
        tmnxHwIndex,
        tmnxHwContainedIndex
    }
    ::= { tmnxHwContainsTable 1 }

TmnxHwContainsEntry              ::= SEQUENCE
{ tmnxHwContainedIndex             TmnxHwIndex }

tmnxHwContainedIndex             OBJECT-TYPE
    SYNTAX      TmnxHwIndex
    MAX-ACCESS  read-only
    STATUS      current
    DESCRIPTION
        "The value of tmnxHwContainedIndex indicates the tmnxHwIndex for the
         contained hardware component."
    ::= { tmnxHwContainsEntry 1 }

tmnxCcmTable                     OBJECT-TYPE
    SYNTAX      SEQUENCE OF TmnxCcmEntry
    MAX-ACCESS  not-accessible
    STATUS      current
    DESCRIPTION
        "This table contains information about CCM."
    ::= { tmnxChassisObjs 10 }

tmnxCcmEntry                     OBJECT-TYPE
    SYNTAX      TmnxCcmEntry
    MAX-ACCESS  not-accessible
    STATUS      current
    DESCRIPTION
        "Contains information regarding a CCM."
    INDEX       {
        tmnxChassisIndex,
        tmnxCcmIndex
    }
    ::= { tmnxCcmTable 1 }

TmnxCcmEntry                     ::= SEQUENCE
{
    tmnxCcmIndex                     Unsigned32,
    tmnxCcmOperStatus                TmnxDeviceState,
    tmnxCcmHwIndex                   TmnxHwIndex,
    tmnxCcmEquippedType              TmnxCcmType
}

tmnxCcmIndex                     OBJECT-TYPE
    SYNTAX      Unsigned32 (1..8)
    MAX-ACCESS  not-accessible
    STATUS      current
    DESCRIPTION
        "The unique value which identifies a specific CCM instance in the
         chassis."
    ::= { tmnxCcmEntry 1 }

tmnxCcmOperStatus                OBJECT-TYPE
    SYNTAX      TmnxDeviceState
    MAX-ACCESS  read-only
    STATUS      current
    DESCRIPTION
        "Current status of the CCM."
    ::= { tmnxCcmEntry 2 }

tmnxCcmHwIndex                   OBJECT-TYPE
    SYNTAX      TmnxHwIndex
    MAX-ACCESS  read-only
    STATUS      current
    DESCRIPTION
        "The value of tmnxCcmHwIndex is the index into the tmnxHwTable for the
         row entry that represents the hardware component information for this
         CCM."
    ::= { tmnxCcmEntry 3 }

tmnxCcmEquippedType              OBJECT-TYPE
    SYNTAX      TmnxCcmType
    MAX-ACCESS  read-only
    STATUS      current
    DESCRIPTION
        "A bit-mask that identifies the CCM type that is physically
         inserted into this chassis.  There will not be more than one
         bit set at a time in tmnxCcmEquippedType."
    ::= { tmnxCcmEntry 4 }

tmnxCcmTypeTable                 OBJECT-TYPE
    SYNTAX      SEQUENCE OF TmnxCcmTypeEntry
    MAX-ACCESS  not-accessible
    STATUS      current
    DESCRIPTION
        "The card type table has an entry for each Nokia 7710 series Chassis
         Control Module (CCM) model."
    ::= { tmnxChassisObjs 11 }

tmnxCcmTypeEntry                 OBJECT-TYPE
    SYNTAX      TmnxCcmTypeEntry
    MAX-ACCESS  not-accessible
    STATUS      current
    DESCRIPTION
        "Each row entry represents an Nokia 7710 series CCM model. Rows in this
         table are created by the agent at initialization and cannot be created
         or destroyed by SNMP Get or Set requests."
    INDEX       { tmnxCcmTypeIndex }
    ::= { tmnxCcmTypeTable 1 }

TmnxCcmTypeEntry                 ::= SEQUENCE
{
    tmnxCcmTypeIndex                 TmnxCcmType,
    tmnxCcmTypeName                  TNamedItemOrEmpty,
    tmnxCcmTypeDescription           TItemDescription,
    tmnxCcmTypeStatus                TruthValue
}

tmnxCcmTypeIndex                 OBJECT-TYPE
    SYNTAX      TmnxCcmType
    MAX-ACCESS  not-accessible
    STATUS      current
    DESCRIPTION
        "The unique index value which identifies this type of Nokia 7710 series
         CCM model."
    ::= { tmnxCcmTypeEntry 1 }

tmnxCcmTypeName                  OBJECT-TYPE
    SYNTAX      TNamedItemOrEmpty
    MAX-ACCESS  read-only
    STATUS      current
    DESCRIPTION
        "The administrative name that identifies this type of Nokia
         7710 series CCM model.  This name string may be used in CLI
         commands to specify a particular card model type."
    ::= { tmnxCcmTypeEntry 2 }

tmnxCcmTypeDescription           OBJECT-TYPE
    SYNTAX      TItemDescription
    MAX-ACCESS  read-only
    STATUS      current
    DESCRIPTION
        "A detailed description of this Nokia 7710 series CCM model."
    ::= { tmnxCcmTypeEntry 3 }

tmnxCcmTypeStatus                OBJECT-TYPE
    SYNTAX      TruthValue
    MAX-ACCESS  read-only
    STATUS      current
    DESCRIPTION
        "When tmnxCcmTypeStatus has a value of 'true' it
         indicates that this CCM is supported in this revision of the
         management software.  When it has a value of 'false' there is no
         support."
    ::= { tmnxCcmTypeEntry 4 }

tmnxFanTrayComponentTable        OBJECT-TYPE
    SYNTAX      SEQUENCE OF TmnxFanTrayComponentEntry
    MAX-ACCESS  not-accessible
    STATUS      current
    DESCRIPTION
        "The Fan Tray Component table has an entry for every sub-component of a
         Fan Tray that has monitored states. Not all fan trays have monitored
         sub-components, in this case, this table will be empty for the given
         fan-tray."
    ::= { tmnxChassisObjs 12 }

tmnxFanTrayComponentEntry        OBJECT-TYPE
    SYNTAX      TmnxFanTrayComponentEntry
    MAX-ACCESS  not-accessible
    STATUS      current
    DESCRIPTION
        "Each row entry represents a fan tray component. Rows in this table are
         created by the agent at initialization and cannot be created or
         destroyed by SNMP Get or Set requests."
    INDEX       {
        tmnxChassisIndex,
        tmnxChassisFanIndex,
        tmnxFanTrayCompIndex
    }
    ::= { tmnxFanTrayComponentTable 1 }

TmnxFanTrayComponentEntry        ::= SEQUENCE
{
    tmnxFanTrayCompIndex             Unsigned32,
    tmnxFanTrayCompSpeed             Gauge32
}

tmnxFanTrayCompIndex             OBJECT-TYPE
    SYNTAX      Unsigned32
    MAX-ACCESS  not-accessible
    STATUS      current
    DESCRIPTION
        "The tmnxFanTrayCompIndex specifies an individual fan tray component."
    ::= { tmnxFanTrayComponentEntry 1 }

tmnxFanTrayCompSpeed             OBJECT-TYPE
    SYNTAX      Gauge32 (0..100)
    UNITS       "percent"
    MAX-ACCESS  read-only
    STATUS      current
    DESCRIPTION
        "The tmnxFanTrayCompSpeed indicates the current speed of the fan tray
         component."
    ::= { tmnxFanTrayComponentEntry 2 }

tmnxHwResourceTable              OBJECT-TYPE
    SYNTAX      SEQUENCE OF TmnxHwResourceEntry
    MAX-ACCESS  not-accessible
    STATUS      current
    DESCRIPTION
        "The tmnxHwResourceTable has an entry for each managed hardware
         component in the Nokia SROS series system's chassis that supports
         resource monitoring. Hardware components that do not support resource
         monitoring will not show up in this table.

         Rows in this table are created by the agent at initialization and
         cannot be created or destroyed by SNMP Get or Set requests."
    ::= { tmnxChassisObjs 13 }

tmnxHwResourceEntry              OBJECT-TYPE
    SYNTAX      TmnxHwResourceEntry
    MAX-ACCESS  not-accessible
    STATUS      current
    DESCRIPTION
        "Each tmnxHwResourceEntry row consists of the current resource levels
         for a particular managed hardware component."
    INDEX       {
        tmnxChassisIndex,
        tmnxHwIndex
    }
    ::= { tmnxHwResourceTable 1 }

TmnxHwResourceEntry              ::= SEQUENCE
{
    tmnxHwResourceCurrentVoltage     Integer32,
    tmnxHwResourcePeakVoltage        Integer32,
    tmnxHwResourcePeakVoltageTime    TimeStamp,
    tmnxHwResourceMinVoltage         Integer32,
    tmnxHwResourceMinVoltageTime     TimeStamp,
    tmnxHwResourceCurrentWattage     Integer32,
    tmnxHwResourcePeakWattage        Integer32,
    tmnxHwResourcePeakWattageTime    TimeStamp,
    tmnxHwResourceMinWattage         Integer32,
    tmnxHwResourceMinWattageTime     TimeStamp,
    tmnxHwResourceCurrentAmperage    Integer32,
    tmnxHwResourcePeakAmperage       Integer32,
    tmnxHwResourcePeakAmperageTime   TimeStamp,
    tmnxHwResourceMinAmperage        Integer32,
    tmnxHwResourceMinAmperageTime    TimeStamp,
    tmnxHwResourceMaxRequiredWattage Integer32
}

tmnxHwResourceCurrentVoltage     OBJECT-TYPE
    SYNTAX      Integer32
    MAX-ACCESS  read-only
    STATUS      current
    DESCRIPTION
        "The value of tmnxHwResourceCurrentVoltage indicates the current
         voltage use of the managed hardware component in milli-Volts (mV)."
    ::= { tmnxHwResourceEntry 1 }

tmnxHwResourcePeakVoltage        OBJECT-TYPE
    SYNTAX      Integer32
    MAX-ACCESS  read-only
    STATUS      current
    DESCRIPTION
        "The value of tmnxHwResourcePeakVoltage indicates the peak voltage use
         of the managed hardware component in milli-Volts (mV) last recorded at
         the time indicated by tmnxHwResourcePeakVoltageTime."
    ::= { tmnxHwResourceEntry 2 }

tmnxHwResourcePeakVoltageTime    OBJECT-TYPE
    SYNTAX      TimeStamp
    MAX-ACCESS  read-only
    STATUS      current
    DESCRIPTION
        "The value of tmnxHwResourcePeakVoltageTime indicates the time, since
         system initialization, that tmnxHwResourcePeakVoltage was last
         updated."
    ::= { tmnxHwResourceEntry 3 }

tmnxHwResourceMinVoltage         OBJECT-TYPE
    SYNTAX      Integer32
    MAX-ACCESS  read-only
    STATUS      current
    DESCRIPTION
        "The value of tmnxHwResourceMinVoltage indicates the lowest voltage use
         of the managed hardware component in milli-Volts (mV) last recorded at
         the time indicated by tmnxHwResourceMinVoltageTime."
    ::= { tmnxHwResourceEntry 4 }

tmnxHwResourceMinVoltageTime     OBJECT-TYPE
    SYNTAX      TimeStamp
    MAX-ACCESS  read-only
    STATUS      current
    DESCRIPTION
        "The value of tmnxHwResourceMinVoltageTime indicates the time, since
         system initialization, that tmnxHwResourceMinVoltage was last updated."
    ::= { tmnxHwResourceEntry 5 }

tmnxHwResourceCurrentWattage     OBJECT-TYPE
    SYNTAX      Integer32
    MAX-ACCESS  read-only
    STATUS      current
    DESCRIPTION
        "The value of tmnxHwResourceCurrentWattage indicates the current power
         use of the managed hardware component in milli-Watts (mW)."
    ::= { tmnxHwResourceEntry 6 }

tmnxHwResourcePeakWattage        OBJECT-TYPE
    SYNTAX      Integer32
    MAX-ACCESS  read-only
    STATUS      current
    DESCRIPTION
        "The value of tmnxHwResourcePeakWattage indicates the peak power use of
         the managed hardware component in milli-Watts (mW) last recorded at
         the time indicated by tmnxHwResourcePeakWattageTime."
    ::= { tmnxHwResourceEntry 7 }

tmnxHwResourcePeakWattageTime    OBJECT-TYPE
    SYNTAX      TimeStamp
    MAX-ACCESS  read-only
    STATUS      current
    DESCRIPTION
        "The value of tmnxHwResourcePeakWattageTime indicates the time, since
         system initialization, that tmnxHwResourcePeakWattage was last
         updated."
    ::= { tmnxHwResourceEntry 8 }

tmnxHwResourceMinWattage         OBJECT-TYPE
    SYNTAX      Integer32
    MAX-ACCESS  read-only
    STATUS      current
    DESCRIPTION
        "The value of tmnxHwResourceMinWattage indicates the lowest power use
         of the managed hardware component in milli-Watts (mW) last recorded at
         the time indicated by tmnxHwResourceMinWattageTime."
    ::= { tmnxHwResourceEntry 9 }

tmnxHwResourceMinWattageTime     OBJECT-TYPE
    SYNTAX      TimeStamp
    MAX-ACCESS  read-only
    STATUS      current
    DESCRIPTION
        "The value of tmnxHwResourceMinWattageTime indicates the time, since
         system initialization, that tmnxHwResourceMinWattage was last updated."
    ::= { tmnxHwResourceEntry 10 }

tmnxHwResourceCurrentAmperage    OBJECT-TYPE
    SYNTAX      Integer32
    MAX-ACCESS  read-only
    STATUS      current
    DESCRIPTION
        "The value of tmnxHwResourceCurrentAmperage indicates the current drawn
         by the managed hardware component in milli-Amperes (mA)."
    ::= { tmnxHwResourceEntry 11 }

tmnxHwResourcePeakAmperage       OBJECT-TYPE
    SYNTAX      Integer32
    MAX-ACCESS  read-only
    STATUS      current
    DESCRIPTION
        "The value of tmnxHwResourcePeakAmperage indicates the peak current
         drawn by the managed hardware component in milli-Amperes (mA) last
         recorded at the time indicated by tmnxHwResourcePeakAmperageTime."
    ::= { tmnxHwResourceEntry 12 }

tmnxHwResourcePeakAmperageTime   OBJECT-TYPE
    SYNTAX      TimeStamp
    MAX-ACCESS  read-only
    STATUS      current
    DESCRIPTION
        "The value of tmnxHwResourcePeakAmperageTime indicates the time, since
         system initialization, that tmnxHwResourcePeakAmperage was last
         updated."
    ::= { tmnxHwResourceEntry 13 }

tmnxHwResourceMinAmperage        OBJECT-TYPE
    SYNTAX      Integer32
    MAX-ACCESS  read-only
    STATUS      current
    DESCRIPTION
        "The value of tmnxHwResourceMinAmperage indicates the lowest current
         drawn by the managed hardware component in milli-Amperes (mA) last
         recorded at the time indicated by tmnxHwResourceMinAmperageTime."
    ::= { tmnxHwResourceEntry 14 }

tmnxHwResourceMinAmperageTime    OBJECT-TYPE
    SYNTAX      TimeStamp
    MAX-ACCESS  read-only
    STATUS      current
    DESCRIPTION
        "The value of tmnxHwResourceMinAmperageTime indicates the time, since
         system initialization, that tmnxHwResourceMinAmperage was last
         updated."
    ::= { tmnxHwResourceEntry 15 }

tmnxHwResourceMaxRequiredWattage OBJECT-TYPE
    SYNTAX      Integer32
    UNITS       "Wattage"
    MAX-ACCESS  read-only
    STATUS      current
    DESCRIPTION
        "The value of tmnxHwResourceMaxRequiredWattage indicates the maximum
         possible power consumption for this device.  This value is used to
         determine the amount of system power to reserve in order to safely
         power up the device."
    ::= { tmnxHwResourceEntry 16 }

tmnxPEQTypeTable                 OBJECT-TYPE
    SYNTAX      SEQUENCE OF TmnxPEQTypeEntry
    MAX-ACCESS  not-accessible
    STATUS      current
    DESCRIPTION
        "The tmnxPEQTypeTable has an entry for each Power Equalizer (PEQ) type
         supported by the system. Some example PEQ types are: 'apeq-dc-2000',
         'apeq-ac-3000'."
    ::= { tmnxChassisObjs 14 }

tmnxPEQTypeEntry                 OBJECT-TYPE
    SYNTAX      TmnxPEQTypeEntry
    MAX-ACCESS  not-accessible
    STATUS      current
    DESCRIPTION
        "Each row entry represents an Nokia SROS series Power Equalizer
         type.  Rows in this table are created by the agent at initialization
         and cannot be created or destroyed by SNMP Get or Set requests."
    INDEX       { tmnxPEQTypeIndex }
    ::= { tmnxPEQTypeTable 1 }

TmnxPEQTypeEntry                 ::= SEQUENCE
{
    tmnxPEQTypeIndex                 TmnxPEQType,
    tmnxPEQTypeName                  TNamedItemOrEmpty,
    tmnxPEQTypeDescription           TItemDescription,
    tmnxPEQTypeNumInputFeed          Unsigned32
}

tmnxPEQTypeIndex                 OBJECT-TYPE
    SYNTAX      TmnxPEQType
    MAX-ACCESS  not-accessible
    STATUS      current
    DESCRIPTION
        "The value of tmnxPEQTypeIndex specifies the unique index which
         identifies the type of Nokia SROS series Power Equalizer (PEQ)."
    ::= { tmnxPEQTypeEntry 1 }

tmnxPEQTypeName                  OBJECT-TYPE
    SYNTAX      TNamedItemOrEmpty
    MAX-ACCESS  read-only
    STATUS      current
    DESCRIPTION
        "The value of tmnxPEQTypeName indicates the administrative name that
         identifies the type of Nokia SROS series PEQ. This name string is used
         in CLI commands to specify a particular PEQ type."
    ::= { tmnxPEQTypeEntry 2 }

tmnxPEQTypeDescription           OBJECT-TYPE
    SYNTAX      TItemDescription
    MAX-ACCESS  read-only
    STATUS      current
    DESCRIPTION
        "The value of tmnxPEQTypeDescription indicates the detailed description
         of this Nokia SROS series PEQ type."
    ::= { tmnxPEQTypeEntry 3 }

tmnxPEQTypeNumInputFeed          OBJECT-TYPE
    SYNTAX      Unsigned32
    MAX-ACCESS  read-only
    STATUS      current
    DESCRIPTION
        "The value of tmnxPEQTypeNumInputFeed indicates the number of input
         feeds that this PEQ type has."
    ::= { tmnxPEQTypeEntry 4 }

tmnxChassisPEQTableLastChg       OBJECT-TYPE
    SYNTAX      TimeStamp
    MAX-ACCESS  read-only
    STATUS      obsolete
    DESCRIPTION
        "The value of tmnxChassisPEQTableLastChg indicates the time, since
         system startup, that a row in the tmnxChassisPEQTable last changed
         configuration.

         This object was made obsolete in release 15.0."
    ::= { tmnxChassisObjs 15 }

tmnxChassisPEQTable              OBJECT-TYPE
    SYNTAX      SEQUENCE OF TmnxChassisPEQEntry
    MAX-ACCESS  not-accessible
    STATUS      obsolete
    DESCRIPTION
        "The tmnxChassisPEQTable contains information about Power Equalizer
         type in the chassis.

         This table was made obsolete in release 15.0."
    ::= { tmnxChassisObjs 16 }

tmnxChassisPEQEntry              OBJECT-TYPE
    SYNTAX      TmnxChassisPEQEntry
    MAX-ACCESS  not-accessible
    STATUS      obsolete
    DESCRIPTION
        "Each row entry represents an Nokia SROS series PEQ slot.

         This table augments the tmnxChassisPowerSupplyTable on chassis that
         support PEQs.

         Rows in this table are created by the agent at initialization and
         cannot be created or destroyed by SNMP Get or Set requests.

         This entry was made obsolete in release 15.0."
    AUGMENTS    { tmnxChassisPowerSupplyEntry }
    ::= { tmnxChassisPEQTable 1 }

TmnxChassisPEQEntry              ::= SEQUENCE
{
    tmnxChassisPEQLastChangedTime    TimeStamp,
    tmnxChassisPEQAssignedType       TmnxPEQType,
    tmnxChassisPEQEquippedType       TmnxPEQType,
    tmnxChassisPEQSupportedTypes     TmnxPEQSuppType,
    tmnxChassisPEQAvailableWattage   Unsigned32,
    tmnxChassisPEQInputPowerMode     Unsigned32
}

tmnxChassisPEQLastChangedTime    OBJECT-TYPE
    SYNTAX      TimeStamp
    MAX-ACCESS  read-only
    STATUS      obsolete
    DESCRIPTION
        "The value of tmnxChassisPEQLastChangedTime indicates the time, since
         system startup, that an object in this row changed configuration.

         This object was made obsolete in release 15.0."
    ::= { tmnxChassisPEQEntry 1 }

tmnxChassisPEQAssignedType       OBJECT-TYPE
    SYNTAX      TmnxPEQType
    MAX-ACCESS  read-write
    STATUS      obsolete
    DESCRIPTION
        "The value of tmnxChassisPEQAssignedType specifies the administratively
         assigned (pre-provisioned) PEQ type defined in the tmnxPEQTypeTable
         that should occupy this PEQ slot in the chassis.  If
         tmnxChassisPEQAssignedType has a value of 1 (unassigned), this slot has
         not yet been pre-provisioned.

         This object was made obsolete in release 15.0."
    DEFVAL      { 1 }
    ::= { tmnxChassisPEQEntry 2 }

tmnxChassisPEQEquippedType       OBJECT-TYPE
    SYNTAX      TmnxPEQType
    MAX-ACCESS  read-only
    STATUS      obsolete
    DESCRIPTION
        "The value of tmnxChassisPEQEquippedType indicates the PEQ type of the
         PEQ that is physically inserted into this PEQ slot in the chassis. If
         the slot has been pre-provisioned, tmnxChassisPEQAssignedType is not
         equal to 1 (unassigned), and the value of tmnxChassisPEQEquippedType
         is not the same as tmnxChassisPEQAssignedType, a mismatch alarm will
         be raised.

         A value of 0 indicates the PEQ type is not recognized by the SROS.

         This object was made obsolete in release 15.0."
    ::= { tmnxChassisPEQEntry 3 }

tmnxChassisPEQSupportedTypes     OBJECT-TYPE
    SYNTAX      TmnxPEQSuppType
    MAX-ACCESS  read-only
    STATUS      obsolete
    DESCRIPTION
        "The value of tmnxChassisPEQSupportedTypes is a bit-mask that indicates
         what PEQ types can be physically supported in this PEQ slot in this
         chassis.

         This object was made obsolete in release 15.0."
    ::= { tmnxChassisPEQEntry 4 }

tmnxChassisPEQAvailableWattage   OBJECT-TYPE
    SYNTAX      Unsigned32
    UNITS       "watts"
    MAX-ACCESS  read-only
    STATUS      obsolete
    DESCRIPTION
        "The value of tmnxChassisPEQAvailableWattage indicates the reported
         available wattage of the PEQ.

         This object was made obsolete in release 15.0."
    ::= { tmnxChassisPEQEntry 5 }

tmnxChassisPEQInputPowerMode     OBJECT-TYPE
    SYNTAX      Unsigned32 (0 | 60 | 80)
    UNITS       "amps"
    MAX-ACCESS  read-write
    STATUS      obsolete
    DESCRIPTION
        "The value of tmnxChassisPEQInputPowerMode specifies the input power
         mode of the PEQ.

         A value of zero indicates that the input power mode is not applicable
         for the PEQ. An SNMP SET request with a value of zero is not
         permitted.

         This object was made obsolete in release 15.0."
    ::= { tmnxChassisPEQEntry 6 }

tmnxChassisPowerMgmtTableLastChg OBJECT-TYPE
    SYNTAX      TimeStamp
    MAX-ACCESS  read-only
    STATUS      current
    DESCRIPTION
        "The value of tmnxChassisPowerMgmtTableLastChg indicates the time,
         since system startup, when a row in the tmnxChassisPowerMgmtTable last
         changed configuration."
    ::= { tmnxChassisObjs 17 }

tmnxChassisPowerMgmtTable        OBJECT-TYPE
    SYNTAX      SEQUENCE OF TmnxChassisPowerMgmtEntry
    MAX-ACCESS  not-accessible
    STATUS      current
    DESCRIPTION
        "The tmnxChassisPowerMgmtTable manages the power requirements on the
         SROS series system. This table controls the behavior of the system
         during power resource contention."
    ::= { tmnxChassisObjs 18 }

tmnxChassisPowerMgmtEntry        OBJECT-TYPE
    SYNTAX      TmnxChassisPowerMgmtEntry
    MAX-ACCESS  not-accessible
    STATUS      current
    DESCRIPTION
        "Each row in the tmnxChassisPowerMgmtTable represents a managed
         power-zone on an SROS series system.

         Rows in this table are created by the agent at initialization and
         cannot be created or destroyed by SNMP Get or Set requests."
    INDEX       {
        tmnxChassisIndex,
        tmnxChassisPwrMgmtZone
    }
    ::= { tmnxChassisPowerMgmtTable 1 }

TmnxChassisPowerMgmtEntry        ::= SEQUENCE
{
    tmnxChassisPwrMgmtZone           Unsigned32,
    tmnxChassisPwrMgmtChangedTime    TimeStamp,
    tmnxChassisPwrMgmtMode           INTEGER,
    tmnxChassisPwrMgmtSafetyLevel    Gauge32,
    tmnxChassisPwrMgmtSafetyAlert    Unsigned32
}

tmnxChassisPwrMgmtZone           OBJECT-TYPE
    SYNTAX      Unsigned32 (1..32)
    MAX-ACCESS  not-accessible
    STATUS      current
    DESCRIPTION
        "The value of tmnxChassisPwrMgmtZone specifies the managed power-zone
         for this management entity."
    ::= { tmnxChassisPowerMgmtEntry 1 }

tmnxChassisPwrMgmtChangedTime    OBJECT-TYPE
    SYNTAX      TimeStamp
    MAX-ACCESS  read-only
    STATUS      current
    DESCRIPTION
        "The value of tmnxChassisPwrMgmtChangedTime indicates the time, since
         system startup, when an object in this row changed configuration."
    ::= { tmnxChassisPowerMgmtEntry 2 }

tmnxChassisPwrMgmtMode           OBJECT-TYPE
    SYNTAX      INTEGER {
        none     (0),
        basic    (1),
        advanced (2)
    }
    MAX-ACCESS  read-write
    STATUS      current
    DESCRIPTION
        "The value of tmnxChassisPwrMgmtMode specifies how the system behaves
         during power contention.

             none (0)  - When set to 'none (0)' the node will bring up as much
                         provisioned equipment in order of priority as possible
                         without exceeding capacity of the equipped or assigned
                         PEQs.

                         In this mode no gradual shutdown of active cards is
                         enforced.

                         Note: No spare capacity is reserved.  Any failure may
                         result in brown-outs or card failures.

             basic (1) - When set to 'basic (1)', the node will bring up, in
                         order of priority, as much of the provisioned equipment
                         as possible using the N+1 algorithm. This means enough
                         capacity will be held in reserve to ensure zero impact
                         should the highest rated PEQ fail or be removed.
                         However, subsequent failures may result in brown-outs
                         if the system can't shutdown low priority cards in time
                         when the secondary failure/removal occurs.

             advanced (2) - When set to 'advanced (2)', the system will maintain
                         a spare PEQ as long as possible to make it immune to
                         the possibility of power brown-outs. It does this by
                         shutting down low priority cards to restore N+1 when
                         N+1 is no longer in effect."
    DEFVAL      { basic }
    ::= { tmnxChassisPowerMgmtEntry 3 }

tmnxChassisPwrMgmtSafetyLevel    OBJECT-TYPE
    SYNTAX      Gauge32 (0..100)
    UNITS       "percent"
    MAX-ACCESS  read-write
    STATUS      current
    DESCRIPTION
        "The value of tmnxChassisPwrMgmtSafetyLevel specifies the percentage of
         the provisioned power requirement that will cause the system to start
         powering off lower-priority cards."
    DEFVAL      { 100 }
    ::= { tmnxChassisPowerMgmtEntry 4 }

tmnxChassisPwrMgmtSafetyAlert    OBJECT-TYPE
    SYNTAX      Unsigned32 (0..105600)
    UNITS       "watts"
    MAX-ACCESS  read-write
    STATUS      current
    DESCRIPTION
        "The value of tmnxChassisPwrMgmtSafetyAlert specifies the power
         capacity threshold where the SROS will trigger an event indicating a
         potential trigger of the safety-level state."
    DEFVAL      { 0 }
    ::= { tmnxChassisPowerMgmtEntry 5 }

tChassisResTable                 OBJECT-TYPE
    SYNTAX      SEQUENCE OF TChassisResEntry
    MAX-ACCESS  not-accessible
    STATUS      current
    DESCRIPTION
        "The value of tChassisResTable represents system resource information
         that are specific to chassis."
    ::= { tmnxChassisObjs 19 }

tChassisResEntry                 OBJECT-TYPE
    SYNTAX      TChassisResEntry
    MAX-ACCESS  not-accessible
    STATUS      current
    DESCRIPTION
        "The value of tChassisResEntry represents chassis specific system
         resource information."
    INDEX       { tmnxChassisIndex }
    ::= { tChassisResTable 1 }

TChassisResEntry                 ::= SEQUENCE
{
    tChassisResSapIngQosPolTotal     Unsigned32,
    tChassisResSapIngQosPolAlloc     Unsigned32,
    tChassisResSapEgrQosPolTotal     Unsigned32,
    tChassisResSapEgrQosPolAlloc     Unsigned32,
    tChassisResIngQGrpTmplTotal      Unsigned32,
    tChassisResIngQGrpTmplAlloc      Unsigned32,
    tChassisResEgrQGrpTmplTotal      Unsigned32,
    tChassisResEgrQGrpTmplAlloc      Unsigned32,
    tChassisResPortEgrQGrpInstTotal  Unsigned32,
    tChassisResPortEgrQGrpInstAlloc  Unsigned32,
    tChassisResFPIngQGrpInstTotal    Unsigned32,
    tChassisResFPIngQGrpInstAlloc    Unsigned32,
    tChassisResPortEgrVPortTotal     Unsigned32,
    tChassisResPortEgrVPortAlloc     Unsigned32,
    tChassisResDynSvcNHEntryTotal    Unsigned32,
    tChassisResDynSvcNHEntryAlloc    Unsigned32,
    tChassisResIpSecNHEntryTotal     Unsigned32,
    tChassisResIpSecNHEntryAlloc     Unsigned32,
    tChassisResSubNHEntryTotal       Unsigned32,
    tChassisResSubNHEntryAlloc       Unsigned32,
    tChassisResSapTotal              Unsigned32,
    tChassisResSapAlloc              Unsigned32
}

tChassisResSapIngQosPolTotal     OBJECT-TYPE
    SYNTAX      Unsigned32
    MAX-ACCESS  read-only
    STATUS      current
    DESCRIPTION
        "The value of tChassisResSapIngQosPolTotal represents the total number
         of sap-ingress QoS policies that are allowed to be provisioned on this
         chassis.

         When the value of tChassisResSapIngQosPolTotal is zero, it indicates
         that this resource type is not supported on this chassis."
    ::= { tChassisResEntry 1 }

tChassisResSapIngQosPolAlloc     OBJECT-TYPE
    SYNTAX      Unsigned32
    MAX-ACCESS  read-only
    STATUS      current
    DESCRIPTION
        "The value of tChassisResSapIngQosPolAlloc represents the total number
         of sap-ingress QoS policies that are currently provisioned on this
         chassis."
    ::= { tChassisResEntry 2 }

tChassisResSapEgrQosPolTotal     OBJECT-TYPE
    SYNTAX      Unsigned32
    MAX-ACCESS  read-only
    STATUS      current
    DESCRIPTION
        "The value of tChassisResSapEgrQosPolTotal represents the total number
         of sap-egress QoS policies that are allowed to be provisioned on this
         chassis.

         When the value of tChassisResSapEgrQosPolTotal is zero, it indicates
         that this resource type is not supported on this chassis."
    ::= { tChassisResEntry 3 }

tChassisResSapEgrQosPolAlloc     OBJECT-TYPE
    SYNTAX      Unsigned32
    MAX-ACCESS  read-only
    STATUS      current
    DESCRIPTION
        "The value of tChassisResSapEgrQosPolAlloc represents the total number
         of sap-egress QoS policies that are currently provisioned on this
         chassis."
    ::= { tChassisResEntry 4 }

tChassisResIngQGrpTmplTotal      OBJECT-TYPE
    SYNTAX      Unsigned32
    MAX-ACCESS  read-only
    STATUS      current
    DESCRIPTION
        "The value of tChassisResIngQGrpTmplTotal represents the total number
         of ingress queue-group-templates that are allowed to be provisioned on
         this chassis.

         When the value of tChassisResIngQGrpTmplTotal is zero, it indicates
         that this resource type is not supported on this chassis."
    ::= { tChassisResEntry 5 }

tChassisResIngQGrpTmplAlloc      OBJECT-TYPE
    SYNTAX      Unsigned32
    MAX-ACCESS  read-only
    STATUS      current
    DESCRIPTION
        "The value of tChassisResIngQGrpTmplAlloc represents the total number
         of ingress queue-group-templates that are currently provisioned on
         this chassis."
    ::= { tChassisResEntry 6 }

tChassisResEgrQGrpTmplTotal      OBJECT-TYPE
    SYNTAX      Unsigned32
    MAX-ACCESS  read-only
    STATUS      current
    DESCRIPTION
        "The value of tChassisResEgrQGrpTmplTotal represents the total number
         of egress queue-group-templates that are allowed to be provisioned on
         this chassis.

         When the value of tChassisResEgrQGrpTmplTotal is zero, it indicates
         that this resource type is not supported on this chassis."
    ::= { tChassisResEntry 7 }

tChassisResEgrQGrpTmplAlloc      OBJECT-TYPE
    SYNTAX      Unsigned32
    MAX-ACCESS  read-only
    STATUS      current
    DESCRIPTION
        "The value of tChassisResEgrQGrpTmplAlloc represents the total number
         of egress queue-group-templates that are currently provisioned on this
         chassis."
    ::= { tChassisResEntry 8 }

tChassisResPortEgrQGrpInstTotal  OBJECT-TYPE
    SYNTAX      Unsigned32
    MAX-ACCESS  read-only
    STATUS      current
    DESCRIPTION
        "The value of tChassisResPortEgrQGrpInstTotal represents the total
         number of port egress queue-group instances across all the ports on
         this chassis including access and network instances that are allowed
         to be provisioned.

         When the value of tChassisResPortEgrQGrpInstTotal is zero, it
         indicates that this resource type is not supported on this chassis."
    ::= { tChassisResEntry 9 }

tChassisResPortEgrQGrpInstAlloc  OBJECT-TYPE
    SYNTAX      Unsigned32
    MAX-ACCESS  read-only
    STATUS      current
    DESCRIPTION
        "The value of tChassisResPortEgrQGrpInstAlloc represents the total
         number of port egress queue-group instances across all the ports on
         this chassis including access and network instances that are currently
         provisioned."
    ::= { tChassisResEntry 10 }

tChassisResFPIngQGrpInstTotal    OBJECT-TYPE
    SYNTAX      Unsigned32
    MAX-ACCESS  read-only
    STATUS      current
    DESCRIPTION
        "The value of tChassisResFPIngQGrpInstTotal represents the total number
         of forwarding-plane (FP) ingress queue-group instances across all the
         FP on this chassis including access and network instances that are
         allowed to be provisioned.

         When the value of tChassisResFPIngQGrpInstTotal is zero, it indicates
         that this resource type is not supported on this chassis."
    ::= { tChassisResEntry 11 }

tChassisResFPIngQGrpInstAlloc    OBJECT-TYPE
    SYNTAX      Unsigned32
    MAX-ACCESS  read-only
    STATUS      current
    DESCRIPTION
        "The value of tChassisResFPIngQGrpInstAlloc represents the total number
         of forwarding-plane (FP) ingress queue-group instances across all the
         FP on this chassis including access and network instances that are
         allowed to be provisioned."
    ::= { tChassisResEntry 12 }

tChassisResPortEgrVPortTotal     OBJECT-TYPE
    SYNTAX      Unsigned32
    MAX-ACCESS  read-only
    STATUS      current
    DESCRIPTION
        "The value of tChassisResPortEgrVPortTotal represents the total number
         of egress virtual ports across all the ports on this chassis that are
         allowed to be provisioned.

         When the value of tChassisResPortEgrVPortTotal is zero, it indicates
         that this resource type is not supported on this chassis."
    ::= { tChassisResEntry 13 }

tChassisResPortEgrVPortAlloc     OBJECT-TYPE
    SYNTAX      Unsigned32
    MAX-ACCESS  read-only
    STATUS      current
    DESCRIPTION
        "The value of tChassisResPortEgrVPortAlloc represents the total number
         of port virtual ports across all the ports on this chassis that are
         currently provisioned."
    ::= { tChassisResEntry 14 }

tChassisResDynSvcNHEntryTotal    OBJECT-TYPE
    SYNTAX      Unsigned32
    MAX-ACCESS  read-only
    STATUS      current
    DESCRIPTION
        "The value of tChassisResDynSvcNHEntryTotal represents the total number
         of dynamic service next-hop entries supported on this chassis.

         When the value of tChassisResDynSvcNHEntryTotal is zero, it indicates
         that this resource type is not supported on this chassis."
    ::= { tChassisResEntry 15 }

tChassisResDynSvcNHEntryAlloc    OBJECT-TYPE
    SYNTAX      Unsigned32
    MAX-ACCESS  read-only
    STATUS      current
    DESCRIPTION
        "The value of tChassisResDynSvcNHEntryAlloc represents the total number
         of dynamic service next-hop entries currently in use on this chassis.

         The value of tChassisResDynSvcNHEntryAlloc will always equal to the
         sum of tChassisResIpSecNHEntryAlloc and tChassisResSubNHEntryAlloc
         since IPsec next-hop and subscriber next-hop resources are subsets of
         dynamic service next-hop entry resources."
    ::= { tChassisResEntry 16 }

tChassisResIpSecNHEntryTotal     OBJECT-TYPE
    SYNTAX      Unsigned32
    MAX-ACCESS  read-only
    STATUS      current
    DESCRIPTION
        "The value of tChassisResIpSecNHEntryTotal represents the total number
         of IPsec next-hop entries supported on this chassis.

         When the value of tChassisResIpSecNHEntryTotal is zero, it indicates
         that this resource type is not supported on this chassis.

         The value of tChassisResIpSecNHEntryTotal will always be less than or
         equal to tChassisResDynSvcNHEntryTotal since IPsec next-hop entry
         resources are a subset of dynamic service next-hop entry resources."
    ::= { tChassisResEntry 17 }

tChassisResIpSecNHEntryAlloc     OBJECT-TYPE
    SYNTAX      Unsigned32
    MAX-ACCESS  read-only
    STATUS      current
    DESCRIPTION
        "The value of tChassisResIpSecNHEntryAlloc represents the total number
         of IPsec next-hop entries currently in use on this chassis.

         The value of tChassisResIpSecNHEntryAlloc will always be less than or
         equal to tChassisResDynSvcNHEntryAlloc since IPsec next-hop entry
         resources are a subset of dynamic service next-hop entry resources."
    ::= { tChassisResEntry 18 }

tChassisResSubNHEntryTotal       OBJECT-TYPE
    SYNTAX      Unsigned32
    MAX-ACCESS  read-only
    STATUS      current
    DESCRIPTION
        "The value of tChassisResSubNHEntryTotal represents the total number of
         subscriber next-hop entries supported on this chassis.

         When the value of tChassisResSubNHEntryTotal is zero, it indicates
         that this resource type is not supported on this chassis.

         The value of tChassisResSubNHEntryTotal will always be less than or
         equal to tChassisResDynSvcNHEntryTotal since subscriber next-hop entry
         resources are a subset of dynamic service next-hop entry resources."
    ::= { tChassisResEntry 19 }

tChassisResSubNHEntryAlloc       OBJECT-TYPE
    SYNTAX      Unsigned32
    MAX-ACCESS  read-only
    STATUS      current
    DESCRIPTION
        "The value of tChassisResSubNHEntryAlloc represents the total number of
         subscriber next-hop entries currently in use on this chassis.

         The value of tChassisResSubNHEntryAlloc will always be less than or
         equal to tChassisResDynSvcNHEntryAlloc since subscriber next-hop entry
         resources are a subset of dynamic service next hop entry resources."
    ::= { tChassisResEntry 20 }

tChassisResSapTotal              OBJECT-TYPE
    SYNTAX      Unsigned32
    MAX-ACCESS  read-only
    STATUS      current
    DESCRIPTION
        "The value of tChassisResSapTotal represents the total number of
         provisioned SAP entries supported on this chassis.

         When the value of tChassisResSapTotal is zero, it indicates that this
         resource type is not supported on this chassis."
    ::= { tChassisResEntry 21 }

tChassisResSapAlloc              OBJECT-TYPE
    SYNTAX      Unsigned32
    MAX-ACCESS  read-only
    STATUS      current
    DESCRIPTION
        "The value of tChassisResSapAlloc represents the total number of
         provisioned SAP entries currently in use on this chassis."
    ::= { tChassisResEntry 22 }

tmnxPhysChassisTable             OBJECT-TYPE
    SYNTAX      SEQUENCE OF TmnxPhysChassisEntry
    MAX-ACCESS  not-accessible
    STATUS      current
    DESCRIPTION
        "The tmnxPhysChassisTable maintains the state of the physical chassis'
         in the system."
    ::= { tmnxChassisObjs 21 }

tmnxPhysChassisEntry             OBJECT-TYPE
    SYNTAX      TmnxPhysChassisEntry
    MAX-ACCESS  not-accessible
    STATUS      current
    DESCRIPTION
        "Each row of tmnxPhysChassisEntry consists of the attributes for an
         individual physical chassis provisioned in the system. Rows are
         created and destroyed by the system."
    INDEX       {
        tmnxChassisIndex,
        tmnxPhysChassisClass,
        tmnxPhysChassisNum
    }
    ::= { tmnxPhysChassisTable 1 }

TmnxPhysChassisEntry             ::= SEQUENCE
{
    tmnxPhysChassisClass             TmnxPhysChassisClass,
    tmnxPhysChassisNum               TmnxPhysChassisIndex,
    tmnxPhysChassisRole              TmnxPhysChassisRole,
    tmnxPhysChassisState             TmnxDeviceState,
    tmnxPhysChassisHwIndex           TmnxHwIndex,
    tmnxPhysChassisNumPwrSupplies    Unsigned32,
    tmnxPhysChassisNumFanTrays       Unsigned32,
    tmnxPhysChassisNumFans           Unsigned32,
    tmnxPhysChassisName              TNamedItem,
    tmnxPhysChassisDescription       TItemDescription
}

tmnxPhysChassisClass             OBJECT-TYPE
    SYNTAX      TmnxPhysChassisClass
    MAX-ACCESS  not-accessible
    STATUS      current
    DESCRIPTION
        "The value of tmnxPhysChassisClass specifies the class of this physical
         chassis in the SROS system."
    ::= { tmnxPhysChassisEntry 1 }

tmnxPhysChassisNum               OBJECT-TYPE
    SYNTAX      TmnxPhysChassisIndex
    MAX-ACCESS  not-accessible
    STATUS      current
    DESCRIPTION
        "The value of tmnxPhysChassisNum specifies the unique identifier,
         within a class, for this physical chassis."
    ::= { tmnxPhysChassisEntry 2 }

tmnxPhysChassisRole              OBJECT-TYPE
    SYNTAX      TmnxPhysChassisRole
    MAX-ACCESS  read-only
    STATUS      current
    DESCRIPTION
        "The value of tmnxPhysChassisRole indicates the role of which this
         physical chassis shall perform while active in the system."
    ::= { tmnxPhysChassisEntry 3 }

tmnxPhysChassisState             OBJECT-TYPE
    SYNTAX      TmnxDeviceState
    MAX-ACCESS  read-only
    STATUS      current
    DESCRIPTION
        "The value of tmnxPhysChassisState indicates the device state of the
         physical chassis in the system."
    ::= { tmnxPhysChassisEntry 4 }

tmnxPhysChassisHwIndex           OBJECT-TYPE
    SYNTAX      TmnxHwIndex
    MAX-ACCESS  read-only
    STATUS      current
    DESCRIPTION
        "The value of tmnxPhysChassisHwIndex indicates the index into the
         tmnxHwTable for the row that represents the hardware component
         information for this physical chassis in the system."
    ::= { tmnxPhysChassisEntry 5 }

tmnxPhysChassisNumPwrSupplies    OBJECT-TYPE
    SYNTAX      Unsigned32
    MAX-ACCESS  read-only
    STATUS      current
    DESCRIPTION
        "The value of tmnxPhysChassisNumPwrSupplies indicates the total number
         of power supplies installed in this physical chassis."
    ::= { tmnxPhysChassisEntry 6 }

tmnxPhysChassisNumFanTrays       OBJECT-TYPE
    SYNTAX      Unsigned32
    MAX-ACCESS  read-only
    STATUS      current
    DESCRIPTION
        "The value of tmnxPhysChassisNumFanTrays indicates the total number of
         fan trays installed in this physical chassis."
    ::= { tmnxPhysChassisEntry 7 }

tmnxPhysChassisNumFans           OBJECT-TYPE
    SYNTAX      Unsigned32
    MAX-ACCESS  read-only
    STATUS      current
    DESCRIPTION
        "The value of tmnxPhysChassisNumFans indicates the total number of fans
         installed in this physical chassis."
    ::= { tmnxPhysChassisEntry 8 }

tmnxPhysChassisName              OBJECT-TYPE
    SYNTAX      TNamedItem
    MAX-ACCESS  read-only
    STATUS      current
    DESCRIPTION
        "The value of tmnxPhysChassisName indicates the textual name for this
         physical chassis.

         Examples:
            tmnxPhysChassisName     tmnxPhysChassisClass    tmnxPhysChassisNum
            1                       'routerChassis(3)'      1
            oes-3                   'oesChassis(4)'         3"
    ::= { tmnxPhysChassisEntry 9 }

tmnxPhysChassisDescription       OBJECT-TYPE
    SYNTAX      TItemDescription
    MAX-ACCESS  read-write
    STATUS      current
    DESCRIPTION
        "The value of tmnxPhysChassisDescription specifies the description of
         the physical chassis."
    DEFVAL      { ''H }
    ::= { tmnxPhysChassisEntry 10 }

tmnxChassisHwEventObjs           OBJECT IDENTIFIER ::= { tmnxChassisObjs 22 }

tmnxCardHwEventTable             OBJECT-TYPE
    SYNTAX      SEQUENCE OF TmnxCardHwEventEntry
    MAX-ACCESS  not-accessible
    STATUS      current
    DESCRIPTION
        "The tmnxCardHwEventTable maintains the basic information regarding
         events detected and reported on provisioned cards on the SROS series
         system."
    ::= { tmnxChassisHwEventObjs 1 }

tmnxCardHwEventEntry             OBJECT-TYPE
    SYNTAX      TmnxCardHwEventEntry
    MAX-ACCESS  not-accessible
    STATUS      current
    DESCRIPTION
        "A tmnxCardHwEventEntry row is created by the system whenever an event
         is detected and reported on either the tmnxCpmCardEntry or
         tmnxCardEntry as specified by the index of the row.  All records are
         cleared on card resets."
    INDEX       {
        tmnxChassisIndex,
        tmnxCardHwEventSlotNum,
        tmnxCardHwEventType,
        tmnxCardHwEventComplex
    }
    ::= { tmnxCardHwEventTable 1 }

TmnxCardHwEventEntry             ::= SEQUENCE
{
    tmnxCardHwEventSlotNum           TmnxSlotNum,
    tmnxCardHwEventType              INTEGER,
    tmnxCardHwEventComplex           Unsigned32,
    tmnxCardHwEventNumOccurrences    Counter32,
    tmnxCardHwEventLastOccurTime     TimeStamp
}

tmnxCardHwEventSlotNum           OBJECT-TYPE
    SYNTAX      TmnxSlotNum
    MAX-ACCESS  not-accessible
    STATUS      current
    DESCRIPTION
        "The value of tmnxCardHwEventSlotNum specifies the slot number of the
         card to which this event is detected."
    ::= { tmnxCardHwEventEntry 1 }

tmnxCardHwEventType              OBJECT-TYPE
    SYNTAX      INTEGER {
        tChipParity (1)
    }
    MAX-ACCESS  not-accessible
    STATUS      current
    DESCRIPTION
        "The value of tmnxCardHwEventType specifies the type of event detected
         and reported against the base card (or one of its complexes).

         The detectable and reportable events supported by this system include:
             tChipParity (1) - Parity error on the switch fabric interface."
    ::= { tmnxCardHwEventEntry 2 }

tmnxCardHwEventComplex           OBJECT-TYPE
    SYNTAX      Unsigned32 (1..2)
    MAX-ACCESS  not-accessible
    STATUS      current
    DESCRIPTION
        "The value of tmnxCardHwEventComplex specifies the card complex in
         which the event occurred. If the type of event raised does not exist
         on a complex, the value of '1' will be used."
    ::= { tmnxCardHwEventEntry 3 }

tmnxCardHwEventNumOccurrences    OBJECT-TYPE
    SYNTAX      Counter32
    MAX-ACCESS  read-only
    STATUS      current
    DESCRIPTION
        "The value of tmnxCardHwEventNumOccurrences indicates the number of
         times the specified tmnxCardHwEventType has occurred on the specified
         base card (or complex) since startup, last clear, or IOM reboot."
    ::= { tmnxCardHwEventEntry 4 }

tmnxCardHwEventLastOccurTime     OBJECT-TYPE
    SYNTAX      TimeStamp
    MAX-ACCESS  read-only
    STATUS      current
    DESCRIPTION
        "The value of tmnxCardHwEventLastOccurTime indicates the last time the
         specified tmnxCardHwEventNumOccurrences incremented."
    ::= { tmnxCardHwEventEntry 5 }

tmnxMdaHwEventTable              OBJECT-TYPE
    SYNTAX      SEQUENCE OF TmnxMdaHwEventEntry
    MAX-ACCESS  not-accessible
    STATUS      current
    DESCRIPTION
        "The tmnxMdaHwEventTable maintains the basic information regarding
         events detected and reported on provisioned MDAs on the SROS series
         system."
    ::= { tmnxChassisHwEventObjs 2 }

tmnxMdaHwEventEntry              OBJECT-TYPE
    SYNTAX      TmnxMdaHwEventEntry
    MAX-ACCESS  not-accessible
    STATUS      current
    DESCRIPTION
        "A tmnxMdaHwEventEntry row is created by the system whenever an event
         is detected and reported on the tmnxMDAEntry as specified by the index
         of the row. All records are cleared whenever a CPM, IOM or MDA is
         reset or unprovisioned."
    INDEX       {
        tmnxCardSlotNum,
        tmnxMDASlotNum,
        tmnxMdaHwEventType
    }
    ::= { tmnxMdaHwEventTable 1 }

TmnxMdaHwEventEntry              ::= SEQUENCE
{
    tmnxMdaHwEventType               INTEGER,
    tmnxMdaHwEventNumOccurrences     Counter32,
    tmnxMdaHwEventLastOccurTime      TimeStamp
}

tmnxMdaHwEventType               OBJECT-TYPE
    SYNTAX      INTEGER {
        ingrXplErr (1)
    }
    MAX-ACCESS  not-accessible
    STATUS      current
    DESCRIPTION
        "The value of tmnxMdaHwEventType specifies the type of event detected
         and reported against the MDA.

         The detectable and reportable events supported by this system include:
             ingrXplErr (1) - Ingress XPL Error"
    ::= { tmnxMdaHwEventEntry 1 }

tmnxMdaHwEventNumOccurrences     OBJECT-TYPE
    SYNTAX      Counter32
    MAX-ACCESS  read-only
    STATUS      current
    DESCRIPTION
        "The value of tmnxMdaHwEventNumOccurrences indicates the number of
         times the specified tmnxMdaHwEventType has occurred on the specified
         MDA since startup, last CPM clear, or IOM reboot."
    ::= { tmnxMdaHwEventEntry 2 }

tmnxMdaHwEventLastOccurTime      OBJECT-TYPE
    SYNTAX      TimeStamp
    MAX-ACCESS  read-only
    STATUS      current
    DESCRIPTION
        "The value of tmnxMdaHwEventLastOccurTime indicates the last time the
         specified tmnxMdaHwEventNumOccurrences incremented."
    ::= { tmnxMdaHwEventEntry 3 }

tmnxChassisMgmtEthRedObjs        OBJECT IDENTIFIER ::= { tmnxChassisObjs 23 }

tmnxChassisMgmtEthRed            OBJECT-TYPE
    SYNTAX      TmnxEnabledDisabled
    MAX-ACCESS  read-write
    STATUS      current
    DESCRIPTION
        "The value of tmnxChassisMgmtEthRed specifies whether or not the
         management Ethernet port redundancy feature is enabled or disabled."
    DEFVAL      { disabled }
    ::= { tmnxChassisMgmtEthRedObjs 1 }

tmnxChassisMgmtEthRedRevertTime  OBJECT-TYPE
    SYNTAX      Unsigned32 (1..300)
    UNITS       "seconds"
    MAX-ACCESS  read-write
    STATUS      current
    DESCRIPTION
        "The value of tmnxChassisMgmtEthRedRevertTime specifies the amount of
         time the system will wait before reverting the standby CPM management
         Ethernet port to the active CPM after the active CPM management
         Ethernet port becomes operationally up."
    DEFVAL      { 5 }
    ::= { tmnxChassisMgmtEthRedObjs 2 }

tmnxChassisMgmtEthRedStandby     OBJECT-TYPE
    SYNTAX      TruthValue
    MAX-ACCESS  read-only
    STATUS      current
    DESCRIPTION
        "The value of tmnxChassisMgmtEthRedStandby indicates whether or not the
         management of the node is operating from the standby CPM's management
         Ethernet port."
    ::= { tmnxChassisMgmtEthRedObjs 3 }

tmnxPhysChassisObjs              OBJECT IDENTIFIER ::= { tmnxChassisObjs 24 }

tmnxPhysChassisFanTable          OBJECT-TYPE
    SYNTAX      SEQUENCE OF TmnxPhysChassisFanEntry
    MAX-ACCESS  not-accessible
    STATUS      current
    DESCRIPTION
        "The tmnxPhysChassisFanTable contains information about fan trays on
         the physical chassis.

         Rows are created/destroyed automatically by the system."
    ::= { tmnxPhysChassisObjs 1 }

tmnxPhysChassisFanEntry          OBJECT-TYPE
    SYNTAX      TmnxPhysChassisFanEntry
    MAX-ACCESS  not-accessible
    STATUS      current
    DESCRIPTION
        "The tmnxPhysChassisFanEntry contains information regarding a fan tray
         for the physical chassis."
    INDEX       {
        tmnxPhysChassisClass,
        tmnxPhysChassisNum,
        tmnxPhysChassisFanIndex
    }
    ::= { tmnxPhysChassisFanTable 1 }

TmnxPhysChassisFanEntry          ::= SEQUENCE
{
    tmnxPhysChassisFanIndex          Unsigned32,
    tmnxPhysChassisFanOperStatus     TmnxDeviceState,
    tmnxPhysChassisFanSpeed          INTEGER,
    tmnxPhysChassisFanRevision       INTEGER,
    tmnxPhysChassisFanSpeedPercent   Unsigned32
}

tmnxPhysChassisFanIndex          OBJECT-TYPE
    SYNTAX      Unsigned32 (1..31)
    MAX-ACCESS  not-accessible
    STATUS      current
    DESCRIPTION
        "The value of tmnxPhysChassisFanIndex specifies a unique value which
         identifies a specific fan tray in the physical chassis."
    ::= { tmnxPhysChassisFanEntry 1 }

tmnxPhysChassisFanOperStatus     OBJECT-TYPE
    SYNTAX      TmnxDeviceState
    MAX-ACCESS  read-only
    STATUS      current
    DESCRIPTION
        "The value of tmnxPhysChassisFanOperStatus indicates the current status
         of the fan tray in the physical chassis."
    ::= { tmnxPhysChassisFanEntry 2 }

tmnxPhysChassisFanSpeed          OBJECT-TYPE
    SYNTAX      INTEGER {
        notApplicable (0),
        unknown       (1),
        halfSpeed     (2),
        fullSpeed     (3)
    }
    MAX-ACCESS  read-only
    STATUS      obsolete
    DESCRIPTION
        "The value of tmnxPhysChassisFanSpeed indicates the speed that the fan
         in the physical chassis is operating at.

         This object was made obsolete in 15.0 and replaced with
         tmnxPhysChassisFanSpeedPercent."
    ::= { tmnxPhysChassisFanEntry 3 }

tmnxPhysChassisFanRevision       OBJECT-TYPE
    SYNTAX      INTEGER {
        unknown (0),
        fan1    (1),
        hfFan2  (2)
    }
    MAX-ACCESS  read-only
    STATUS      current
    DESCRIPTION
        "The value of tmnxPhysChassisFanRevision indicates the revision of the
         fan in the physical chassis.

         Values:
             unknown (0) - revision is unknown
             fan1    (1) - represents the original fan tray
             hfFan2  (2) - represents the high-flow fan tray; second revision"
    ::= { tmnxPhysChassisFanEntry 4 }

tmnxPhysChassisFanSpeedPercent   OBJECT-TYPE
    SYNTAX      Unsigned32 (0..100)
    UNITS       "percent"
    MAX-ACCESS  read-only
    STATUS      current
    DESCRIPTION
        "The value of tmnxPhysChassisFanSpeedPercent indicates the speed of the
         fan as a percentage of maximum speed."
    ::= { tmnxPhysChassisFanEntry 5 }

tmnxPhysChassisPowerSupplyTable  OBJECT-TYPE
    SYNTAX      SEQUENCE OF TmnxPhysChassisPowerSupplyEntry
    MAX-ACCESS  not-accessible
    STATUS      current
    DESCRIPTION
        "The tmnxPhysChassisPowerSupplyTable contains information about power
         supply trays, also known as PEMs (Power Entry Modules) in the physical
         chassis.

         Rows are created/destroyed automatically by the system."
    ::= { tmnxPhysChassisObjs 2 }

tmnxPhysChassisPowerSupplyEntry  OBJECT-TYPE
    SYNTAX      TmnxPhysChassisPowerSupplyEntry
    MAX-ACCESS  not-accessible
    STATUS      current
    DESCRIPTION
        "The tmnxPhysChassisPowerSupplyEntry contains information regarding a
         power supply tray in the physical chassis."
    INDEX       {
        tmnxPhysChassisClass,
        tmnxPhysChassisNum,
        tmnxPhysChassPowerSupId
    }
    ::= { tmnxPhysChassisPowerSupplyTable 1 }

TmnxPhysChassisPowerSupplyEntry  ::= SEQUENCE
{
    tmnxPhysChassPowerSupId          Unsigned32,
    tmnxPhysChassPowerSupACStatus    TmnxDeviceState,
    tmnxPhysChassPowerSupDCStatus    TmnxDeviceState,
    tmnxPhysChassPowerSupTempStatus  TmnxDeviceState,
    tmnxPhysChassPowerSupTempThrshld Integer32,
    tmnxPhysChassPowerSup1Status     TmnxDeviceState,
    tmnxPhysChassPowerSup2Status     TmnxDeviceState,
    tmnxPhysChassPowerSupAssignType  TmnxPowerSupAssignType,
    tmnxPhysChassPowerSupInputStatus TmnxDeviceState,
    tmnxPhysChassPowerSupOutptStatus TmnxDeviceState,
    tmnxPhysChassPowerSupPemType     TmnxChassisPemType,
    tmnxPhysChassPowerSupPemACRect   BITS,
    tmnxPhysChassPowerSupInFeedDown  BITS,
    tmnxPhysChassPowerSupFanDir      INTEGER
}

tmnxPhysChassPowerSupId          OBJECT-TYPE
    SYNTAX      Unsigned32 (1..31)
    MAX-ACCESS  not-accessible
    STATUS      current
    DESCRIPTION
        "The value of tmnxPhysChassPowerSupId specifies a unique identifier
         index for a power supply in the physical chassis."
    ::= { tmnxPhysChassisPowerSupplyEntry 1 }

tmnxPhysChassPowerSupACStatus    OBJECT-TYPE
    SYNTAX      TmnxDeviceState
    MAX-ACCESS  read-only
    STATUS      current
    DESCRIPTION
        "The value of tmnxPhysChassPowerSupACStatus indicates the AC status of
         the power supply in the physical chassis.

         If the value is 'deviceStateOk (3)', the input AC voltage is within
         range. If the value is 'deviceStateFailed (4)', an AC voltage out of
         range condition has been detected. A value of 'deviceNotEquipped (2)'
         indicates that the AC power supply is not present."
    ::= { tmnxPhysChassisPowerSupplyEntry 2 }

tmnxPhysChassPowerSupDCStatus    OBJECT-TYPE
    SYNTAX      TmnxDeviceState
    MAX-ACCESS  read-only
    STATUS      current
    DESCRIPTION
        "The value of tmnxPhysChassPowerSupDCStatus indicates the DC status of
         the power supply in the physical chassis.

         If the value is 'deviceStateOk (3)', the output DC voltage is within
         range. If the value is 'deviceStateFailed (4)', a DC voltage out of
         range condition has been detected. A value of 'deviceNotEquipped (2)'
         indicates that the DC power supply is not present or the equipped
         power supply does not support the reporting of this status."
    ::= { tmnxPhysChassisPowerSupplyEntry 3 }

tmnxPhysChassPowerSupTempStatus  OBJECT-TYPE
    SYNTAX      TmnxDeviceState
    MAX-ACCESS  read-only
    STATUS      current
    DESCRIPTION
        "The value of tmnxPhysChassPowerSupTempStatus indicates the status of
         the power supply's temperature in the physical chassis.

         If the value is 'deviceStateOk (3)', the current temperature is within
         acceptable range. If the value is 'deviceStateFailed (4)', a
         temperature too high condition has been detected."
    ::= { tmnxPhysChassisPowerSupplyEntry 4 }

tmnxPhysChassPowerSupTempThrshld OBJECT-TYPE
    SYNTAX      Integer32
    UNITS       "degrees celsius"
    MAX-ACCESS  read-only
    STATUS      current
    DESCRIPTION
        "The value of tmnxPhysChassPowerSupTempThrshld indicates the
         temperature threshold in degrees celsius of the power supply in the
         physical chassis.

         When the temperature of the power supply raises above
         tmnxPhysChassPowerSupTempThrshld, a 'temperature too high' event will
         be generated."
    ::= { tmnxPhysChassisPowerSupplyEntry 5 }

tmnxPhysChassPowerSup1Status     OBJECT-TYPE
    SYNTAX      TmnxDeviceState
    MAX-ACCESS  read-only
    STATUS      current
    DESCRIPTION
        "The value of tmnxPhysChassPowerSup1Status indicates the overall status
         of the equipped power supply in the physical chassis.

         For AC multiple power supplies, this represents the overall status of
         the first power supply in the tray. For any other type, this
         represents the overall status of the power supply.

         If the value is 'deviceStateOk (3)', then all monitored statuses are
         'deviceStateOk (3)'. A value of 'deviceStateFailed (4)' represents a
         condition where at least one monitored status is in a failed state."
    ::= { tmnxPhysChassisPowerSupplyEntry 6 }

tmnxPhysChassPowerSup2Status     OBJECT-TYPE
    SYNTAX      TmnxDeviceState
    MAX-ACCESS  read-only
    STATUS      current
    DESCRIPTION
        "The value of tmnxPhysChassPowerSup2Status indicates the overall status
         of the equipped power supply in the physical chassis.

         For AC multiple power supplies, this represents the overall status of
         the second power supply in the tray. For any other type, this object
         is not applicable and set to 'deviceNotEquipped (2)'.

         If the value is 'deviceStateOk (3)', then all monitored statuses are
         'deviceStateOk (3)'. A value of 'deviceStateFailed (4)' represents a
         condition where at least one monitored status is in a failed state."
    ::= { tmnxPhysChassisPowerSupplyEntry 7 }

tmnxPhysChassPowerSupAssignType  OBJECT-TYPE
    SYNTAX      TmnxPowerSupAssignType
    MAX-ACCESS  read-write
    STATUS      current
    DESCRIPTION
        "The value of tmnxPhysChassPowerSupAssignType specifies the type of
         power supply that is assigned to the physical chassis. Based on the
         value assigned to this object, various power supply monitoring signals
         will be interpreted. For example, if a platform is provisioned to use
         DC power supplies, then the signal that indicates an AC power supply
         is missing can be ignored. The configuration of this object away from
         'default (4)' is required for proper generation of traps and LED
         management."
    ::= { tmnxPhysChassisPowerSupplyEntry 8 }

tmnxPhysChassPowerSupInputStatus OBJECT-TYPE
    SYNTAX      TmnxDeviceState
    MAX-ACCESS  read-only
    STATUS      current
    DESCRIPTION
        "The value of tmnxPhysChassPowerSupInputStatus indicates the status of
         the input voltage of the power supply in the physical chassis.

         If the value is 'deviceStateOk (3)', the input voltage of the power
         supply is within range. If the value is 'deviceStateFailed (4)', an
         input voltage out of range condition has been detected. A value of
         'deviceNotEquipped (2)' indicates that the power supply is not present
         in the physical chassis."
    ::= { tmnxPhysChassisPowerSupplyEntry 9 }

tmnxPhysChassPowerSupOutptStatus OBJECT-TYPE
    SYNTAX      TmnxDeviceState
    MAX-ACCESS  read-only
    STATUS      current
    DESCRIPTION
        "The value of tmnxPhysChassPowerSupOutptStatus indicates the status of
         the output voltage of the power supply in the physical chassis.

         If the value is 'deviceStateOk (3)', the output voltage of the power
         supply is within range. If the value is 'deviceStateFailed (4)', an
         output voltage out of range condition has been detected. A value of
         'deviceNotEquipped (2)' indicates that the power supply is not present
         in the physical chassis."
    ::= { tmnxPhysChassisPowerSupplyEntry 10 }

tmnxPhysChassPowerSupPemType     OBJECT-TYPE
    SYNTAX      TmnxChassisPemType
    MAX-ACCESS  read-only
    STATUS      current
    DESCRIPTION
        "The value of tmnxPhysChassPowerSupPemType indicates the Power Entry
         Module (PEM) type installed in the PEM slot for the physical chassis."
    ::= { tmnxPhysChassisPowerSupplyEntry 11 }

tmnxPhysChassPowerSupPemACRect   OBJECT-TYPE
    SYNTAX      BITS {
        acRect1 (0),
        acRect2 (1)
    }
    MAX-ACCESS  read-only
    STATUS      current
    DESCRIPTION
        "The value of tmnxPhysChassPowerSupPemACRect indicates which Power
         Entry Module AC rectifiers installed in the PEM slot are in a failed
         state or are missing for the physical chassis.

         Values:
            acRect1 (0) - the first PEM AC rectifier has failed or is missing
            acRect2 (1) - The second PEM AC rectifier has failed or is missing"
    ::= { tmnxPhysChassisPowerSupplyEntry 12 }

tmnxPhysChassPowerSupInFeedDown  OBJECT-TYPE
    SYNTAX      BITS {
        inputFeedA (0),
        inputFeedB (1)
    }
    MAX-ACCESS  read-only
    STATUS      current
    DESCRIPTION
        "The value of tmnxPhysChassPowerSupInFeedDown indicates which input
         feeds are not supplying power.

         Values:
            inputFeedA (0) - input feed A is not supplying power
            inputFeedB (1) - input feed B is not supplying power"
    ::= { tmnxPhysChassisPowerSupplyEntry 13 }

tmnxPhysChassPowerSupFanDir      OBJECT-TYPE
    SYNTAX      INTEGER {
        unknown     (0),
        frontToBack (1),
        backToFront (2)
    }
    MAX-ACCESS  read-only
    STATUS      current
    DESCRIPTION
        "The value of tmnxPhysChassPowerSupFanDir indicates the direction of
         the power supply's fan in the physical chassis.

         Values:
             unknown     (0) - fan direction is unknown
             frontToBack (1) - fan direction is from front of chassis to back
             backToFront (2) - fan direction is from back of chassis to front"
    ::= { tmnxPhysChassisPowerSupplyEntry 14 }

tmnxPhysChassisPEQTableLastChg   OBJECT-TYPE
    SYNTAX      TimeStamp
    MAX-ACCESS  read-only
    STATUS      current
    DESCRIPTION
        "The value of tmnxPhysChassisPEQTableLastChg indicates the time, since
         system startup, that a row in the tmnxPhysChassisPEQTable last changed
         configuration."
    ::= { tmnxPhysChassisObjs 3 }

tmnxPhysChassisPEQTable          OBJECT-TYPE
    SYNTAX      SEQUENCE OF TmnxPhysChassisPEQEntry
    MAX-ACCESS  not-accessible
    STATUS      current
    DESCRIPTION
        "The tmnxPhysChassisPEQTable contains information about Power Equalizer
         type in the physical chassis.

         This table replaces tmnxChassisPEQTable in release 15.0 of SROS series
         systems."
    ::= { tmnxPhysChassisObjs 4 }

tmnxPhysChassisPEQEntry          OBJECT-TYPE
    SYNTAX      TmnxPhysChassisPEQEntry
    MAX-ACCESS  not-accessible
    STATUS      current
    DESCRIPTION
        "Each row entry represents a Nokia SROS series PEQ slot.

         This table augments the tmnxPhysChassisPowerSupplyTable on physical
         chassis that support PEQs.

         Rows in this table are created by the agent at initialization and
         cannot be created or destroyed by SNMP Get or Set requests."
    AUGMENTS    { tmnxPhysChassisPowerSupplyEntry }
    ::= { tmnxPhysChassisPEQTable 1 }

TmnxPhysChassisPEQEntry          ::= SEQUENCE
{
    tmnxPhysChassisPEQLastChangeTime TimeStamp,
    tmnxPhysChassisPEQAssignedType   TmnxPEQType,
    tmnxPhysChassisPEQEquippedType   TmnxPEQType,
    tmnxPhysChassisPEQSupportedTypes TmnxPEQSuppType,
    tmnxPhysChassisPEQAvailableWatt  Unsigned32,
    tmnxPhysChassisPEQInputPowerMode Unsigned32
}

tmnxPhysChassisPEQLastChangeTime OBJECT-TYPE
    SYNTAX      TimeStamp
    MAX-ACCESS  read-only
    STATUS      current
    DESCRIPTION
        "The value of tmnxPhysChassisPEQLastChangeTime indicates the time,
         since system startup, that an object in this row changed
         configuration."
    ::= { tmnxPhysChassisPEQEntry 1 }

tmnxPhysChassisPEQAssignedType   OBJECT-TYPE
    SYNTAX      TmnxPEQType
    MAX-ACCESS  read-write
    STATUS      current
    DESCRIPTION
        "The value of tmnxPhysChassisPEQAssignedType specifies the
         administratively assigned (pre-provisioned) PEQ type defined in the
         tmnxPEQTypeTable that should occupy this PEQ slot in the chassis.  If
         tmnxPhysChassisPEQAssignedType has a value of 1 (unassigned), this slot
         has not yet been pre-provisioned."
    DEFVAL      { 1 }
    ::= { tmnxPhysChassisPEQEntry 2 }

tmnxPhysChassisPEQEquippedType   OBJECT-TYPE
    SYNTAX      TmnxPEQType
    MAX-ACCESS  read-only
    STATUS      current
    DESCRIPTION
        "The value of tmnxPhysChassisPEQEquippedType indicates the PEQ type of
         the PEQ that is physically inserted into this PEQ slot in the chassis.
         If the slot has been pre-provisioned, tmnxPhysChassisPEQAssignedType
         is not equal to 1 (unassigned), and the value of
         tmnxPhysChassisPEQEquippedType is not the same as
         tmnxPhysChassisPEQAssignedType, a mismatch alarm will be raised.

         A value of 0 indicates the PEQ type is not recognized by the SROS."
    ::= { tmnxPhysChassisPEQEntry 3 }

tmnxPhysChassisPEQSupportedTypes OBJECT-TYPE
    SYNTAX      TmnxPEQSuppType
    MAX-ACCESS  read-only
    STATUS      current
    DESCRIPTION
        "The value of tmnxPhysChassisPEQSupportedTypes is a bit-mask that
         indicates what PEQ types can be physically supported in this PEQ slot
         in this chassis."
    ::= { tmnxPhysChassisPEQEntry 4 }

tmnxPhysChassisPEQAvailableWatt  OBJECT-TYPE
    SYNTAX      Unsigned32
    UNITS       "watts"
    MAX-ACCESS  read-only
    STATUS      current
    DESCRIPTION
        "The value of tmnxPhysChassisPEQAvailableWatt indicates the reported
         available wattage of the PEQ."
    ::= { tmnxPhysChassisPEQEntry 5 }

tmnxPhysChassisPEQInputPowerMode OBJECT-TYPE
    SYNTAX      Unsigned32 (0 | 60 | 80)
    UNITS       "amps"
    MAX-ACCESS  read-write
    STATUS      current
    DESCRIPTION
        "The value of tmnxPhysChassisPEQInputPowerMode specifies the input
         power mode of the PEQ.

         A value of zero indicates that the input power mode is not applicable
         for the PEQ. An SNMP SET request with a value of zero is not
         permitted."
    ::= { tmnxPhysChassisPEQEntry 6 }

tmnxSlotObjs                     OBJECT IDENTIFIER ::= { tmnxHwObjs 2 }

tmnxCardObjs                     OBJECT IDENTIFIER ::= { tmnxHwObjs 3 }

tmnxCardLastChange               OBJECT-TYPE
    SYNTAX      TimeStamp
    MAX-ACCESS  read-only
    STATUS      current
    DESCRIPTION
        "The value of sysUpTime when the tmnxCardTable was last changed."
    ::= { tmnxCardObjs 1 }

tmnxCardTable                    OBJECT-TYPE
    SYNTAX      SEQUENCE OF TmnxCardEntry
    MAX-ACCESS  not-accessible
    STATUS      current
    DESCRIPTION
        "The tmnxCardTable has an entry for each IOM card slot in each chassis
         in the TMNX system."
    ::= { tmnxCardObjs 2 }

tmnxCardEntry                    OBJECT-TYPE
    SYNTAX      TmnxCardEntry
    MAX-ACCESS  not-accessible
    STATUS      current
    DESCRIPTION
        "Each row entry represents an IOM card slot in a chassis in the
         system.  Entries cannot be created and deleted via SNMP SET
         operations.  When a tmnxChassisEntry is created, a tmnxCardEntry
         is created for each IOM card slot in that chassis.  Before a
         tmnxChassisEntry can be deleted, each tmnxCardEntry for that
         chassis must be in the proper state for removal."
    INDEX       {
        tmnxChassisIndex,
        tmnxCardSlotNum
    }
    ::= { tmnxCardTable 1 }

TmnxCardEntry                    ::= SEQUENCE
{
    tmnxCardSlotNum                  TmnxSlotNum,
    tmnxCardSupportedTypes           TmnxCardSuppType,
    tmnxCardAllowedTypes             TmnxCardType,
    tmnxCardAssignedType             TmnxCardType,
    tmnxCardEquippedType             TmnxCardType,
    tmnxCardHwIndex                  TmnxHwIndex,
    tmnxCardClockSource              TItemDescription,
    tmnxCardNumMdaSlots              Unsigned32,
    tmnxCardNumMdas                  Unsigned32,
    tmnxCardReboot                   TmnxCardRebootType,
    tmnxCardMemorySize               Unsigned32,
    tmnxCardNamedPoolAdminMode       TmnxAdminStateOld,
    tmnxCardNamedPoolOperMode        TmnxAdminState,
    tmnxCardSoftReset                TmnxActionType,
    tmnxCardLastBootupReason         INTEGER,
    tmnxCardCmplx1IngrFcsOccur       Counter32,
    tmnxCardCmplx1IngrFcsOccurTime   TimeStamp,
    tmnxCardCmplx1EgrFcsOccur        Counter32,
    tmnxCardCmplx1EgrFcsOccurTime    TimeStamp,
    tmnxCardCmplx2IngrFcsOccur       Counter32,
    tmnxCardCmplx2IngrFcsOccurTime   TimeStamp,
    tmnxCardCmplx2EgrFcsOccur        Counter32,
    tmnxCardCmplx2EgrFcsOccurTime    TimeStamp,
    tmnxCardCmplx1MemParityOccur     Counter32,
    tmnxCardCmplx1MemParityOccurTime TimeStamp,
    tmnxCardCmplx2MemParityOccur     Counter32,
    tmnxCardCmplx2MemParityOccurTime TimeStamp,
    tmnxCardCapability               BITS,
    tmnxCardCmplx1CAMErrorOccur      Counter32,
    tmnxCardCmplx1CAMErrorOccurTime  TimeStamp,
    tmnxCardCmplx2CAMErrorOccur      Counter32,
    tmnxCardCmplx2CAMErrorOccurTime  TimeStamp,
    tmnxCardFailOnError              BITS,
    tmnxCardCmplx1EgrFcsSrcSlots     TmnxCardSlotBitMap,
    tmnxCardCmplx2EgrFcsSrcSlots     TmnxCardSlotBitMap,
    tmnxCardHardResetUnsupMdas       TruthValue,
    tmnxCardCmpl1BufMemErrOccur      Counter32,
    tmnxCardCmpl1BufMemErrOccurTime  TimeStamp,
    tmnxCardCmpl2BufMemErrOccur      Counter32,
    tmnxCardCmpl2BufMemErrOccurTime  TimeStamp,
    tmnxCardCmpl1StatMemErrOccur     Counter32,
    tmnxCardCmpl1StatMemErrOccurTime TimeStamp,
    tmnxCardCmpl2StatMemErrOccur     Counter32,
    tmnxCardCmpl2StatMemErrOccurTime TimeStamp,
    tmnxCardCmpl1IntMemErrOccur      Counter32,
    tmnxCardCmpl1IntMemErrOccurTime  TimeStamp,
    tmnxCardCmpl2IntMemErrOccur      Counter32,
    tmnxCardCmpl2IntMemErrOccurTime  TimeStamp,
    tmnxCardCmpl1ChipIfDownOcc       Counter32,
    tmnxCardCmpl1ChipIfDownOccTime   TimeStamp,
    tmnxCardCmpl2ChipIfDownOcc       Counter32,
    tmnxCardCmpl2ChipIfDownOccTime   TimeStamp,
    tmnxCardCmpl1ChipIfCellOcc       Counter32,
    tmnxCardCmpl1ChipIfCellOccTime   TimeStamp,
    tmnxCardCmpl2ChipIfCellOcc       Counter32,
    tmnxCardCmpl2ChipIfCellOccTime   TimeStamp,
    tmnxCardResetOnRecoverableError  TruthValue
}

tmnxCardSlotNum                  OBJECT-TYPE
    SYNTAX      TmnxSlotNum
    MAX-ACCESS  not-accessible
    STATUS      current
    DESCRIPTION
        "The unique value which identifies this IOM slot within a chassis in
         the system."
    ::= { tmnxCardEntry 1 }

tmnxCardSupportedTypes           OBJECT-TYPE
    SYNTAX      TmnxCardSuppType
    MAX-ACCESS  read-only
    STATUS      current
    DESCRIPTION
        "A bit-mask that indicates what card types can be physically supported
         in this IOM slot in this chassis."
    ::= { tmnxCardEntry 2 }

tmnxCardAllowedTypes             OBJECT-TYPE
    SYNTAX      TmnxCardType
    MAX-ACCESS  read-write
    STATUS      obsolete
    DESCRIPTION
        "A bit-mask that specifies what IOM card types the administrator
         has designated be allowed to be inserted into this slot.
         If the slot has not-been pre-provisioned and a card that
         does not match one of the allowed types is inserted into
         this slot, a mismatch alarm will be raised.  If a specific
         value has not yet been SET by the manager, tmnxCardAllowedTypes
         will return the same value to a GET request as
         tmnxCardSupportedTypes.

         The object was made obsolete in the 3.0 release."
    ::= { tmnxCardEntry 3 }

tmnxCardAssignedType             OBJECT-TYPE
    SYNTAX      TmnxCardType
    MAX-ACCESS  read-write
    STATUS      current
    DESCRIPTION
        "The tmnxCardAssignedType specifies the administratively assigned
         (pre-provisioned) IOM card type defined in the tmnxCardTypeTable that
         should occupy this slot in this chassis.  If tmnxCardAssignedType has
         a value of 1 (unassigned), this slot has not yet been pre-provisioned."
    DEFVAL      { 1 }
    ::= { tmnxCardEntry 4 }

tmnxCardEquippedType             OBJECT-TYPE
    SYNTAX      TmnxCardType
    MAX-ACCESS  read-only
    STATUS      current
    DESCRIPTION
        "The tmnxCardEquippedType indicates the IOM card type that is physically
         inserted into this slot in this chassis.  If the slot has been
         pre-provisioned, tmnxCardAssignedType is not equal to 1 (unassigned),
         and the value of tmnxCardEquippedType is not the same as
         tmnxCardAssignedType, a mismatch alarm will be raised.

         A value of 0 indicates the IOM card type is not recognized by the
         software."
    ::= { tmnxCardEntry 5 }

tmnxCardHwIndex                  OBJECT-TYPE
    SYNTAX      TmnxHwIndex
    MAX-ACCESS  read-only
    STATUS      current
    DESCRIPTION
        "The value of tmnxCardHwIndex is the index into the tmnxHwTable for the
         row entry that represents the hardware component information for this
         IOM card."
    ::= { tmnxCardEntry 6 }

tmnxCardClockSource              OBJECT-TYPE
    SYNTAX      TItemDescription
    MAX-ACCESS  read-only
    STATUS      current
    DESCRIPTION
        "The clock source used by the IOM card in this slot."
    ::= { tmnxCardEntry 10 }

tmnxCardNumMdaSlots              OBJECT-TYPE
    SYNTAX      Unsigned32
    MAX-ACCESS  read-only
    STATUS      current
    DESCRIPTION
        "The number of Media Dependent Adapter (MDA) slots available on this
         IOM card."
    ::= { tmnxCardEntry 11 }

tmnxCardNumMdas                  OBJECT-TYPE
    SYNTAX      Unsigned32
    MAX-ACCESS  read-only
    STATUS      current
    DESCRIPTION
        "The number of Media Dependent Adapters installed on this IOM card."
    ::= { tmnxCardEntry 12 }

tmnxCardReboot                   OBJECT-TYPE
    SYNTAX      TmnxCardRebootType
    MAX-ACCESS  read-write
    STATUS      current
    DESCRIPTION
        "Setting this variable to 'cardReboot' causes the IOM card to execute a
         soft-reboot. Setting this variable to 'cardPowerCycle' causes the IOM
         to turn off and turn on power to the card initiating a hard-reboot."
    DEFVAL      { notApplicable }
    ::= { tmnxCardEntry 13 }

tmnxCardMemorySize               OBJECT-TYPE
    SYNTAX      Unsigned32
    UNITS       "Mega-bytes"
    MAX-ACCESS  read-only
    STATUS      current
    DESCRIPTION
        "The value of tmnxCardMemorySize indicates the amount of memory, in
         mega-bytes, populated on this IOM card."
    ::= { tmnxCardEntry 14 }

tmnxCardNamedPoolAdminMode       OBJECT-TYPE
    SYNTAX      TmnxAdminStateOld
    MAX-ACCESS  read-write
    STATUS      current
    DESCRIPTION
        "The value of tmnxCardNamedPoolAdminMode specifies whether or not an
         IOM is provisioned for the configuration of named pools. If the value
         of tmnxCardNamedPoolAdminMode is 'inService(2)', the system will
         change the way default pools are created and allow for the creation of
         MDA and port level named buffer pools. If the value of
         tmnxCardNamedPoolAdminMode is 'outOfService(3)', the system will not
         create per port pools, instead a default network and access pool is
         created for ingress and egress and is shared by queues on all ports.
         This object is used in conjunction with tmnxCardNamedPoolOperMode."
    DEFVAL      { outOfService }
    ::= { tmnxCardEntry 15 }

tmnxCardNamedPoolOperMode        OBJECT-TYPE
    SYNTAX      TmnxAdminState
    MAX-ACCESS  read-only
    STATUS      current
    DESCRIPTION
        "The value of tmnxCardNamedPoolOperMode indicates whether or not an IOM
         provisioned with tmnxCardNamedPoolAdminMode to a value of
         'inService(2)' will actively use named pools or not. A value of
         'outOfService(3) means that the named pool configurations will not be
         downloaded to the IOM until after a reset of the IOM is performed. A
         value of 'inService(2)' means that the named pool configurations are
         programmed by the IOM. On systems using a separate CPM and IOM
         combination the value of tmnxCardNamedPoolOperMode and
         tmnxCardNamedPoolAdminMode will always be in sync due to a mandatory
         reboot of the IOM. On systems using a combined image (CFM) these
         values will be out-of-sync until the chassis is rebooted."
    DEFVAL      { outOfService }
    ::= { tmnxCardEntry 16 }

tmnxCardSoftReset                OBJECT-TYPE
    SYNTAX      TmnxActionType
    MAX-ACCESS  read-write
    STATUS      current
    DESCRIPTION
        "The value of tmnxCardSoftReset, when set to 'doAction(1)', causes the
         IOM card to re-initialize the applications and protocols running on
         the card with limited traffic impact."
    DEFVAL      { notApplicable }
    ::= { tmnxCardEntry 17 }

tmnxCardLastBootupReason         OBJECT-TYPE
    SYNTAX      INTEGER {
        hardReboot     (0),
        softReset      (1),
        powerCycle     (2),
        clearCard      (3),
        activitySwitch (4),
        configChange   (5),
        runtimeFail    (6),
        bootFail       (7),
        unexpected     (8),
        issuTimeout    (9),
        reinserted     (10),
        issuHardReboot (11),
        ccmFail        (12),
        powerChange    (13)
    }
    MAX-ACCESS  read-only
    STATUS      current
    DESCRIPTION
        "The value of tmnxCardLastBootupReason indicates the type of the last
         reboot/reset of the IOM card.

         Not all reasons exist in all software versions.

         hardReboot     - new/different card inserted for first time
         softReset      - user initiated soft reset
         powerCycle     - user initiated power cycle
         clearCard      - user initiated clear card
         activitySwitch - card rebooted during activity switch
         configChange   - configuration change forced a reboot
         runtimeFail    - card failed while running and was rebooted
         bootFail       - card failed during boot and was rebooted
         unexpected     - card unexpectedly rebooted
         issuTimeout    - ISSU timeout timer expired
         reinserted     - card was removed and reinserted
         issuHardReboot - card rebooted during ISSU upgrade
                             (soft reset ineligible)
         ccmFail        - Chassis Control Module (CCM) failed.
         powerChange    - Power availability changed."
    ::= { tmnxCardEntry 18 }

tmnxCardCmplx1IngrFcsOccur       OBJECT-TYPE
    SYNTAX      Counter32
    MAX-ACCESS  read-only
    STATUS      current
    DESCRIPTION
        "The value of tmnxCardCmplx1IngrFcsOccur indicates the number of times
         the first complex experienced an occurrence of an FCS error in the
         ingress direction since startup, last clear, or IOM reboot."
    ::= { tmnxCardEntry 19 }

tmnxCardCmplx1IngrFcsOccurTime   OBJECT-TYPE
    SYNTAX      TimeStamp
    MAX-ACCESS  read-only
    STATUS      current
    DESCRIPTION
        "The value of tmnxCardCmplx1IngrFcsOccurTime indicates the last time
         tmnxCardCmplx1IngrFcsOccur incremented."
    ::= { tmnxCardEntry 20 }

tmnxCardCmplx1EgrFcsOccur        OBJECT-TYPE
    SYNTAX      Counter32
    MAX-ACCESS  read-only
    STATUS      current
    DESCRIPTION
        "The value of tmnxCardCmplx1EgrFcsOccur indicates the number of times
         the first complex experienced an occurrence of an FCS error in the
         egress direction since startup, last clear, or IOM reboot."
    ::= { tmnxCardEntry 21 }

tmnxCardCmplx1EgrFcsOccurTime    OBJECT-TYPE
    SYNTAX      TimeStamp
    MAX-ACCESS  read-only
    STATUS      current
    DESCRIPTION
        "The value of tmnxCardCmplx1EgrFcsOccurTime indicates the last time
         tmnxCardCmplx1EgrFcsOccur incremented."
    ::= { tmnxCardEntry 22 }

tmnxCardCmplx2IngrFcsOccur       OBJECT-TYPE
    SYNTAX      Counter32
    MAX-ACCESS  read-only
    STATUS      current
    DESCRIPTION
        "The value of tmnxCardCmplx2IngrFcsOccur indicates the number of times
         the second complex experienced an occurrence of an FCS error in the
         ingress direction since startup, last clear, or IOM reboot."
    ::= { tmnxCardEntry 23 }

tmnxCardCmplx2IngrFcsOccurTime   OBJECT-TYPE
    SYNTAX      TimeStamp
    MAX-ACCESS  read-only
    STATUS      current
    DESCRIPTION
        "The value of tmnxCardCmplx2IngrFcsOccurTime indicates the last time
         tmnxCardCmplx2IngrFcsOccur incremented."
    ::= { tmnxCardEntry 24 }

tmnxCardCmplx2EgrFcsOccur        OBJECT-TYPE
    SYNTAX      Counter32
    MAX-ACCESS  read-only
    STATUS      current
    DESCRIPTION
        "The value of tmnxCardCmplx2EgrFcsOccur indicates the number of times
         the second complex experienced an occurrence of an FCS error in the
         egress direction since startup, last clear, or IOM reboot."
    ::= { tmnxCardEntry 25 }

tmnxCardCmplx2EgrFcsOccurTime    OBJECT-TYPE
    SYNTAX      TimeStamp
    MAX-ACCESS  read-only
    STATUS      current
    DESCRIPTION
        "The value of tmnxCardCmplx2EgrFcsOccurTime indicates the last time
         tmnxCardCmplx2EgrFcsOccur incremented."
    ::= { tmnxCardEntry 26 }

tmnxCardCmplx1MemParityOccur     OBJECT-TYPE
    SYNTAX      Counter32
    MAX-ACCESS  read-only
    STATUS      current
    DESCRIPTION
        "The value of tmnxCardCmplx1MemParityOccur indicates the number of
         times the first complex experienced an occurrence of a memory parity
         error since startup, last clear, or IOM reboot."
    ::= { tmnxCardEntry 27 }

tmnxCardCmplx1MemParityOccurTime OBJECT-TYPE
    SYNTAX      TimeStamp
    MAX-ACCESS  read-only
    STATUS      current
    DESCRIPTION
        "The value of tmnxCardCmplx1MemParityOccurTime indicates the last time
         tmnxCardCmplx1MemParityOccur incremented."
    ::= { tmnxCardEntry 28 }

tmnxCardCmplx2MemParityOccur     OBJECT-TYPE
    SYNTAX      Counter32
    MAX-ACCESS  read-only
    STATUS      current
    DESCRIPTION
        "The value of tmnxCardCmplx2MemParityOccur indicates the number of
         times the second complex experienced an occurrence of a memory parity
         error since startup, last clear, or IOM reboot."
    ::= { tmnxCardEntry 29 }

tmnxCardCmplx2MemParityOccurTime OBJECT-TYPE
    SYNTAX      TimeStamp
    MAX-ACCESS  read-only
    STATUS      current
    DESCRIPTION
        "The value of tmnxCardCmplx2MemParityOccurTime indicates the last time
         tmnxCardCmplx2MemParityOccur incremented."
    ::= { tmnxCardEntry 30 }

tmnxCardCapability               OBJECT-TYPE
    SYNTAX      BITS {
        sr (0)
    }
    MAX-ACCESS  read-write
    STATUS      current
    DESCRIPTION
        "The value of tmnxCardCapability indicates special capabilities that
         are set on this card.

         tmnxCardCapability is a bitmap with the following values:
            'sr': Enable SR capabilities on this card. "
    ::= { tmnxCardEntry 31 }

tmnxCardCmplx1CAMErrorOccur      OBJECT-TYPE
    SYNTAX      Counter32
    MAX-ACCESS  read-only
    STATUS      current
    DESCRIPTION
        "The value of tmnxCardCmplx1CAMErrorOccur indicates the number of times
         the first complex experienced an occurrence of a CAM error since
         startup, last clear, or IOM reboot."
    ::= { tmnxCardEntry 32 }

tmnxCardCmplx1CAMErrorOccurTime  OBJECT-TYPE
    SYNTAX      TimeStamp
    MAX-ACCESS  read-only
    STATUS      current
    DESCRIPTION
        "The value of tmnxCardCmplx1CAMErrorOccurTime indicates the last time
         tmnxCardCmplx1CAMErrorOccur incremented."
    ::= { tmnxCardEntry 33 }

tmnxCardCmplx2CAMErrorOccur      OBJECT-TYPE
    SYNTAX      Counter32
    MAX-ACCESS  read-only
    STATUS      current
    DESCRIPTION
        "The value of tmnxCardCmplx2CAMErrorOccur indicates the number of times
         the second complex experienced an occurrence of a CAM error since
         startup, last clear, or IOM reboot."
    ::= { tmnxCardEntry 34 }

tmnxCardCmplx2CAMErrorOccurTime  OBJECT-TYPE
    SYNTAX      TimeStamp
    MAX-ACCESS  read-only
    STATUS      current
    DESCRIPTION
        "The value of tmnxCardCmplx2CAMErrorOccurTime indicates the last time
         tmnxCardCmplx2CAMErrorOccur incremented."
    ::= { tmnxCardEntry 35 }

tmnxCardFailOnError              OBJECT-TYPE
    SYNTAX      BITS {
        memoryEventGroupA (0)
    }
    MAX-ACCESS  read-write
    STATUS      current
    DESCRIPTION
        "The value of tmnxCardFailOnError specifies the set of events that, if
         triggered, will cause the card to fail. The suppression or generation
         of the NOTIFICATION-TYPE event is independent of the card failing.

         The following set of events are configurable:
              memoryEventGroupA (0) - tmnxEqCardPChipMemoryEvent
                                      tmnxEqCardPChipCamEvent
                                      tmnxEqCardPChipError
                                      tmnxEqCardQChipBufMemoryEvent
                                      tmnxEqCardQChipStatsMemoryEvent
                                      tmnxEqCardQChipIntMemoryEvent
                                      tmnxEqCardChipIfCellEvent

         tmnxEqCardPChipError will only cause a card failure if all MDAs(s) on
         the complex are Ethernet or ISAs."
    DEFVAL      { {} }
    ::= { tmnxCardEntry 36 }

tmnxCardCmplx1EgrFcsSrcSlots     OBJECT-TYPE
    SYNTAX      TmnxCardSlotBitMap
    MAX-ACCESS  read-only
    STATUS      current
    DESCRIPTION
        "The value of tmnxCardCmplx1EgrFcsSrcSlots indicates the source slots
         reported from the last time tmnxCardCmplx1EgrFcsOccur incremented."
    ::= { tmnxCardEntry 37 }

tmnxCardCmplx2EgrFcsSrcSlots     OBJECT-TYPE
    SYNTAX      TmnxCardSlotBitMap
    MAX-ACCESS  read-only
    STATUS      current
    DESCRIPTION
        "The value of tmnxCardCmplx2EgrFcsSrcSlots indicates the source slots
         reported from the last time tmnxCardCmplx2EgrFcsOccur incremented."
    ::= { tmnxCardEntry 38 }

tmnxCardHardResetUnsupMdas       OBJECT-TYPE
    SYNTAX      TruthValue
    MAX-ACCESS  read-write
    STATUS      current
    DESCRIPTION
        "The value of tmnxCardHardResetUnsupMdas specifies whether to do hard
         reset of the soft reset incapable MDAs as part setting 'doAction' to
         tmnxCardSoftReset object."
    DEFVAL      { false }
    ::= { tmnxCardEntry 39 }

tmnxCardCmpl1BufMemErrOccur      OBJECT-TYPE
    SYNTAX      Counter32
    MAX-ACCESS  read-only
    STATUS      current
    DESCRIPTION
        "The value of tmnxCardCmpl1BufMemErrOccur indicates the number of times
         the first complex experienced an occurrence of a buffer memory error
         since startup, last clear, or IOM reboot."
    ::= { tmnxCardEntry 40 }

tmnxCardCmpl1BufMemErrOccurTime  OBJECT-TYPE
    SYNTAX      TimeStamp
    MAX-ACCESS  read-only
    STATUS      current
    DESCRIPTION
        "The value of tmnxCardCmpl1BufMemErrOccurTime indicates the last time
         tmnxCardCmpl1BufMemErrOccur incremented."
    ::= { tmnxCardEntry 41 }

tmnxCardCmpl2BufMemErrOccur      OBJECT-TYPE
    SYNTAX      Counter32
    MAX-ACCESS  read-only
    STATUS      current
    DESCRIPTION
        "The value of tmnxCardCmpl2BufMemErrOccur indicates the number of times
         the second complex experienced an occurrence of a buffer memory error
         since startup, last clear, or IOM reboot."
    ::= { tmnxCardEntry 42 }

tmnxCardCmpl2BufMemErrOccurTime  OBJECT-TYPE
    SYNTAX      TimeStamp
    MAX-ACCESS  read-only
    STATUS      current
    DESCRIPTION
        "The value of tmnxCardCmpl2BufMemErrOccurTime indicates the last time
         tmnxCardCmpl2BufMemErrOccur incremented."
    ::= { tmnxCardEntry 43 }

tmnxCardCmpl1StatMemErrOccur     OBJECT-TYPE
    SYNTAX      Counter32
    MAX-ACCESS  read-only
    STATUS      current
    DESCRIPTION
        "The value of tmnxCardCmpl1StatMemErrOccur indicates the number of
         times the first complex experienced an occurrence of a statistics
         memory error since startup, last clear, or IOM reboot."
    ::= { tmnxCardEntry 44 }

tmnxCardCmpl1StatMemErrOccurTime OBJECT-TYPE
    SYNTAX      TimeStamp
    MAX-ACCESS  read-only
    STATUS      current
    DESCRIPTION
        "The value of tmnxCardCmpl1StatMemErrOccurTime indicates the last time
         tmnxCardCmpl1StatMemErrOccur incremented."
    ::= { tmnxCardEntry 45 }

tmnxCardCmpl2StatMemErrOccur     OBJECT-TYPE
    SYNTAX      Counter32
    MAX-ACCESS  read-only
    STATUS      current
    DESCRIPTION
        "The value of tmnxCardCmpl2StatMemErrOccur indicates the number of
         times the second complex experienced an occurrence of a statistics
         memory error since startup, last clear, or IOM reboot."
    ::= { tmnxCardEntry 46 }

tmnxCardCmpl2StatMemErrOccurTime OBJECT-TYPE
    SYNTAX      TimeStamp
    MAX-ACCESS  read-only
    STATUS      current
    DESCRIPTION
        "The value of tmnxCardCmpl2StatMemErrOccurTime indicates the last time
         tmnxCardCmpl2StatMemErrOccur incremented."
    ::= { tmnxCardEntry 47 }

tmnxCardCmpl1IntMemErrOccur      OBJECT-TYPE
    SYNTAX      Counter32
    MAX-ACCESS  read-only
    STATUS      current
    DESCRIPTION
        "The value of tmnxCardCmpl1IntMemErrOccur indicates the number of times
         the first complex experienced an occurrence of an internal memory
         error since startup, last clear, or IOM reboot."
    ::= { tmnxCardEntry 48 }

tmnxCardCmpl1IntMemErrOccurTime  OBJECT-TYPE
    SYNTAX      TimeStamp
    MAX-ACCESS  read-only
    STATUS      current
    DESCRIPTION
        "The value of tmnxCardCmpl1IntMemErrOccurTime indicates the last time
         tmnxCardCmpl1IntMemErrOccur incremented."
    ::= { tmnxCardEntry 49 }

tmnxCardCmpl2IntMemErrOccur      OBJECT-TYPE
    SYNTAX      Counter32
    MAX-ACCESS  read-only
    STATUS      current
    DESCRIPTION
        "The value of tmnxCardCmpl2IntMemErrOccur indicates the number of times
         the second complex experienced an occurrence of an internal memory
         error since startup, last clear, or IOM reboot."
    ::= { tmnxCardEntry 50 }

tmnxCardCmpl2IntMemErrOccurTime  OBJECT-TYPE
    SYNTAX      TimeStamp
    MAX-ACCESS  read-only
    STATUS      current
    DESCRIPTION
        "The value of tmnxCardCmpl2IntMemErrOccurTime indicates the last time
         tmnxCardCmpl2IntMemErrOccur incremented."
    ::= { tmnxCardEntry 51 }

tmnxCardCmpl1ChipIfDownOcc       OBJECT-TYPE
    SYNTAX      Counter32
    MAX-ACCESS  read-only
    STATUS      current
    DESCRIPTION
        "The value of tmnxCardCmpl1ChipIfDownOcc indicates the number of times
         the first complex experienced an occurrence of an internal datapath
         problem."
    ::= { tmnxCardEntry 52 }

tmnxCardCmpl1ChipIfDownOccTime   OBJECT-TYPE
    SYNTAX      TimeStamp
    MAX-ACCESS  read-only
    STATUS      current
    DESCRIPTION
        "The value of tmnxCardCmpl1ChipIfDownOccTime indicates the last time
         tmnxCardCmpl1ChipIfDownOcc incremented."
    ::= { tmnxCardEntry 53 }

tmnxCardCmpl2ChipIfDownOcc       OBJECT-TYPE
    SYNTAX      Counter32
    MAX-ACCESS  read-only
    STATUS      current
    DESCRIPTION
        "The value of tmnxCardCmpl2ChipIfDownOcc indicates the number of times
         the second complex experienced an occurrence of an internal datapath
         problem."
    ::= { tmnxCardEntry 54 }

tmnxCardCmpl2ChipIfDownOccTime   OBJECT-TYPE
    SYNTAX      TimeStamp
    MAX-ACCESS  read-only
    STATUS      current
    DESCRIPTION
        "The value of tmnxCardCmpl2ChipIfDownOccTime indicates the last time
         tmnxCardCmpl2ChipIfDownOcc incremented."
    ::= { tmnxCardEntry 55 }

tmnxCardCmpl1ChipIfCellOcc       OBJECT-TYPE
    SYNTAX      Counter32
    MAX-ACCESS  read-only
    STATUS      current
    DESCRIPTION
        "The value of tmnxCardCmpl1ChipIfCellOcc indicates the number of times
         the first complex experienced an occurrence of internal datapath cell
         errors."
    ::= { tmnxCardEntry 56 }

tmnxCardCmpl1ChipIfCellOccTime   OBJECT-TYPE
    SYNTAX      TimeStamp
    MAX-ACCESS  read-only
    STATUS      current
    DESCRIPTION
        "The value of tmnxCardCmpl1ChipIfCellOccTime indicates the last time
         tmnxCardCmpl1ChipIfCellOcc incremented."
    ::= { tmnxCardEntry 57 }

tmnxCardCmpl2ChipIfCellOcc       OBJECT-TYPE
    SYNTAX      Counter32
    MAX-ACCESS  read-only
    STATUS      current
    DESCRIPTION
        "The value of tmnxCardCmpl2ChipIfCellOcc indicates the number of times
         the second complex experienced an occurrence of internal datapath cell
         errors."
    ::= { tmnxCardEntry 58 }

tmnxCardCmpl2ChipIfCellOccTime   OBJECT-TYPE
    SYNTAX      TimeStamp
    MAX-ACCESS  read-only
    STATUS      current
    DESCRIPTION
        "The value of tmnxCardCmpl2ChipIfCellOccTime indicates the last time
         tmnxCardCmpl2ChipIfCellOcc incremented."
    ::= { tmnxCardEntry 59 }

tmnxCardResetOnRecoverableError  OBJECT-TYPE
    SYNTAX      TruthValue
    MAX-ACCESS  read-write
    STATUS      current
    DESCRIPTION
        "The value of tmnxCardResetOnRecoverableError specifies whether or not
         the system resets the card when there are fatal memory parity errors
         on one of the Q-chips on that card.

         If the value of tmnxCardResetOnRecoverableError is 'true (1)' and
         there is a fatal memory parity error on a Q-chip, the system will
         reset the card but not fail it, even if tmnxCardFailOnError is 'true
         (1)'."
    DEFVAL      { false }
    ::= { tmnxCardEntry 60 }

tmnxCpmCardLastChange            OBJECT-TYPE
    SYNTAX      TimeStamp
    MAX-ACCESS  read-only
    STATUS      current
    DESCRIPTION
        "The value of sysUpTime when the tmnxCpmCardTable was last changed."
    ::= { tmnxCardObjs 3 }

tmnxCpmCardTable                 OBJECT-TYPE
    SYNTAX      SEQUENCE OF TmnxCpmCardEntry
    MAX-ACCESS  not-accessible
    STATUS      current
    DESCRIPTION
        "The tmnxCpmCardTable has an entry for each CPM card or module in each
         chassis in the TMNX system."
    ::= { tmnxCardObjs 4 }

tmnxCpmCardEntry                 OBJECT-TYPE
    SYNTAX      TmnxCpmCardEntry
    MAX-ACCESS  not-accessible
    STATUS      current
    DESCRIPTION
        "Each row entry represents a CPM card or module in a chassis in the
         system.  Entries cannot be created and deleted via SNMP SET
         operations.  When a tmnxChassisEntry is created, a tmnxCpmCardEntry
         is created for each CPM card or module in that chassis.  Before a
         tmnxChassisEntry can be deleted, each tmnxCpmCardEntry for that
         chassis must be in the proper state for removal."
    INDEX       {
        tmnxChassisIndex,
        tmnxCpmCardSlotNum,
        tmnxCpmCardNum
    }
    ::= { tmnxCpmCardTable 1 }

TmnxCpmCardEntry                 ::= SEQUENCE
{
    tmnxCpmCardSlotNum               TmnxSlotNum,
    tmnxCpmCardNum                   Unsigned32,
    tmnxCpmCardSupportedTypes        TmnxCardSuppType,
    tmnxCpmCardAllowedTypes          TmnxCardType,
    tmnxCpmCardAssignedType          TmnxCardType,
    tmnxCpmCardEquippedType          TmnxCardType,
    tmnxCpmCardHwIndex               TmnxHwIndex,
    tmnxCpmCardBootOptionVersion     TItemDescription,
    tmnxCpmCardBootOptionLastModified DateAndTime,
    tmnxCpmCardConfigBootedVersion   TItemDescription,
    tmnxCpmCardIndexBootedVersion    TItemDescription,
    tmnxCpmCardConfigLastModified    DateAndTime,
    tmnxCpmCardConfigLastSaved       DateAndTime,
    tmnxCpmCardRedundant             INTEGER,
    tmnxCpmCardClockSource           TItemDescription,
    tmnxCpmCardNumCpus               Unsigned32,
    tmnxCpmCardCpuType               INTEGER,
    tmnxCpmCardMemorySize            Unsigned32,
    tmnxCpmCardSwitchToRedundantCard TmnxActionType,
    tmnxCpmCardReboot                TmnxActionType,
    tmnxCpmCardRereadBootOptions     TmnxActionType,
    tmnxCpmCardConfigFileLastBooted  DisplayString,
    tmnxCpmCardConfigFileLastSaved   DisplayString,
    tmnxCpmCardConfigFileLastBootedHeader OCTET STRING,
    tmnxCpmCardIndexFileLastBootedHeader OCTET STRING,
    tmnxCpmCardBootOptionSource      DisplayString,
    tmnxCpmCardConfigSource          INTEGER,
    tmnxCpmCardBootOptionLastSaved   DateAndTime,
    tmnxCpmCardMasterSlaveRefState   INTEGER,
    tmnxCpmCardConfigUserLastModified SnmpAdminString,
    tmnxCpmCardCmplxCAMErrOccur      Counter32,
    tmnxCpmCardCmplxCAMErrOccurTime  TimeStamp,
    tmnxCpmCardOscillatorType        INTEGER,
    tmnxCpmCardCmplxMemErrOccur      Counter32,
    tmnxCpmCardCmplxMemErrOccurTime  TimeStamp,
    tmnxCpmCardCmplBufMemErrOcc      Counter32,
    tmnxCpmCardCmplBufMemErrOccTime  TimeStamp,
    tmnxCpmCardCmplStatMemErrOcc     Counter32,
    tmnxCpmCardCmplStatMemErrOccTime TimeStamp,
    tmnxCpmCardCmplIntMemErrOcc      Counter32,
    tmnxCpmCardCmplIntMemErrOccTime  TimeStamp,
    tmnxCpmCardCmplChipIfDownOcc     Counter32,
    tmnxCpmCardCmplChipIfDownOccTime TimeStamp,
    tmnxCpmCardCmplChipIfCellOcc     Counter32,
    tmnxCpmCardCmplChipIfCellOccTime TimeStamp,
    tmnxCpmCardRebootHold            TruthValue,
    tmnxCpmCardUuid                  TmnxUuid,
    tmnxCpmCardCmplxIngrFcsOccur     Counter32,
    tmnxCpmCardCmplxIngrFcsOccurTime TimeStamp,
    tmnxCpmCardCmplxEgrFcsOccur      Counter32,
    tmnxCpmCardCmplxEgrFcsOccurTime  TimeStamp,
    tmnxCpmCardCmplxEgrFcsSrcSlots   TmnxCardSlotBitMap
}

tmnxCpmCardSlotNum               OBJECT-TYPE
    SYNTAX      TmnxSlotNum
    MAX-ACCESS  not-accessible
    STATUS      current
    DESCRIPTION
        "The unique value which identifies this slot within a chassis in
         the system.  Depending upon the value of tmnxChassisType, this may
         represent a fabric slot or a regular card slot.  If this CPM module
         resides on a fabric card, tmnxCpmCardSlotNum has the value the
         corresponding tmnxFabricSlotNum.  If this is a CPM module on a
         fabric card, tmnxCpmCardSlotNum is the fabric slot number in the
         chassis where this CPM module is located.  Else if this is a
         CPM card, tmnxCpmCardSlotNum is a regular card slot number."
    ::= { tmnxCpmCardEntry 1 }

tmnxCpmCardNum                   OBJECT-TYPE
    SYNTAX      Unsigned32
    MAX-ACCESS  not-accessible
    STATUS      current
    DESCRIPTION
        "The unique value which identifies this CPM module within a specific
         card slot within a chassis in the system."
    ::= { tmnxCpmCardEntry 2 }

tmnxCpmCardSupportedTypes        OBJECT-TYPE
    SYNTAX      TmnxCardSuppType
    MAX-ACCESS  read-only
    STATUS      current
    DESCRIPTION
        "A bit-mask that indicates what CPM card types can be physically
         supported in this slot in this chassis."
    ::= { tmnxCpmCardEntry 3 }

tmnxCpmCardAllowedTypes          OBJECT-TYPE
    SYNTAX      TmnxCardType
    MAX-ACCESS  read-write
    STATUS      obsolete
    DESCRIPTION
        "A bit-mask that specifies what CPM card types the administrator
         has designated be allowed to be inserted into this slot.  If the
         slot has not-been pre-provisioned and a card that does not match
         one of the allowed types is inserted into this slot, a mismatch
         alarm will be raised.  If a specific value has not yet been SET by
         the manager, tmnxCpmCardAllowedTypes will return the same value to
         a GET request as tmnxCpmCardSupportedTypes.

         The object was made obsolete in the 3.0 release."
    ::= { tmnxCpmCardEntry 4 }

tmnxCpmCardAssignedType          OBJECT-TYPE
    SYNTAX      TmnxCardType
    MAX-ACCESS  read-write
    STATUS      current
    DESCRIPTION
        "The tmnxCpmCardAssignedType specifies the administratively assigned
         (pre-provisioned) CPM card type defined in tmnxCardTypeTable that
         should occupy this slot in this chassis.  If tmnxCpmCardAssignedType
         has a value of 1 (unassigned), this slot has not yet been
         pre-provisioned."
    DEFVAL      { 1 }
    ::= { tmnxCpmCardEntry 5 }

tmnxCpmCardEquippedType          OBJECT-TYPE
    SYNTAX      TmnxCardType
    MAX-ACCESS  read-only
    STATUS      current
    DESCRIPTION
        "The tmnxCpmCardEquippedType indicates the CPM card type that is
         physically inserted into this slot in this chassis.  If the slot has
         been pre-provisioned, tmnxCpmCardAssignedType is not equal to 1
         (unassigned), and the value of tmnxCpmCardEquippedType is not the same
         as tmnxCpmCardAssignedType, a mismatch alarm will be raised."
    ::= { tmnxCpmCardEntry 6 }

tmnxCpmCardHwIndex               OBJECT-TYPE
    SYNTAX      TmnxHwIndex
    MAX-ACCESS  read-only
    STATUS      current
    DESCRIPTION
        "The value of tmnxCpmCardHwIndex is the index into the tmnxHwTable for
         the row entry that represents the hardware component information for
         this CPM card or module."
    ::= { tmnxCpmCardEntry 7 }

tmnxCpmCardBootOptionVersion     OBJECT-TYPE
    SYNTAX      TItemDescription
    MAX-ACCESS  read-only
    STATUS      current
    DESCRIPTION
        "The version number of boot option file (BOF) read by the CPM card in
         this slot."
    ::= { tmnxCpmCardEntry 8 }

tmnxCpmCardBootOptionLastModified OBJECT-TYPE
    SYNTAX      DateAndTime
    MAX-ACCESS  read-only
    STATUS      current
    DESCRIPTION
        "The date and time the boot options file (BOF) for this card was last
         modified.  If tmnxCpmCardBootOptionLastModified is more recent than
         tmnxHwSwLastBoot, the boot options file has been edited since
         the software was booted and different software images or configuration
         will likely be used when this card is next rebooted."
    ::= { tmnxCpmCardEntry 9 }

tmnxCpmCardConfigBootedVersion   OBJECT-TYPE
    SYNTAX      TItemDescription
    MAX-ACCESS  read-only
    STATUS      current
    DESCRIPTION
        "The version of the configuration file read when this CPM card was last
         rebooted."
    ::= { tmnxCpmCardEntry 10 }

tmnxCpmCardIndexBootedVersion    OBJECT-TYPE
    SYNTAX      TItemDescription
    MAX-ACCESS  read-only
    STATUS      current
    DESCRIPTION
        "The version of the index file read when this CPM card was last
         rebooted."
    ::= { tmnxCpmCardEntry 11 }

tmnxCpmCardConfigLastModified    OBJECT-TYPE
    SYNTAX      DateAndTime
    MAX-ACCESS  read-only
    STATUS      current
    DESCRIPTION
        "The date and time the running configuration was last modified. If
         tmnxCpmCardConfigLastModified is more recent than tmnxHwSwLastBoot,
         the current configuration may be different than that in the
         configuration file read upon system initialization."
    ::= { tmnxCpmCardEntry 12 }

tmnxCpmCardConfigLastSaved       OBJECT-TYPE
    SYNTAX      DateAndTime
    MAX-ACCESS  read-only
    STATUS      current
    DESCRIPTION
        "The date and time the current configuration was last saved. If
         tmnxCpmCardConfigLastSaved is more recent the value of
         tmnxHwSwLastBoot, the initial configuration is likely to be different
         the next time the system is rebooted."
    ::= { tmnxCpmCardEntry 13 }

tmnxCpmCardRedundant             OBJECT-TYPE
    SYNTAX      INTEGER {
        singleton           (1),
        redundantActive     (2),
        redundantStandby    (3),
        redundantSplit      (4),
        redundantDisabled   (5),
        redundantSyncing    (6),
        redundantExtActive  (7),
        redundantExtStandby (8)
    }
    MAX-ACCESS  read-only
    STATUS      current
    DESCRIPTION
        "The value of tmnxCpmCardRedundant indicates the role of the CPM card
         for the redundant pair.

         The possible values are:
         singleton           (1) - standalone CPM, no redundant pair
         redundantActive     (2) - the active CPM in the redundant pair
         redundantStandby    (3) - the standby CPM in the redundant pair
         redundantSplit      (4) - not implemented
         redundantDisabled   (5) - tmnxHwOperState indicates the specific
                                   reason why this redundant CPM is not
                                   available
         redundantSyncing    (6) - the redundant pair is syncing
         redundantExtActive  (7) - the active CPM in the redundant pair
                                   for the extension chassis
         redundantExtStandby (8) - the standby CPM in the redundant pair
                                   for the extension chassis"
    ::= { tmnxCpmCardEntry 14 }

tmnxCpmCardClockSource           OBJECT-TYPE
    SYNTAX      TItemDescription
    MAX-ACCESS  read-only
    STATUS      current
    DESCRIPTION
        "The clock source used by the CPM card in this slot."
    ::= { tmnxCpmCardEntry 15 }

tmnxCpmCardNumCpus               OBJECT-TYPE
    SYNTAX      Unsigned32
    MAX-ACCESS  read-only
    STATUS      current
    DESCRIPTION
        "The value of tmnxCpmCardNumCpus indicates the number of CPU chips
         populated on this CPM module."
    ::= { tmnxCpmCardEntry 16 }

tmnxCpmCardCpuType               OBJECT-TYPE
    SYNTAX      INTEGER {
        unknown    (1),
        mips       (2),
        pentium-pc (3)
    }
    MAX-ACCESS  read-only
    STATUS      current
    DESCRIPTION
        "The value of tmnxCpmCardCpuType indicates the type of CPU chips
         populated on this CPM module."
    ::= { tmnxCpmCardEntry 17 }

tmnxCpmCardMemorySize            OBJECT-TYPE
    SYNTAX      Unsigned32
    UNITS       "Mega-bytes"
    MAX-ACCESS  read-only
    STATUS      current
    DESCRIPTION
        "The value of tmnxCpmCardMemorySize indicates the amount of memory, in
         mega-bytes, populated on this CPM module."
    ::= { tmnxCpmCardEntry 18 }

tmnxCpmCardSwitchToRedundantCard OBJECT-TYPE
    SYNTAX      TmnxActionType
    MAX-ACCESS  read-write
    STATUS      current
    DESCRIPTION
        "Setting this variable to doAction causes the switchover to the
         redundant CPM card."
    DEFVAL      { notApplicable }
    ::= { tmnxCpmCardEntry 19 }

tmnxCpmCardReboot                OBJECT-TYPE
    SYNTAX      TmnxActionType
    MAX-ACCESS  read-write
    STATUS      current
    DESCRIPTION
        "Setting this variable to 'doAction' causes the CPM card to execute a
         soft-reboot."
    DEFVAL      { notApplicable }
    ::= { tmnxCpmCardEntry 20 }

tmnxCpmCardRereadBootOptions     OBJECT-TYPE
    SYNTAX      TmnxActionType
    MAX-ACCESS  read-write
    STATUS      current
    DESCRIPTION
        "Setting this variable to 'doAction' causes the Boot Options File (BOF)
         to be reread and applied."
    DEFVAL      { notApplicable }
    ::= { tmnxCpmCardEntry 21 }

tmnxCpmCardConfigFileLastBooted  OBJECT-TYPE
    SYNTAX      DisplayString
    MAX-ACCESS  read-only
    STATUS      current
    DESCRIPTION
        "tmnxCpmCardConfigFileLastBooted indicates the location and name of the
         configuration file from which the system last rebooted."
    ::= { tmnxCpmCardEntry 22 }

tmnxCpmCardConfigFileLastSaved   OBJECT-TYPE
    SYNTAX      DisplayString
    MAX-ACCESS  read-only
    STATUS      current
    DESCRIPTION
        "tmnxCpmCardConfigFileLastSaved indicates the location and name of the
         file to which the configuration was last saved."
    ::= { tmnxCpmCardEntry 23 }

tmnxCpmCardConfigFileLastBootedHeader OBJECT-TYPE
    SYNTAX      OCTET STRING (SIZE (0..512))
    MAX-ACCESS  read-only
    STATUS      current
    DESCRIPTION
        "tmnxCpmCardConfigFileLastBootedHeader contains the header of the
         configuration file from which the system last rebooted."
    ::= { tmnxCpmCardEntry 24 }

tmnxCpmCardIndexFileLastBootedHeader OBJECT-TYPE
    SYNTAX      OCTET STRING (SIZE (0..512))
    MAX-ACCESS  read-only
    STATUS      current
    DESCRIPTION
        "tmnxCpmCardIndexFileLastBootedHeader contains the header of the index
         file from which the system last rebooted."
    ::= { tmnxCpmCardEntry 25 }

tmnxCpmCardBootOptionSource      OBJECT-TYPE
    SYNTAX      DisplayString
    MAX-ACCESS  read-only
    STATUS      current
    DESCRIPTION
        "tmnxCpmCardBootOptionSource indicates the compact flash slot where the
         Boot Options File (BOF) file was found when the system last rebooted.
         For example, if the BOF file was found on compact flash slot 1, the
         value of this variable will be 'cf1:'"
    ::= { tmnxCpmCardEntry 26 }

tmnxCpmCardConfigSource          OBJECT-TYPE
    SYNTAX      INTEGER {
        unknown   (0),
        primary   (1),
        secondary (2),
        tertiary  (3)
    }
    MAX-ACCESS  read-only
    STATUS      current
    DESCRIPTION
        "The value of tmnxCpmCardConfigSource indicates the location in the
         Boot Options File(BOF) where the configuration file was found when the
         system last rebooted."
    ::= { tmnxCpmCardEntry 27 }

tmnxCpmCardBootOptionLastSaved   OBJECT-TYPE
    SYNTAX      DateAndTime
    MAX-ACCESS  read-only
    STATUS      current
    DESCRIPTION
        "The date and time the boot options file (BOF) was last saved. If
         tmnxCpmCardBootOptionLastSaved is more recent than the value of
         tmnxHwSwLastBoot, the boot options file has been edited since the
         software was booted and different software images or configuration
         will likely be used when this card is next rebooted."
    ::= { tmnxCpmCardEntry 28 }

tmnxCpmCardMasterSlaveRefState   OBJECT-TYPE
    SYNTAX      INTEGER {
        primaryRef     (1),
        secondaryRef   (2),
        notInitialized (3)
    }
    MAX-ACCESS  read-only
    STATUS      current
    DESCRIPTION
        "The current Master/Slave clocking reference designation.

         primaryRef       Indicates this card is designated as the primary
                          clocking reference in a redundant system for cards
                          within the same physical chassis.
         secondaryRef     Indicates this card is designated as the secondary
                          clocking reference in a redundant system for cards
                          within the same physical chassis.
         notInitialized   Indicates the clock is not initialized."
    ::= { tmnxCpmCardEntry 30 }

tmnxCpmCardConfigUserLastModified OBJECT-TYPE
    SYNTAX      SnmpAdminString (SIZE (0..65))
    MAX-ACCESS  read-only
    STATUS      current
    DESCRIPTION
        "The value of tmnxCpmCardConfigUserLastModified indicates the last user
         who modified the configuration.

         If the configuration was last modified by an SNMPv1 or SNMPv2 set
         operation, the value of this object will indicate the SNMP community
         string and view name separated by the '/' character.

         If the configuration was last modified by an SNMPv3 set operation, the
         value of this object will be the SNMPv3 user and view name separated
         by the '/' character.

         If the configuration has not been saved since the last boot, the
         object will have the value of an empty string."
    ::= { tmnxCpmCardEntry 31 }

tmnxCpmCardCmplxCAMErrOccur      OBJECT-TYPE
    SYNTAX      Counter32
    MAX-ACCESS  read-only
    STATUS      current
    DESCRIPTION
        "The value of tmnxCpmCardCmplxCAMErrOccur indicates the number of times
         the complex experienced an occurrence of a CAM error since startup, or
         card reboot."
    ::= { tmnxCpmCardEntry 32 }

tmnxCpmCardCmplxCAMErrOccurTime  OBJECT-TYPE
    SYNTAX      TimeStamp
    MAX-ACCESS  read-only
    STATUS      current
    DESCRIPTION
        "The value of tmnxCpmCardCmplxCAMErrOccurTime indicates the last time
         tmnxCpmCardCmplxCAMErrOccur incremented."
    ::= { tmnxCpmCardEntry 33 }

tmnxCpmCardOscillatorType        OBJECT-TYPE
    SYNTAX      INTEGER {
        none (1),
        tcxo (2),
        ocxo (3)
    }
    MAX-ACCESS  read-only
    STATUS      current
    DESCRIPTION
        "The value of tmnxCpmCardOscillatorType indicates the type of
         oscillator present on the card.

         An Oven-Controlled Crystal Oscillator (OCXO) is required for the card
         to support IEEE 1588 clock recovery.  A Temperature-Compensated Crystal
         Oscillator (TCXO) is not sufficient.

         The type of oscillator also affects the holdover performance of the
         system."
    ::= { tmnxCpmCardEntry 34 }

tmnxCpmCardCmplxMemErrOccur      OBJECT-TYPE
    SYNTAX      Counter32
    MAX-ACCESS  read-only
    STATUS      current
    DESCRIPTION
        "The value of tmnxCpmCardCmplxMemErrOccur indicates the number of times
         the complex experienced an occurrence of a memory error since startup,
         or card reboot."
    ::= { tmnxCpmCardEntry 35 }

tmnxCpmCardCmplxMemErrOccurTime  OBJECT-TYPE
    SYNTAX      TimeStamp
    MAX-ACCESS  read-only
    STATUS      current
    DESCRIPTION
        "The value of tmnxCpmCardCmplxMemErrOccurTime indicates the last time
         tmnxCpmCardCmplxMemErrOccur incremented."
    ::= { tmnxCpmCardEntry 36 }

tmnxCpmCardCmplBufMemErrOcc      OBJECT-TYPE
    SYNTAX      Counter32
    MAX-ACCESS  read-only
    STATUS      current
    DESCRIPTION
        "The value of tmnxCpmCardCmplBufMemErrOcc indicates the number of times
         the complex experienced an occurrence of a buffer memory error since
         startup, or card reboot."
    ::= { tmnxCpmCardEntry 37 }

tmnxCpmCardCmplBufMemErrOccTime  OBJECT-TYPE
    SYNTAX      TimeStamp
    MAX-ACCESS  read-only
    STATUS      current
    DESCRIPTION
        "The value of tmnxCpmCardCmplBufMemErrOccTime indicates the last time
         tmnxCpmCardCmplBufMemErrOcc incremented."
    ::= { tmnxCpmCardEntry 38 }

tmnxCpmCardCmplStatMemErrOcc     OBJECT-TYPE
    SYNTAX      Counter32
    MAX-ACCESS  read-only
    STATUS      current
    DESCRIPTION
        "The value of tmnxCpmCardCmplStatMemErrOcc indicates the number of
         times the complex experienced an occurrence of a statistics memory
         error since startup, or card reboot."
    ::= { tmnxCpmCardEntry 39 }

tmnxCpmCardCmplStatMemErrOccTime OBJECT-TYPE
    SYNTAX      TimeStamp
    MAX-ACCESS  read-only
    STATUS      current
    DESCRIPTION
        "The value of tmnxCpmCardCmplStatMemErrOccTime indicates the last time
         tmnxCpmCardCmplStatMemErrOcc incremented."
    ::= { tmnxCpmCardEntry 40 }

tmnxCpmCardCmplIntMemErrOcc      OBJECT-TYPE
    SYNTAX      Counter32
    MAX-ACCESS  read-only
    STATUS      current
    DESCRIPTION
        "The value of tmnxCpmCardCmplIntMemErrOcc indicates the number of times
         the complex experienced an occurrence of an internal memory error
         since startup, or card reboot."
    ::= { tmnxCpmCardEntry 41 }

tmnxCpmCardCmplIntMemErrOccTime  OBJECT-TYPE
    SYNTAX      TimeStamp
    MAX-ACCESS  read-only
    STATUS      current
    DESCRIPTION
        "The value of tmnxCpmCardCmplIntMemErrOccTime indicates the last time
         tmnxCpmCardCmplIntMemErrOcc incremented."
    ::= { tmnxCpmCardEntry 42 }

tmnxCpmCardCmplChipIfDownOcc     OBJECT-TYPE
    SYNTAX      Counter32
    MAX-ACCESS  read-only
    STATUS      current
    DESCRIPTION
        "The value of tmnxCpmCardCmplChipIfDownOcc indicates the number of
         times the complex experienced an occurrence of an internal datapath
         problem."
    ::= { tmnxCpmCardEntry 43 }

tmnxCpmCardCmplChipIfDownOccTime OBJECT-TYPE
    SYNTAX      TimeStamp
    MAX-ACCESS  read-only
    STATUS      current
    DESCRIPTION
        "The value of tmnxCpmCardCmplChipIfDownOccTime indicates the last time
         tmnxCpmCardCmplChipIfDownOcc incremented."
    ::= { tmnxCpmCardEntry 44 }

tmnxCpmCardCmplChipIfCellOcc     OBJECT-TYPE
    SYNTAX      Counter32
    MAX-ACCESS  read-only
    STATUS      current
    DESCRIPTION
        "The value of tmnxCpmCardCmplChipIfCellOcc indicates the number of
         times the complex experienced an occurrence of internal datapath cell
         errors."
    ::= { tmnxCpmCardEntry 45 }

tmnxCpmCardCmplChipIfCellOccTime OBJECT-TYPE
    SYNTAX      TimeStamp
    MAX-ACCESS  read-only
    STATUS      current
    DESCRIPTION
        "The value of tmnxCpmCardCmplChipIfCellOccTime indicates the last time
         tmnxCpmCardCmplChipIfCellOcc incremented."
    ::= { tmnxCpmCardEntry 46 }

tmnxCpmCardRebootHold            OBJECT-TYPE
    SYNTAX      TruthValue
    MAX-ACCESS  read-write
    STATUS      current
    DESCRIPTION
        "The value of tmnxCpmCardRebootHold specifies putting the standby CPM
         card in hold on a soft reboot, preventing the standby CPM+SFM from
         coming back online. To do so, this attribute must be set to 'true(1)'
         together with tmnxCpmCardReboot set to 'doAction(1)' and only for the
         standby CPM; otherwise, the set will fail with error
         'inconsistentValue'. For the active CPM, tmnxCpmCardRebootHold can't
         be set to 'true(1)' and will always return a value of 'false(2)'.

         When tmnxCpmCardRebootHold is set to 'true(1)', the standby CPM
         reboots as expected, but remains in a booting state (in hold).

         The setting of tmnxCpmCardRebootHold to 'true(1)' prevents the active
         CPM from declaring the standby CPM dead because it failed to boot. MIB
         attribute tmnxHwFailureReason will be updated for the standby CPM
         indicating that there is no SFM.

         The system is not redundant while tmnxCpmCardRebootHold is 'true(1)'.
         If the active CPM fails, or is manually rebooted, the standby CPM will
         also reboot.

         tmnxCpmCardRebootHold is set to 'false(2)' when tmnxCpmCardReboot for
         the standby CPM is set to 'doAction(1)' without also setting
         tmnxCpmCardRebootHold, or if the active CPM reboots."
    DEFVAL      { false }
    ::= { tmnxCpmCardEntry 47 }

tmnxCpmCardUuid                  OBJECT-TYPE
    SYNTAX      TmnxUuid
    MAX-ACCESS  read-only
    STATUS      current
    DESCRIPTION
        "The value of tmnxCpmCardUuid indicates the Universally Unique
         Identifier (UUID) of the CPM card."
    ::= { tmnxCpmCardEntry 49 }

tmnxCpmCardCmplxIngrFcsOccur     OBJECT-TYPE
    SYNTAX      Counter32
    MAX-ACCESS  read-only
    STATUS      current
    DESCRIPTION
        "The value of tmnxCpmCardCmplxIngrFcsOccur indicates the number of
         times the first CPM card complex experienced an occurrence of an FCS
         error in the ingress direction since startup, last clear, or CPM
         reboot."
    ::= { tmnxCpmCardEntry 50 }

tmnxCpmCardCmplxIngrFcsOccurTime OBJECT-TYPE
    SYNTAX      TimeStamp
    MAX-ACCESS  read-only
    STATUS      current
    DESCRIPTION
        "The value of tmnxCpmCardCmplxIngrFcsOccurTime indicates the last time
         tmnxCardCmplx1IngrFcsOccur incremented."
    ::= { tmnxCpmCardEntry 51 }

tmnxCpmCardCmplxEgrFcsOccur      OBJECT-TYPE
    SYNTAX      Counter32
    MAX-ACCESS  read-only
    STATUS      current
    DESCRIPTION
        "The value of tmnxCpmCardCmplxEgrFcsOccur indicates the number of times
         the first CPM card complex experienced an occurrence of an FCS error
         in the egress direction since startup, last clear, or CPM reboot."
    ::= { tmnxCpmCardEntry 52 }

tmnxCpmCardCmplxEgrFcsOccurTime  OBJECT-TYPE
    SYNTAX      TimeStamp
    MAX-ACCESS  read-only
    STATUS      current
    DESCRIPTION
        "The value of tmnxCpmCardCmplxEgrFcsOccurTime indicates the last time
         tmnxCardCmplx1EgrFcsOccur incremented."
    ::= { tmnxCpmCardEntry 53 }

tmnxCpmCardCmplxEgrFcsSrcSlots   OBJECT-TYPE
    SYNTAX      TmnxCardSlotBitMap
    MAX-ACCESS  read-only
    STATUS      current
    DESCRIPTION
        "The value of tmnxCpmCardCmplxEgrFcsSrcSlots indicates the source slots
         reported from the last time tmnxCpmCardCmplxEgrFcsOccur incremented."
    ::= { tmnxCpmCardEntry 54 }

tmnxFabricLastChange             OBJECT-TYPE
    SYNTAX      TimeStamp
    MAX-ACCESS  read-only
    STATUS      current
    DESCRIPTION
        "The value of sysUpTime when the tmnxFabricTable was last changed."
    ::= { tmnxCardObjs 5 }

tmnxFabricTable                  OBJECT-TYPE
    SYNTAX      SEQUENCE OF TmnxFabricEntry
    MAX-ACCESS  not-accessible
    STATUS      current
    DESCRIPTION
        "The tmnxFabricTable has an entry for each fabric card slot in each
         chassis in the TMNX system."
    ::= { tmnxCardObjs 6 }

tmnxFabricEntry                  OBJECT-TYPE
    SYNTAX      TmnxFabricEntry
    MAX-ACCESS  not-accessible
    STATUS      current
    DESCRIPTION
        "Each row entry represents a fabric card slot in a chassis in
         the system.  Entries cannot be created and deleted via
         SNMP SET operations.  When a tmnxChassisEntry is created,
         a tmnxFabricEntry is created for each fabric card slot in that
         chassis.  Before a tmnxChassisEntry can be deleted, each
         tmnxFabricEntry for that chassis must be in the proper state
         for removal."
    INDEX       {
        tmnxChassisIndex,
        tmnxFabricSlotNum
    }
    ::= { tmnxFabricTable 1 }

TmnxFabricEntry                  ::= SEQUENCE
{
    tmnxFabricSlotNum                Unsigned32,
    tmnxFabricAssignedType           TmnxFabricType,
    tmnxFabricEquippedType           TmnxFabricType,
    tmnxFabricHwIndex                TmnxHwIndex,
    tmnxFabricSupportedTypes         TmnxFabricSuppType,
    tmnxFabricReboot                 TmnxActionType
}

tmnxFabricSlotNum                OBJECT-TYPE
    SYNTAX      Unsigned32 (1..16)
    MAX-ACCESS  not-accessible
    STATUS      current
    DESCRIPTION
        "The unique value which identifies this fabric slot within a
         chassis in the system. The CPM cards and IOM cards cannot be
         physically inserted into the switch fabric card slots.  In
         some models, the CPM is not a separate card, but rather a
         module on a Fabric card."
    ::= { tmnxFabricEntry 1 }

tmnxFabricAssignedType           OBJECT-TYPE
    SYNTAX      TmnxFabricType
    MAX-ACCESS  read-write
    STATUS      current
    DESCRIPTION
        "The administratively assigned switch fabric card type that should
         occupy this fabric slot in this chassis."
    DEFVAL      { 1 }
    ::= { tmnxFabricEntry 2 }

tmnxFabricEquippedType           OBJECT-TYPE
    SYNTAX      TmnxFabricType
    MAX-ACCESS  read-only
    STATUS      current
    DESCRIPTION
        "The switch fabric card type that is physically inserted into this slot
         in this chassis."
    ::= { tmnxFabricEntry 3 }

tmnxFabricHwIndex                OBJECT-TYPE
    SYNTAX      TmnxHwIndex
    MAX-ACCESS  read-only
    STATUS      current
    DESCRIPTION
        "The value of tmnxFabricHwIndex indicates the tmnxHwIndex into the
         tmnxHwTable to locate the row entry that represents the hardware
         component information for this fabric card."
    ::= { tmnxFabricEntry 4 }

tmnxFabricSupportedTypes         OBJECT-TYPE
    SYNTAX      TmnxFabricSuppType
    MAX-ACCESS  read-only
    STATUS      current
    DESCRIPTION
        "A bit-mask that indicates what fabric card types can be configured in
         this slot in this chassis."
    ::= { tmnxFabricEntry 5 }

tmnxFabricReboot                 OBJECT-TYPE
    SYNTAX      TmnxActionType
    MAX-ACCESS  read-write
    STATUS      current
    DESCRIPTION
        "Setting this variable to 'doAction' causes the fabric to execute a
         soft-reboot."
    DEFVAL      { notApplicable }
    ::= { tmnxFabricEntry 6 }

tmnxCpmFlashTable                OBJECT-TYPE
    SYNTAX      SEQUENCE OF TmnxCpmFlashEntry
    MAX-ACCESS  not-accessible
    STATUS      current
    DESCRIPTION
        "This table contains information about Flash devices on a CPM card."
    ::= { tmnxCardObjs 7 }

tmnxCpmFlashEntry                OBJECT-TYPE
    SYNTAX      TmnxCpmFlashEntry
    MAX-ACCESS  not-accessible
    STATUS      current
    DESCRIPTION
        "Contains information regarding a CPM card's flash unit."
    INDEX       {
        tmnxChassisIndex,
        tmnxCardSlotNum,
        tmnxCpmFlashId
    }
    ::= { tmnxCpmFlashTable 1 }

TmnxCpmFlashEntry                ::= SEQUENCE
{
    tmnxCpmFlashId                   Unsigned32,
    tmnxCpmFlashOperStatus           TmnxDeviceState,
    tmnxCpmFlashSerialNumber         TItemDescription,
    tmnxCpmFlashFirmwareRevision     TItemDescription,
    tmnxCpmFlashModelNumber          TItemDescription,
    tmnxCpmFlashCapacity             Unsigned32,
    tmnxCpmFlashUsed                 Unsigned32,
    tmnxCpmFlashHwIndex              TmnxHwIndex,
    tmnxCpmFlashPercentageUsed       Unsigned32
}

tmnxCpmFlashId                   OBJECT-TYPE
    SYNTAX      Unsigned32 (1..32)
    MAX-ACCESS  not-accessible
    STATUS      current
    DESCRIPTION
        "The unique identifier index for a flash device on a CPM card."
    ::= { tmnxCpmFlashEntry 1 }

tmnxCpmFlashOperStatus           OBJECT-TYPE
    SYNTAX      TmnxDeviceState
    MAX-ACCESS  read-only
    STATUS      current
    DESCRIPTION
        "Current status of this flash unit on this CPM card."
    ::= { tmnxCpmFlashEntry 2 }

tmnxCpmFlashSerialNumber         OBJECT-TYPE
    SYNTAX      TItemDescription
    MAX-ACCESS  read-only
    STATUS      current
    DESCRIPTION
        "The serial number for this flash unit on this CPM card."
    ::= { tmnxCpmFlashEntry 3 }

tmnxCpmFlashFirmwareRevision     OBJECT-TYPE
    SYNTAX      TItemDescription
    MAX-ACCESS  read-only
    STATUS      current
    DESCRIPTION
        "The firmware revision number for this flash unit on this CPM card."
    ::= { tmnxCpmFlashEntry 4 }

tmnxCpmFlashModelNumber          OBJECT-TYPE
    SYNTAX      TItemDescription
    MAX-ACCESS  read-only
    STATUS      current
    DESCRIPTION
        "The model number for this flash unit on this CPM card."
    ::= { tmnxCpmFlashEntry 5 }

tmnxCpmFlashCapacity             OBJECT-TYPE
    SYNTAX      Unsigned32
    UNITS       "sectors"
    MAX-ACCESS  read-only
    STATUS      current
    DESCRIPTION
        "The value of tmnxCpmFlashCapacity indicates the maximum size of this
         flash unit in 512-byte sectors."
    ::= { tmnxCpmFlashEntry 6 }

tmnxCpmFlashUsed                 OBJECT-TYPE
    SYNTAX      Unsigned32
    UNITS       "sectors"
    MAX-ACCESS  read-only
    STATUS      current
    DESCRIPTION
        "The value of tmnxCpmFlashUsed indicates the amount used, in 512-byte
         sectors, of this flash unit's total capacity."
    ::= { tmnxCpmFlashEntry 7 }

tmnxCpmFlashHwIndex              OBJECT-TYPE
    SYNTAX      TmnxHwIndex
    MAX-ACCESS  read-only
    STATUS      current
    DESCRIPTION
        "The value of tmnxCpmFlashHwIndex indicates the tmnxHwIndex into the
         tmnxHwTable for the row entry that represents the hardware component
         information for this flash unit."
    ::= { tmnxCpmFlashEntry 8 }

tmnxCpmFlashPercentageUsed       OBJECT-TYPE
    SYNTAX      Unsigned32
    UNITS       "percent"
    MAX-ACCESS  read-only
    STATUS      current
    DESCRIPTION
        "The value of tmnxCpmFlashPercentageUsed indicates the amount used for
         this flash unit as a percentage of total capacity."
    ::= { tmnxCpmFlashEntry 9 }

tmnxMDATable                     OBJECT-TYPE
    SYNTAX      SEQUENCE OF TmnxMDAEntry
    MAX-ACCESS  not-accessible
    STATUS      current
    DESCRIPTION
        "The tmnxMDATable has an entry for each MDA slot in each IOM card in
         this chassis in the TMNX system."
    ::= { tmnxCardObjs 8 }

tmnxMDAEntry                     OBJECT-TYPE
    SYNTAX      TmnxMDAEntry
    MAX-ACCESS  not-accessible
    STATUS      current
    DESCRIPTION
        "Each row entry represents a MDA slot in an IOM card in a
         chassis in the system.  Entries cannot be created and
         deleted via SNMP SET operations.  When a tmnxCardEntry
         has tmnxCardAssignedType or tmnxCardEquippedType equal to
         an IOM card type that supports MDA slots, a tmnxMDAEntry is
         created by the agent for each MDA slot on that IOM card.
         Before a tmnxCardEntry can be deleted, each tmnxMDAEntry for
         that card must be in the proper state for removal."
    INDEX       {
        tmnxChassisIndex,
        tmnxCardSlotNum,
        tmnxMDASlotNum
    }
    ::= { tmnxMDATable 1 }

TmnxMDAEntry                     ::= SEQUENCE
{
    tmnxMDASlotNum                   Unsigned32,
    tmnxMDASupportedTypes            TmnxMDASuppType,
    tmnxMDAAllowedTypes              TmnxMdaType,
    tmnxMDAAssignedType              TmnxMdaType,
    tmnxMDAEquippedType              TmnxMdaType,
    tmnxMDAHwIndex                   TmnxHwIndex,
    tmnxMDAMaxPorts                  Integer32,
    tmnxMDAEquippedPorts             Unsigned32,
    tmnxMDATxTimingSelected          INTEGER,
    tmnxMDASyncIfTimingStatus        INTEGER,
    tmnxMDANetworkIngQueues          TNamedItem,
    tmnxMDACapabilities              BITS,
    tmnxMDAMinChannelization         TmnxMDAChanType,
    tmnxMDAMaxChannelization         TmnxMDAChanType,
    tmnxMDAMaxChannels               Unsigned32,
    tmnxMDAChannelsInUse             Unsigned32,
    tmnxMDACcagId                    TmnxCcagId,
    tmnxMDAReboot                    TmnxActionType,
    tmnxMDAHiBwMcastSource           TruthValue,
    tmnxMDAHiBwMcastAlarm            TruthValue,
    tmnxMDAHiBwMcastTapCount         Gauge32,
    tmnxMDAHiBwMcastGroup            Unsigned32,
    tmnxMDAClockMode                 INTEGER,
    tmnxMDADiffTimestampFreq         Unsigned32,
    tmnxMDAIngHsmdaSchedPolicy       TNamedItemOrEmpty,
    tmnxMDAMcPathMgmtBwPlcyName      TNamedItem,
    tmnxMDAMcPathMgmtPriPathLimit    Unsigned32,
    tmnxMDAMcPathMgmtSecPathLimit    Unsigned32,
    tmnxMDAMcPathMgmtAncPathLimit    Unsigned32,
    tmnxMDAMcPathMgmtAdminState      TmnxAdminState,
    tmnxMDAIngNamedPoolPolicy        TNamedItemOrEmpty,
    tmnxMDAEgrNamedPoolPolicy        TNamedItemOrEmpty,
    tmnxMDAIngHsmdaPoolPolicy        TNamedItemOrEmpty,
    tmnxMDAEgrHsmdaPoolPolicy        TNamedItemOrEmpty,
    tmnxMDAMcPathMgmtPriInUseBw      Gauge32,
    tmnxMDAMcPathMgmtSecInUseBw      Gauge32,
    tmnxMDAMcPathMgmtAncInUseBw      Gauge32,
    tmnxMDAMcPathMgmtBlkHoleInUseBw  Gauge32,
    tmnxMDASynchronousEthernet       INTEGER,
    tmnxMDAXplErrorTime              TimeStamp,
    tmnxMDAXplFailedCount            Gauge32,
    tmnxMDAAtmMode                   TmnxMdaAtmMode,
    tmnxMDAEgrHsmdaThrshLoBrstMult   Integer32,
    tmnxMDAEgrHsmdaThrshHiBrstInc    Integer32,
    tmnxMDAIsaTunnelGroup            TmnxTunnelGroupIdOrZero,
    tmnxMDAIsaTunnelGroupInUse       TruthValue,
    tmnxMDAHwPowerPriority           Unsigned32,
    tmnxMDAFailOnError               BITS,
    tmnxMDAEgrXplErrThreshold        Unsigned32,
    tmnxMDAEgrXplErrWindow           Unsigned32,
    tmnxMDAIngrXplErrThreshold       Unsigned32,
    tmnxMDAIngrXplErrWindow          Unsigned32,
    tmnxMDAResetOnRecoverableError   TruthValue
}

tmnxMDASlotNum                   OBJECT-TYPE
    SYNTAX      Unsigned32 (0..16)
    MAX-ACCESS  not-accessible
    STATUS      current
    DESCRIPTION
        "The unique value which identifies this MDA slot within a
         specific IOM card in the system.  Rows with a tmnxMDASlotNum
         value of zero (0) represent the special case of an IOM card
         without MDA slots but that instead has its ports directly
         on the IOM card itself.  In that case, there should be only
         that one row entry in the tmnxMDATable for that IOM card."
    ::= { tmnxMDAEntry 1 }

tmnxMDASupportedTypes            OBJECT-TYPE
    SYNTAX      TmnxMDASuppType
    MAX-ACCESS  read-only
    STATUS      current
    DESCRIPTION
        "A bit-mask that indicates what MDA card types can be configured in
         this slot in this chassis."
    ::= { tmnxMDAEntry 2 }

tmnxMDAAllowedTypes              OBJECT-TYPE
    SYNTAX      TmnxMdaType
    MAX-ACCESS  read-write
    STATUS      obsolete
    DESCRIPTION
        "An integer that specified what MDA card types the administrator has
         designated be allowed to be inserted into this slot. If the slot has
         not-been pre-provisioned and a MDA card that does not match one of the
         allowed types is inserted into this slot, a mismatch alarm will be
         raised.

         The object was made obsolete in the 3.0 release."
    ::= { tmnxMDAEntry 3 }

tmnxMDAAssignedType              OBJECT-TYPE
    SYNTAX      TmnxMdaType
    MAX-ACCESS  read-write
    STATUS      current
    DESCRIPTION
        "An integer that specifies the administratively assigned
         (pre-provisioned) MDA card type that should occupy this slot in
         this chassis.  If tmnxMDAAssignedType has a value of
         'unassigned', this slot has not yet been pre-provisioned."
    DEFVAL      { 1 }
    ::= { tmnxMDAEntry 4 }

tmnxMDAEquippedType              OBJECT-TYPE
    SYNTAX      TmnxMdaType
    MAX-ACCESS  read-only
    STATUS      current
    DESCRIPTION
        "An integer that indicates the MDA card type that is physically
         inserted into this slot in this chassis.  If the slot has been
         pre-provisioned, tmnxMDAAssignedType is not equal 'unassigned',
         and the value of tmnxMDAEquippedType is not the same as
         tmnxMDAAssignedType, a mismatch alarm will be raised.
         A value of 0 indicates the equipped MDA is not supported by
         this software release."
    ::= { tmnxMDAEntry 5 }

tmnxMDAHwIndex                   OBJECT-TYPE
    SYNTAX      TmnxHwIndex
    MAX-ACCESS  read-only
    STATUS      current
    DESCRIPTION
        "The value of tmnxMDAHwIndex indicates the tmnxHwIndex into the
         tmnxHwTable for the row entry that represents the hardware component
         information for this MDA card."
    ::= { tmnxMDAEntry 6 }

tmnxMDAMaxPorts                  OBJECT-TYPE
    SYNTAX      Integer32
    MAX-ACCESS  read-only
    STATUS      current
    DESCRIPTION
        "The maximum number of ports that can be equipped on this MDA card."
    ::= { tmnxMDAEntry 7 }

tmnxMDAEquippedPorts             OBJECT-TYPE
    SYNTAX      Unsigned32
    MAX-ACCESS  read-only
    STATUS      current
    DESCRIPTION
        "The value of tmnxMDAEquippedPorts indicates the number of ports
         equipped on this MDA card."
    ::= { tmnxMDAEntry 8 }

tmnxMDATxTimingSelected          OBJECT-TYPE
    SYNTAX      INTEGER {
        cpmCardA      (1),
        cpmCardB      (2),
        local         (3),
        holdover      (4),
        notApplicable (5),
        cpmCardC      (6),
        cpmCardD      (7)
    }
    MAX-ACCESS  read-only
    STATUS      current
    DESCRIPTION
        "The value of tmnxMDATxTimingSelected indicates the transmit timing
         method which is presently selected and being used by this MDA.
         tmnxMDATxTimingSelected will be set to 'notApplicable (5)' if this MDA
         does not use the transmit timing subsystem."
    ::= { tmnxMDAEntry 10 }

tmnxMDASyncIfTimingStatus        OBJECT-TYPE
    SYNTAX      INTEGER {
        qualified      (1),
        not-qualified  (2),
        not-applicable (3)
    }
    MAX-ACCESS  read-only
    STATUS      current
    DESCRIPTION
        "Indicates the status of the synchronous equipment timing subsystem. If
         the tmnxSyncIfTimingRef1Qualified and tmnxSyncIfTimingRef2Qualified
         are both set to 'not-qualified, then tmnxMDASyncIfTimingStatus is set
         to 'not-qualified'. If any of the timing references is in use, then
         tmnxMDASyncIfTimingStatus is set to 'qualified'.
         tmnxMDASyncIfTimingStatus will be set to 'not-applicable' if this MDA
         does not use the transmit timing subsystem."
    ::= { tmnxMDAEntry 11 }

tmnxMDANetworkIngQueues          OBJECT-TYPE
    SYNTAX      TNamedItem
    MAX-ACCESS  read-write
    STATUS      current
    DESCRIPTION
        "Specifies the network queue policy being used for this object to
         define the queueing structure for this object."
    DEFVAL      { "default" }
    ::= { tmnxMDAEntry 12 }

tmnxMDACapabilities              OBJECT-TYPE
    SYNTAX      BITS {
        isEthernet    (0),
        isSonet       (1),
        isTDM         (2),
        supportsPPP   (3),
        supportsFR    (4),
        supportsATM   (5),
        supportscHDLC (6),
        isCMA         (7),
        supportsCEM   (8),
        isSerial      (9),
        isWireless    (10)
    }
    MAX-ACCESS  read-only
    STATUS      current
    DESCRIPTION
        "tmnxMDACapabilities indicates the capabilities of this MDA. It
         identifies the type of MDA and the protocols that can run on it."
    ::= { tmnxMDAEntry 13 }

tmnxMDAMinChannelization         OBJECT-TYPE
    SYNTAX      TmnxMDAChanType
    MAX-ACCESS  read-only
    STATUS      current
    DESCRIPTION
        "tmnxMDAMinChannelization indicates the minimum size of the channel
         that can exist on this MDA."
    ::= { tmnxMDAEntry 14 }

tmnxMDAMaxChannelization         OBJECT-TYPE
    SYNTAX      TmnxMDAChanType
    MAX-ACCESS  read-only
    STATUS      current
    DESCRIPTION
        "tmnxMDAMaxChannelization indicates the maximum size of the channel
         that can exist on this MDA."
    ::= { tmnxMDAEntry 15 }

tmnxMDAMaxChannels               OBJECT-TYPE
    SYNTAX      Unsigned32
    MAX-ACCESS  read-only
    STATUS      current
    DESCRIPTION
        "tmnxMDAMaxChannels is applicable for SONET and TDM MDAs only. It
         indicates the total number of leaf SONET paths, TDM channels and
         bundles on the MDA that may be configured to pass traffic."
    ::= { tmnxMDAEntry 16 }

tmnxMDAChannelsInUse             OBJECT-TYPE
    SYNTAX      Unsigned32
    MAX-ACCESS  read-only
    STATUS      current
    DESCRIPTION
        "tmnxMDAChannelsInUse is applicable for SONET and TDM MDAs only.  It
         indicates the total number of leaf SONET paths, TDM channels and
         bundles on the MDA which are in use.  A leaf SONET path or TDM
         channel which is currently capable of passing traffic is considered
         to be in use.  Also, a SONET path or TDM channel which is
         channelized and has no subchannels capable of passing traffic
         is considered to be in use.  A SONET path or TDM channel which is
         channelized and has one or more subchannels capable of passing
         traffic is not considered to be in use, although the subchannels
         themselves are considered to be in use.  A bundle is considered to
         be a channel in use as are each of its members since they are TDM
         channels capable of passing traffic."
    ::= { tmnxMDAEntry 17 }

tmnxMDACcagId                    OBJECT-TYPE
    SYNTAX      TmnxCcagId
    MAX-ACCESS  read-write
    STATUS      current
    DESCRIPTION
        "When tmnxMDAAssignedType has a value of 'cca' , the value of
         tmnxMDACcagId specifies the Cross Connect Aggregation Group (CCAG)
         entry this MDA is provisioned on.  If this entry does not represent
         a 'cca' MDA or is not associated with a CCAG, tmnxMDACcagId
         has a value of zero. "
    DEFVAL      { 0 }
    ::= { tmnxMDAEntry 18 }

tmnxMDAReboot                    OBJECT-TYPE
    SYNTAX      TmnxActionType
    MAX-ACCESS  read-write
    STATUS      current
    DESCRIPTION
        "Setting this variable to 'doAction' causes the MDA to execute a
         soft-reboot."
    DEFVAL      { notApplicable }
    ::= { tmnxMDAEntry 19 }

tmnxMDAHiBwMcastSource           OBJECT-TYPE
    SYNTAX      TruthValue
    MAX-ACCESS  read-write
    STATUS      obsolete
    DESCRIPTION
        "The value of tmnxMDAHiBwMcastSource specifies if this MDA should
         attempt to allocate separate fabric planes to allocate high bandwidth
         multicast traffic taps.

         tmnxMDAHiBwMcastGroup must be set in the same SNMP request PDU with
         tmnxMDAHiBwMcastSource or an 'inconsistentValue' error will be
         returned.

         This object was obsoleted from release 15.0R1."
    DEFVAL      { false }
    ::= { tmnxMDAEntry 20 }

tmnxMDAHiBwMcastAlarm            OBJECT-TYPE
    SYNTAX      TruthValue
    MAX-ACCESS  read-write
    STATUS      obsolete
    DESCRIPTION
        "The value of tmnxMDAHiBwMcastAlarm specifies if a
         tmnxChassisHiBwMcastAlarm alarm is raised if there are more than one
         high bandwidth multicast traffic taps sharing a plane.

         This object was obsoleted from release 15.0R1."
    DEFVAL      { true }
    ::= { tmnxMDAEntry 21 }

tmnxMDAHiBwMcastTapCount         OBJECT-TYPE
    SYNTAX      Gauge32
    MAX-ACCESS  read-only
    STATUS      obsolete
    DESCRIPTION
        "The value of tmnxMDAHiBwMcastTapCount indicates the number of high
         bandwidth multicast traffic taps on this MDA.

         This object was obsoleted from release 15.0R1."
    ::= { tmnxMDAEntry 22 }

tmnxMDAHiBwMcastGroup            OBJECT-TYPE
    SYNTAX      Unsigned32 (0..32)
    MAX-ACCESS  read-write
    STATUS      obsolete
    DESCRIPTION
        "The value of tmnxMDAHiBwMcastGroup specifies the group of high
         bandwidth multicast traffic taps to which this tap belongs.

         A value of '0' specifies that this tap is not a member of any High
         Bandwidth Multicast group.

         On an IOM of type 'iom-10g', the value of tmnxMDAHiBwMcastGroup should
         be the same as the value of tmnxMDAHiBwMcastGroup set on the other MDA
         residing on the IOM if the tmnxMDAHiBwMcastSource is set to 'true'.
         Attempt to set to different values will result in an
         'inconsistentValue' error.

         tmnxMDAHiBwMcastGroup must be set in the same SNMP request PDU with
         tmnxMDAHiBwMcastSource or an 'inconsistentValue' error will be
         returned.

         This object was obsoleted from release 15.0R1."
    DEFVAL      { 0 }
    ::= { tmnxMDAEntry 23 }

tmnxMDAClockMode                 OBJECT-TYPE
    SYNTAX      INTEGER {
        notApplicable (0),
        adaptive      (1),
        differential  (2)
    }
    MAX-ACCESS  read-write
    STATUS      current
    DESCRIPTION
        "The value of tmnxMDAClockMode specifies the clock mode of the MDA.

         notApplicable - The MDA does not support any clock modes or domains.
         adaptive      - The MDA is in 'adaptive' clock mode.  This allows
                         adaptive clock domains to be created.
         differential  - The MDA is in 'differential clock mode.  This allows
                         differential clock domains to be created.

         The value of tmnxMDAClockMode can be changed when there are no ports
         created on the MDA.  If there are ports created, a shutdown of the
         MDA is required in order to change the value."
    DEFVAL      { notApplicable }
    ::= { tmnxMDAEntry 24 }

tmnxMDADiffTimestampFreq         OBJECT-TYPE
    SYNTAX      Unsigned32 (0 | 19440 | 77760 | 103680)
    UNITS       "kilohertz"
    MAX-ACCESS  read-write
    STATUS      current
    DESCRIPTION
        "The value of tmnxMDADiffTimestampFreq specifies the differential
         timestamp frequency of the differential clock on the MDA.

         The value must be a multiple of 8 KHz.

         This value can only be changed if the value of tmnxMDAClockMode is
         'differential (2)' and there are no ports created on the MDA.  If
         there are ports created, a shutdown of the MDA is required in order
         to change the value.

         If the value of tmnxMDAClockMode is 'differential (2) then the default
         is 103,680 KHz. If the value of tmnxMDAClockMode is not 'differential
         (2)' then this value is 0 KHz and cannot be changed."
    DEFVAL      { 0 }
    ::= { tmnxMDAEntry 25 }

tmnxMDAIngHsmdaSchedPolicy       OBJECT-TYPE
    SYNTAX      TNamedItemOrEmpty
    MAX-ACCESS  read-write
    STATUS      obsolete
    DESCRIPTION
        "The value of tmnxMDAIngHsmdaSchedPolicy specifies the name of High
         Scale MDA (HSMDA) scheduler policy to use on the ingress of the MDA.

         An 'inconsistentValue' error is returned if this object is set to a
         value which does not have a corresponding entry in
         TIMETRA-QOS-MIB::tHsmdaSchedulerPlcyTable.

         When the value of tmnxMDAAssignedType specifies a non-HSMDA MDA Type,
         an 'inconsistentValue' error is returned if this object is set to any
         non-empty string.

         This object is obsoleted in 10.0 Release."
    DEFVAL      { "" }
    ::= { tmnxMDAEntry 26 }

tmnxMDAMcPathMgmtBwPlcyName      OBJECT-TYPE
    SYNTAX      TNamedItem
    MAX-ACCESS  read-write
    STATUS      obsolete
    DESCRIPTION
        "The value of tmnxMDAMcPathMgmtBwPlcyName specifies the multicast
         policy name configured on the MDA.

         This object was obsoleted from release 15.0R1."
    DEFVAL      { "default" }
    ::= { tmnxMDAEntry 27 }

tmnxMDAMcPathMgmtPriPathLimit    OBJECT-TYPE
    SYNTAX      Unsigned32 (0..2000)
    UNITS       "mega-bits-per-second"
    MAX-ACCESS  read-write
    STATUS      obsolete
    DESCRIPTION
        "The value of tmnxMDAMcPathMgmtPriPathLimit specifies the primary path
         limit for the MDA.

         This object was obsoleted from release 15.0R1."
    DEFVAL      { 0 }
    ::= { tmnxMDAEntry 28 }

tmnxMDAMcPathMgmtSecPathLimit    OBJECT-TYPE
    SYNTAX      Unsigned32 (0..2000)
    UNITS       "mega-bits-per-second"
    MAX-ACCESS  read-write
    STATUS      obsolete
    DESCRIPTION
        "The value of tmnxMDAMcPathMgmtSecPathLimit specifies the secondary
         path limit for the MDA.

         This object was obsoleted from release 15.0R1."
    DEFVAL      { 0 }
    ::= { tmnxMDAEntry 29 }

tmnxMDAMcPathMgmtAncPathLimit    OBJECT-TYPE
    SYNTAX      Unsigned32 (0..5000)
    UNITS       "mega-bits-per-second"
    MAX-ACCESS  read-write
    STATUS      obsolete
    DESCRIPTION
        "The value of tmnxMDAMcPathMgmtAncPathLimit specifies the ancillary
         path limit for the MDA.

         This object was obsoleted from release 15.0R1."
    DEFVAL      { 0 }
    ::= { tmnxMDAEntry 30 }

tmnxMDAMcPathMgmtAdminState      OBJECT-TYPE
    SYNTAX      TmnxAdminState
    MAX-ACCESS  read-write
    STATUS      obsolete
    DESCRIPTION
        "The value of tmnxMDAMcPathMgmtAdminState specifies administrative
         state of this multicast path on the MDA.

         This object was obsoleted from release 15.0R1."
    DEFVAL      { outOfService }
    ::= { tmnxMDAEntry 31 }

tmnxMDAIngNamedPoolPolicy        OBJECT-TYPE
    SYNTAX      TNamedItemOrEmpty
    MAX-ACCESS  read-write
    STATUS      current
    DESCRIPTION
        "The value of tmnxMDAIngNamedPoolPolicy specifies a named pool policy
         associated with an MDA ingress context. The policy governs the way
         named pools are created at the MDA level."
    DEFVAL      { "" }
    ::= { tmnxMDAEntry 32 }

tmnxMDAEgrNamedPoolPolicy        OBJECT-TYPE
    SYNTAX      TNamedItemOrEmpty
    MAX-ACCESS  read-write
    STATUS      current
    DESCRIPTION
        "The value of tmnxMDAEgrNamedPoolPolicy specifies a named pool policy
         associated with an MDA egress context. The policy governs the way
         named pools are created at the MDA level."
    DEFVAL      { "" }
    ::= { tmnxMDAEntry 33 }

tmnxMDAIngHsmdaPoolPolicy        OBJECT-TYPE
    SYNTAX      TNamedItemOrEmpty
    MAX-ACCESS  read-write
    STATUS      obsolete
    DESCRIPTION
        "The value of tmnxMDAIngHsmdaPoolPolicy specifies  the name of
         High Scale MDA (HSMDA) pool policy to use on the ingress
         of the MDA.

         An 'inconsistentValue' error is returned if this object is set to a
         value which does not have a corresponding entry in
         TIMETRA-QOS-MIB::tHsmdaPoolPolicyTable.

         When the value of tmnxMDAAssignedType specifies a non-HSMDA MDA Type,
         an 'inconsistentValue' error is returned if this object is set to any
         non-empty string.

         This object is obsoleted in 10.0 Release."
    DEFVAL      { "" }
    ::= { tmnxMDAEntry 34 }

tmnxMDAEgrHsmdaPoolPolicy        OBJECT-TYPE
    SYNTAX      TNamedItemOrEmpty
    MAX-ACCESS  read-write
    STATUS      current
    DESCRIPTION
        "The value of tmnxMDAEgrHsmdaPoolPolicy specifies  the name of
         High Scale MDA (HSMDA) pool policy to use on the egress
         of the MDA.

         An 'inconsistentValue' error is returned if this object is set to a
         value which does not have a corresponding entry in
         TIMETRA-QOS-MIB::tHsmdaPoolPolicyTable.

         When the value of tmnxMDAAssignedType specifies a non-HSMDA MDA Type,
         an 'inconsistentValue' error is returned if this object is set to any
         non-empty string."
    DEFVAL      { "" }
    ::= { tmnxMDAEntry 35 }

tmnxMDAMcPathMgmtPriInUseBw      OBJECT-TYPE
    SYNTAX      Gauge32
    UNITS       "Kbps"
    MAX-ACCESS  read-only
    STATUS      obsolete
    DESCRIPTION
        "The value of tmnxMDAMcPathMgmtPriInUseBw indicates the in use ingress
         multicast bandwidth for the primary forwarding path.

         This object was obsoleted from release 15.0R1."
    ::= { tmnxMDAEntry 36 }

tmnxMDAMcPathMgmtSecInUseBw      OBJECT-TYPE
    SYNTAX      Gauge32
    UNITS       "Kbps"
    MAX-ACCESS  read-only
    STATUS      obsolete
    DESCRIPTION
        "The value of tmnxMDAMcPathMgmtSecInUseBw indicates the in use ingress
         multicast bandwidth for the secondary forwarding path.

         This object was obsoleted from release 15.0R1."
    ::= { tmnxMDAEntry 37 }

tmnxMDAMcPathMgmtAncInUseBw      OBJECT-TYPE
    SYNTAX      Gauge32
    UNITS       "Kbps"
    MAX-ACCESS  read-only
    STATUS      obsolete
    DESCRIPTION
        "The value of tmnxMDAMcPathMgmtAncInUseBw indicates the in use ingress
         multicast bandwidth for the ancillary forwarding path.

         This object was obsoleted from release 15.0R1."
    ::= { tmnxMDAEntry 38 }

tmnxMDAMcPathMgmtBlkHoleInUseBw  OBJECT-TYPE
    SYNTAX      Gauge32
    UNITS       "Kbps"
    MAX-ACCESS  read-only
    STATUS      obsolete
    DESCRIPTION
        "The value of tmnxMDAMcPathMgmtBlkHoleInUseBw indicates the bandwidth
         of the ingress multicast traffic that is being black holed on the MDA.

         This object was obsoleted from release 15.0R1."
    ::= { tmnxMDAEntry 39 }

tmnxMDASynchronousEthernet       OBJECT-TYPE
    SYNTAX      INTEGER {
        not-applicable (0),
        enabled        (1),
        disabled       (2)
    }
    MAX-ACCESS  read-write
    STATUS      current
    DESCRIPTION
        "The value of tmnxMDASynchronousEthernet specifies whether or not the
         MDA maintains synchronous Ethernet (syncE) communication on all of its
         ports.

         not-applicable - The MDA does not support synchronous Ethernet.
         enabled        - The MDA is in synchronous mode.
         disabled       - The MDA is in asynchronous mode (default).

         On MDAs that do not support synchronous ethernet the only supported
         value is 'not-applicable (0)'.

         If tmnxMDASynchronousEthernet is 'enabled (1)' then any port on the
         MDA can be used as a source port in the tmnxSyncIfTimingTable."
    DEFVAL      { disabled }
    ::= { tmnxMDAEntry 40 }

tmnxMDAXplErrorTime              OBJECT-TYPE
    SYNTAX      TimeStamp
    MAX-ACCESS  read-only
    STATUS      current
    DESCRIPTION
        "The value of tmnxMDAXplErrorTime indicates the last time when the
         tmnxEqMdaXplError notification occurred."
    ::= { tmnxMDAEntry 41 }

tmnxMDAXplFailedCount            OBJECT-TYPE
    SYNTAX      Gauge32
    MAX-ACCESS  read-only
    STATUS      current
    DESCRIPTION
        "The value of tmnxMDAXplFailedCount indicates the number of egress XPL
         failures on the MDA since startup."
    ::= { tmnxMDAEntry 42 }

tmnxMDAAtmMode                   OBJECT-TYPE
    SYNTAX      TmnxMdaAtmMode
    MAX-ACCESS  read-write
    STATUS      current
    DESCRIPTION
        "The value of tmnxMDAAtmMode specifies the maximum number of Virtual
         Circuits for the MDA.

         On MDA's that do not support ATM, 'notApplicable' is the only allowed
         value and this is also the default value.

         On MDA's that support ATM, the default value is 'max8kVc'."
    ::= { tmnxMDAEntry 43 }

tmnxMDAEgrHsmdaThrshLoBrstMult   OBJECT-TYPE
    SYNTAX      Integer32 (-1 | 1..65536)
    UNITS       "bytes per megabit of rate"
    MAX-ACCESS  read-write
    STATUS      current
    DESCRIPTION
        "The value of tmnxMDAEgrHsmdaThrshLoBrstMult specifies the bytes per
         megabit/second of rate multiplier for the aggregate rate of the queues
         pertaining to the low burst threshold in the queue group.

         When set to the default value '-1', the system will adopt the lowest
         usable threshold as a default setting per rate."
    DEFVAL      { -1 }
    ::= { tmnxMDAEntry 44 }

tmnxMDAEgrHsmdaThrshHiBrstInc    OBJECT-TYPE
    SYNTAX      Integer32 (-1..65536)
    UNITS       "bytes"
    MAX-ACCESS  read-write
    STATUS      current
    DESCRIPTION
        "The value of tmnxMDAEgrHsmdaThrshHiBrstInc specifies the incremental
         number of bytes above the low burst limit to be used as the high burst
         threshold for the aggregate rate of the queues pertaining to the high
         burst threshold in the queue group.

         When set to the default value '-1', the system will default to a value
         of '4000' bytes."
    DEFVAL      { -1 }
    ::= { tmnxMDAEntry 45 }

tmnxMDAIsaTunnelGroup            OBJECT-TYPE
    SYNTAX      TmnxTunnelGroupIdOrZero
    MAX-ACCESS  read-write
    STATUS      current
    DESCRIPTION
        "The value of tmnxMDAIsaTunnelGroup specifies the tunnel-group
         identifiter associated with this MDA."
    DEFVAL      { 0 }
    ::= { tmnxMDAEntry 46 }

tmnxMDAIsaTunnelGroupInUse       OBJECT-TYPE
    SYNTAX      TruthValue
    MAX-ACCESS  read-only
    STATUS      current
    DESCRIPTION
        "The value of tmnxMDAIsaTunnelGroupInUse indicates if this MDA is
         active in the Integrated Service Adaptor tunnel group indicated by
         tmnxMDAIsaTunnelGroup."
    ::= { tmnxMDAEntry 47 }

tmnxMDAHwPowerPriority           OBJECT-TYPE
    SYNTAX      Unsigned32 (1..200)
    MAX-ACCESS  read-write
    STATUS      current
    DESCRIPTION
        "The value of tmnxMDAHwPowerPriority specifies the functional priority
         of the MDA. Lower priority (higher numerically) MDAs will power off
         sooner than higher priority (lower numerically) MDAs during a power
         shortage. Lower priority MDAs will also power up after higher priority
         MDAs."
    DEFVAL      { 150 }
    ::= { tmnxMDAEntry 48 }

tmnxMDAFailOnError               OBJECT-TYPE
    SYNTAX      BITS {
        eventGroupA (0)
    }
    MAX-ACCESS  read-write
    STATUS      current
    DESCRIPTION
        "The value of tmnxMDAFailOnError specifies the set of events that, if
         triggered, will cause the MDA to fail. The suppression or generation
         of the NOTIFICATION-TYPE event is independent of the MDA failing.

         The following set of events are configurable:
              eventGroupA (0) - tmnxEqMdaXplError
                              - tmnxEqMdaIngrXplError

         If an XPL error is declared, the MDA is declared failed."
    DEFVAL      { {} }
    ::= { tmnxMDAEntry 49 }

tmnxMDAEgrXplErrThreshold        OBJECT-TYPE
    SYNTAX      Unsigned32 (1..1000000)
    UNITS       "XPL errors"
    MAX-ACCESS  read-write
    STATUS      current
    DESCRIPTION
        "The value of tmnxMDAEgrXplErrThreshold specifies the threshold for
         egress XPL errors that determine a failure scenario."
    DEFVAL      { 1000 }
    ::= { tmnxMDAEntry 50 }

tmnxMDAEgrXplErrWindow           OBJECT-TYPE
    SYNTAX      Unsigned32 (1..1440)
    UNITS       "minutes"
    MAX-ACCESS  read-write
    STATUS      current
    DESCRIPTION
        "The value of tmnxMDAEgrXplErrWindow specifies the window size in
         minutes for egress XPL errors that determine a failure scenario."
    DEFVAL      { 60 }
    ::= { tmnxMDAEntry 51 }

tmnxMDAIngrXplErrThreshold       OBJECT-TYPE
    SYNTAX      Unsigned32 (1..1000000)
    UNITS       "XPL errors"
    MAX-ACCESS  read-write
    STATUS      current
    DESCRIPTION
        "The value of tmnxMDAIngrXplErrThreshold specifies the threshold for
         ingress XPL errors that determine a failure scenario."
    DEFVAL      { 1000 }
    ::= { tmnxMDAEntry 52 }

tmnxMDAIngrXplErrWindow          OBJECT-TYPE
    SYNTAX      Unsigned32 (1..1440)
    UNITS       "minutes"
    MAX-ACCESS  read-write
    STATUS      current
    DESCRIPTION
        "The value of tmnxMDAIngrXplErrWindow specifies the window size in
         minutes for ingress XPL errors that determine a failure scenario."
    DEFVAL      { 60 }
    ::= { tmnxMDAEntry 53 }

tmnxMDAResetOnRecoverableError   OBJECT-TYPE
    SYNTAX      TruthValue
    MAX-ACCESS  read-write
    STATUS      current
    DESCRIPTION
        "The value of tmnxMDAResetOnRecoverableError specifies whether or not
         the system resets the MDA when there are fatal memory parity errors on
         one of the Q-chips on the card with which this MDA is associated.

         If the value of tmnxMDAResetOnRecoverableError is 'true (1)' and there
         is a fatal memory parity error on a Q-chip, the system will reset the
         MDA but not fail it, even if tmnxMDAFailOnError is 'true (1)'."
    DEFVAL      { false }
    ::= { tmnxMDAEntry 54 }

tmnxCardTypeTable                OBJECT-TYPE
    SYNTAX      SEQUENCE OF TmnxCardTypeEntry
    MAX-ACCESS  not-accessible
    STATUS      current
    DESCRIPTION
        "The card type table has an entry for each card model supported by the
         system. Some example card types are: 'iom3-xp', 'sfm4-12',
         'imm12-10gb-sf+'."
    ::= { tmnxCardObjs 9 }

tmnxCardTypeEntry                OBJECT-TYPE
    SYNTAX      TmnxCardTypeEntry
    MAX-ACCESS  not-accessible
    STATUS      current
    DESCRIPTION
        "Each row entry represents an Nokia SROS series Card model. Rows in
         this table are created by the agent at initialization and cannot be
         created or destroyed by SNMP Get or Set requests."
    INDEX       { tmnxCardTypeIndex }
    ::= { tmnxCardTypeTable 1 }

TmnxCardTypeEntry                ::= SEQUENCE
{
    tmnxCardTypeIndex                TmnxCardType,
    tmnxCardTypeName                 TNamedItemOrEmpty,
    tmnxCardTypeDescription          TItemDescription,
    tmnxCardTypeStatus               TruthValue
}

tmnxCardTypeIndex                OBJECT-TYPE
    SYNTAX      TmnxCardType
    MAX-ACCESS  not-accessible
    STATUS      current
    DESCRIPTION
        "The unique index value which identifies this type of Nokia SROS series
         card model."
    ::= { tmnxCardTypeEntry 1 }

tmnxCardTypeName                 OBJECT-TYPE
    SYNTAX      TNamedItemOrEmpty
    MAX-ACCESS  read-only
    STATUS      current
    DESCRIPTION
        "The administrative name that identifies this type of Nokia
         SROS series card model.  This name string may be used in
         CLI commands to specify a particular card model type."
    ::= { tmnxCardTypeEntry 2 }

tmnxCardTypeDescription          OBJECT-TYPE
    SYNTAX      TItemDescription
    MAX-ACCESS  read-only
    STATUS      current
    DESCRIPTION
        "A detailed description of this Nokia SROS series card model."
    ::= { tmnxCardTypeEntry 3 }

tmnxCardTypeStatus               OBJECT-TYPE
    SYNTAX      TruthValue
    MAX-ACCESS  read-only
    STATUS      current
    DESCRIPTION
        "When tmnxCardTypeStatus has a value of 'true' it indicates that
         this card model is supported in this revision of the management
         software.  When it has a value of 'false' there is no support."
    ::= { tmnxCardTypeEntry 4 }

tmnxMdaTypeTable                 OBJECT-TYPE
    SYNTAX      SEQUENCE OF TmnxMdaTypeEntry
    MAX-ACCESS  not-accessible
    STATUS      current
    DESCRIPTION
        "The MDA type table has an entry for each MDA card model supported by
         the system. Some example MDA types are: 'm10-1gb-xp-sfp', 'isa-bb',
         'imm1-100gb-xp-cfp', 'p160-1gb-csfp', 'x40-10g-sfp'."
    ::= { tmnxCardObjs 10 }

tmnxMdaTypeEntry                 OBJECT-TYPE
    SYNTAX      TmnxMdaTypeEntry
    MAX-ACCESS  not-accessible
    STATUS      current
    DESCRIPTION
        "Each row entry represents an Nokia SROS series MDA card
         model.  Rows in this table are created by the agent at initialization
         and cannot be created or destroyed by SNMP Get or Set requests."
    INDEX       { tmnxMdaTypeIndex }
    ::= { tmnxMdaTypeTable 1 }

TmnxMdaTypeEntry                 ::= SEQUENCE
{
    tmnxMdaTypeIndex                 TmnxMdaType,
    tmnxMdaTypeName                  TNamedItemOrEmpty,
    tmnxMdaTypeDescription           TItemDescription,
    tmnxMdaTypeStatus                TruthValue
}

tmnxMdaTypeIndex                 OBJECT-TYPE
    SYNTAX      TmnxMdaType
    MAX-ACCESS  not-accessible
    STATUS      current
    DESCRIPTION
        "The unique index value which identifies this type of Nokia SROS series
         MDA card model."
    ::= { tmnxMdaTypeEntry 1 }

tmnxMdaTypeName                  OBJECT-TYPE
    SYNTAX      TNamedItemOrEmpty
    MAX-ACCESS  read-only
    STATUS      current
    DESCRIPTION
        "The administrative name that identifies this type of Nokia
         SROS series MDA card model.  This name string may be used
         in CLI commands to specify a particular MDA card model type."
    ::= { tmnxMdaTypeEntry 2 }

tmnxMdaTypeDescription           OBJECT-TYPE
    SYNTAX      TItemDescription
    MAX-ACCESS  read-only
    STATUS      current
    DESCRIPTION
        "A detailed description of this Nokia SROS series MDA card model."
    ::= { tmnxMdaTypeEntry 3 }

tmnxMdaTypeStatus                OBJECT-TYPE
    SYNTAX      TruthValue
    MAX-ACCESS  read-only
    STATUS      current
    DESCRIPTION
        "When tmnxMdaTypeStatus has a value of 'true' it indicates that
         this MDA card model is supported in this revision of the management
         software.  When it has a value of 'false' there is no support."
    ::= { tmnxMdaTypeEntry 4 }

tmnxSyncIfTimingTable            OBJECT-TYPE
    SYNTAX      SEQUENCE OF TmnxSyncIfTimingEntry
    MAX-ACCESS  not-accessible
    STATUS      current
    DESCRIPTION
        "The synchronous interface timing table has an entry for each cpm card
         in the system."
    ::= { tmnxCardObjs 11 }

tmnxSyncIfTimingEntry            OBJECT-TYPE
    SYNTAX      TmnxSyncIfTimingEntry
    MAX-ACCESS  not-accessible
    STATUS      current
    DESCRIPTION
        "A row represents the configuration of Synchronous Equipment Timing
         Source (SETS) of the system. Entries cannot be created and deleted
         via SNMP SET operations.  When a tmnxCpmCardEntry is created, a
         tmnxSyncIfTimingEntry is created.  SNMP set operations with
         tmnxCpmCardSlotNum of the secondary CPM will be denied.

         If the value of the reference source port is a valid Port ID then the
         reference is a port.  If the value of the source hardware is a valid
         non-zero HWIndex then the source is the hardware specified by the
         HWIndex."
    AUGMENTS    { tmnxCpmCardEntry }
    ::= { tmnxSyncIfTimingTable 1 }

TmnxSyncIfTimingEntry            ::= SEQUENCE
{
    tmnxSyncIfTimingRevert           TruthValue,
    tmnxSyncIfTimingRefOrder1        TmnxSETSRefSource,
    tmnxSyncIfTimingRefOrder2        TmnxSETSRefSource,
    tmnxSyncIfTimingRef1SrcPort      TmnxPortID,
    tmnxSyncIfTimingRef1AdminStatus  TmnxPortAdminStatus,
    tmnxSyncIfTimingRef1InUse        TruthValue,
    tmnxSyncIfTimingRef1Qualified    TmnxSETSRefQualified,
    tmnxSyncIfTimingRef1Alarm        TmnxSETSRefAlarm,
    tmnxSyncIfTimingRef2SrcPort      TmnxPortID,
    tmnxSyncIfTimingRef2AdminStatus  TmnxPortAdminStatus,
    tmnxSyncIfTimingRef2InUse        TruthValue,
    tmnxSyncIfTimingRef2Qualified    TmnxSETSRefQualified,
    tmnxSyncIfTimingRef2Alarm        TmnxSETSRefAlarm,
    tmnxSyncIfTimingFreqOffset       Integer32,
    tmnxSyncIfTimingStatus           TmnxSETSStatus,
    tmnxSyncIfTimingRefOrder3        TmnxSETSRefSource,
    tmnxSyncIfTimingBITSIfType       TmnxBITSIfType,
    tmnxSyncIfTimingBITSAdminStatus  TmnxPortAdminStatus,
    tmnxSyncIfTimingBITSInUse        TruthValue,
    tmnxSyncIfTimingBITSQualified    TmnxSETSRefQualified,
    tmnxSyncIfTimingBITSAlarm        TmnxSETSRefAlarm,
    tmnxSyncIfTimingRef1SrcHw        TmnxHwIndexOrZero,
    tmnxSyncIfTimingRef1BITSIfType   TmnxBITSIfType,
    tmnxSyncIfTimingRef2SrcHw        TmnxHwIndexOrZero,
    tmnxSyncIfTimingRef2BITSIfType   TmnxBITSIfType,
    tmnxSyncIfTimingBITSOutAdmStatus TmnxPortAdminStatus,
    tmnxSyncIfTimingBITSOutLineLen   INTEGER,
    tmnxSyncIfTimingRef1CfgQltyLevel TmnxSSMQualityLevel,
    tmnxSyncIfTimingRef1RxQltyLevel  TmnxSSMQualityLevel,
    tmnxSyncIfTimingRef2CfgQltyLevel TmnxSSMQualityLevel,
    tmnxSyncIfTimingRef2RxQltyLevel  TmnxSSMQualityLevel,
    tmnxSyncIfTimingBITSCfgQltyLevel TmnxSSMQualityLevel,
    tmnxSyncIfTimingBITSRxQltyLevel  TmnxSSMQualityLevel,
    tmnxSyncIfTimingBITS2InUse       TruthValue,
    tmnxSyncIfTimingBITS2Qualified   TmnxSETSRefQualified,
    tmnxSyncIfTimingBITS2Alarm       TmnxSETSRefAlarm,
    tmnxSyncIfTimingBITS2RxQltyLevel TmnxSSMQualityLevel,
    tmnxSyncIfTimingRef1State        TmnxRefInState,
    tmnxSyncIfTimingRef2State        TmnxRefInState,
    tmnxSyncIfTimingBITSState        TmnxRefInState,
    tmnxSyncIfTimingBITS2State       TmnxRefInState,
    tmnxSyncIfTimingRef1NationalUse  Unsigned32,
    tmnxSyncIfTimingRef2NationalUse  Unsigned32,
    tmnxSyncIfTimingBITSNationalUse  Unsigned32,
    tmnxSyncIfTimingQLSelection      TmnxEnabledDisabled,
    tmnxSyncIfTimingOtherCPMInUse    TruthValue,
    tmnxSyncIfTimingOtherCPMQual     TmnxSETSRefQualified,
    tmnxSyncIfTimingOtherCPMAlarm    TmnxSETSRefAlarm,
    tmnxSyncIfTimingOtherCPMState    TmnxRefInState,
    tmnxSyncIfTimingBITSOutRefSel    TmnxSETSRefSource,
    tmnxSyncIfTimingBITSTxQltyLevel  TmnxSSMQualityLevel,
    tmnxSyncIfTimingBITS2AdminStatus TmnxPortAdminStatus,
    tmnxSyncIfTimingSystemQltyLevel  TmnxSSMQualityLevel,
    tmnxSyncIfTimingRefOrder4        TmnxSETSRefSource,
    tmnxSyncIfTimingPTPAdminStatus   TmnxPortAdminStatus,
    tmnxSyncIfTimingPTPInUse         TruthValue,
    tmnxSyncIfTimingPTPQualified     TmnxSETSRefQualified,
    tmnxSyncIfTimingPTPAlarm         TmnxSETSRefAlarm,
    tmnxSyncIfTimingPTPCfgQltyLevel  TmnxSSMQualityLevel,
    tmnxSyncIfTimingPTPRxQltyLevel   TmnxSSMQualityLevel,
    tmnxSyncIfTimingPTPState         TmnxRefInState,
    tmnxSyncIfTimingBITSOutSource    TmnxBITSOutSource,
    tmnxSyncIfTimingBITSOutQlMin     TmnxSSMQualityLevel,
    tmnxSyncIfTimingBITSOutSquelch   TruthValue,
    tmnxSyncIfTimingQlMin            TmnxSSMQualityLevel,
    tmnxSyncIfTimingWaitToRestorTime Unsigned32
}

tmnxSyncIfTimingRevert           OBJECT-TYPE
    SYNTAX      TruthValue
    MAX-ACCESS  read-only
    STATUS      current
    DESCRIPTION
        "The value of tmnxSyncIfTimingRevert indicates whether the reference
         source will revert to a higher priority source that has been
         re-validated or newly validated.

         The synchronous interface timing subsystem is by default non-revertive
         ('false')."
    ::= { tmnxSyncIfTimingEntry 1 }

tmnxSyncIfTimingRefOrder1        OBJECT-TYPE
    SYNTAX      TmnxSETSRefSource
    MAX-ACCESS  read-only
    STATUS      current
    DESCRIPTION
        "The value of tmnxSyncIfTimingRefOrder1 indicates the most preferred
         timing reference source.

         Four different timing input references may be specified in the
         reference order ('bits', 'reference1', 'reference2', and 'ptp').

         The synchronous equipment timing subsystem chooses a reference based
         on priority."
    ::= { tmnxSyncIfTimingEntry 2 }

tmnxSyncIfTimingRefOrder2        OBJECT-TYPE
    SYNTAX      TmnxSETSRefSource
    MAX-ACCESS  read-only
    STATUS      current
    DESCRIPTION
        "The value of tmnxSyncIfTimingRefOrder2 indicates the second most
         preferred timing reference for the synchronous equipment timing
         subsystem."
    ::= { tmnxSyncIfTimingEntry 3 }

tmnxSyncIfTimingRef1SrcPort      OBJECT-TYPE
    SYNTAX      TmnxPortID
    MAX-ACCESS  read-only
    STATUS      current
    DESCRIPTION
        "The value of tmnxSyncIfTimingRef1SrcPort indicates the source port of
         the first timing reference.

         A value of '1e000000'H indicates that there is no source port for this
         reference."
    ::= { tmnxSyncIfTimingEntry 4 }

tmnxSyncIfTimingRef1AdminStatus  OBJECT-TYPE
    SYNTAX      TmnxPortAdminStatus
    MAX-ACCESS  read-only
    STATUS      current
    DESCRIPTION
        "The value of tmnxSyncIfTimingRef1AdminStatus indicates the
         administrative status of the first timing reference."
    ::= { tmnxSyncIfTimingEntry 5 }

tmnxSyncIfTimingRef1InUse        OBJECT-TYPE
    SYNTAX      TruthValue
    MAX-ACCESS  read-only
    STATUS      current
    DESCRIPTION
        "The value of tmnxSyncIfTimingRef1InUse indicates whether the first
         timing reference is presently being used by the synchronous timing
         subsystem.  If it is in use, tmnxSyncIfTimingFreqOffset indicates
         the frequency offset for this reference."
    ::= { tmnxSyncIfTimingEntry 6 }

tmnxSyncIfTimingRef1Qualified    OBJECT-TYPE
    SYNTAX      TmnxSETSRefQualified
    MAX-ACCESS  read-only
    STATUS      current
    DESCRIPTION
        "The value of tmnxSyncIfTimingRef1Qualified indicates whether the first
         timing reference is qualified for use by the synchronous timing
         subsystem.  If tmnxSyncIfTimingRef1Qualified is set to 'not-qualified',
         then the object tmnxSyncIfTimingRef1Alarm gives the reason for
         disqualification."
    ::= { tmnxSyncIfTimingEntry 7 }

tmnxSyncIfTimingRef1Alarm        OBJECT-TYPE
    SYNTAX      TmnxSETSRefAlarm
    MAX-ACCESS  read-only
    STATUS      current
    DESCRIPTION
        "The value of tmnxSyncIfTimingRef1Alarm indicates the alarms on the
         first reference.  If any of the bits is set to '1', then the first
         reference is disqualified by the timing subsystem and the value of
         tmnxSyncIfTimingRef1Qualified is set to 'not-qualified'.
         los    - loss of signal
         oof    - out of frequency range
         oopir  - out of pull in range"
    ::= { tmnxSyncIfTimingEntry 8 }

tmnxSyncIfTimingRef2SrcPort      OBJECT-TYPE
    SYNTAX      TmnxPortID
    MAX-ACCESS  read-only
    STATUS      current
    DESCRIPTION
        "The value of tmnxSyncIfTimingRef2SrcPort indicates the source port of
         the second timing reference.

         A value of '1e000000'H indicates that there is no source port for this
         reference."
    ::= { tmnxSyncIfTimingEntry 9 }

tmnxSyncIfTimingRef2AdminStatus  OBJECT-TYPE
    SYNTAX      TmnxPortAdminStatus
    MAX-ACCESS  read-only
    STATUS      current
    DESCRIPTION
        "The value of tmnxSyncIfTimingRef2AdminStatus indicates the
         administrative status of the second timing reference."
    ::= { tmnxSyncIfTimingEntry 10 }

tmnxSyncIfTimingRef2InUse        OBJECT-TYPE
    SYNTAX      TruthValue
    MAX-ACCESS  read-only
    STATUS      current
    DESCRIPTION
        "The value of tmnxSyncIfTimingRef2InUse indicates whether the second
         timing reference is presently being used by the synchronous timing
         subsystem."
    ::= { tmnxSyncIfTimingEntry 11 }

tmnxSyncIfTimingRef2Qualified    OBJECT-TYPE
    SYNTAX      TmnxSETSRefQualified
    MAX-ACCESS  read-only
    STATUS      current
    DESCRIPTION
        "The value of tmnxSyncIfTimingRef2Qualified indicates whether the
         second timing reference is qualified for use by the synchronous
         timing subsystem.  If tmnxSyncIfTimingRef2Qualified is 'not-qualified'
         then the object tmnxSyncIfTimingRef2Alarm gives the reason for
         disqualification."
    ::= { tmnxSyncIfTimingEntry 12 }

tmnxSyncIfTimingRef2Alarm        OBJECT-TYPE
    SYNTAX      TmnxSETSRefAlarm
    MAX-ACCESS  read-only
    STATUS      current
    DESCRIPTION
        "The value of tmnxSyncIfTimingRef2Alarm indicates the alarms on the
         second reference.  If any of the bits is set to '1', then the second
         reference is disqualified by the timing subsystem and the value of
         tmnxSyncIfTimingRef2Qualified is set to 'not-qualified'.
         los    - loss of signal
         oof    - out of frequency range
         oopir  - out of pull in range"
    ::= { tmnxSyncIfTimingEntry 13 }

tmnxSyncIfTimingFreqOffset       OBJECT-TYPE
    SYNTAX      Integer32
    UNITS       "parts-per-million"
    MAX-ACCESS  read-only
    STATUS      current
    DESCRIPTION
        "The value of tmnxSyncIfTimingFreqOffset indicates the frequency offset
         of the current selected timing reference in parts per million (ppm)."
    ::= { tmnxSyncIfTimingEntry 14 }

tmnxSyncIfTimingStatus           OBJECT-TYPE
    SYNTAX      TmnxSETSStatus
    MAX-ACCESS  read-only
    STATUS      current
    DESCRIPTION
        "The value of tmnxSyncIfTimingStatus indicates the present status of
         the Synchronous Timing Equipment Source (SETS)."
    ::= { tmnxSyncIfTimingEntry 15 }

tmnxSyncIfTimingRefOrder3        OBJECT-TYPE
    SYNTAX      TmnxSETSRefSource
    MAX-ACCESS  read-only
    STATUS      current
    DESCRIPTION
        "The value of tmnxSyncIfTimingRefOrder3 is the third most preferred
         timing reference for the synchronous equipment timing subsystem."
    ::= { tmnxSyncIfTimingEntry 16 }

tmnxSyncIfTimingBITSIfType       OBJECT-TYPE
    SYNTAX      TmnxBITSIfType
    MAX-ACCESS  read-only
    STATUS      current
    DESCRIPTION
        "The value of tmnxSyncIfTimingBITSIfType indicates the interface type
         of the BITS (Building Integrated Timing Supply) timing reference. It
         also indicates the framing type of the interface."
    ::= { tmnxSyncIfTimingEntry 17 }

tmnxSyncIfTimingBITSAdminStatus  OBJECT-TYPE
    SYNTAX      TmnxPortAdminStatus
    MAX-ACCESS  read-only
    STATUS      current
    DESCRIPTION
        "The value of tmnxSyncIfTimingBITSAdminStatus indicates administrative
         status of the BITS (Building Integrated Timing Supply) input timing
         reference.

         The value of this object for the extension chassis in an XRS-40 system
         is always 'inService(2)'."
    ::= { tmnxSyncIfTimingEntry 18 }

tmnxSyncIfTimingBITSInUse        OBJECT-TYPE
    SYNTAX      TruthValue
    MAX-ACCESS  read-only
    STATUS      current
    DESCRIPTION
        "The value of tmnxSyncIfTimingBITSInUse indicates whether the BITS
         timing reference is presently being used by the synchronous timing
         subsystem.  If it is in use, tmnxSyncIfTimingFreqOffset indicates
         the frequency offset for this reference."
    ::= { tmnxSyncIfTimingEntry 19 }

tmnxSyncIfTimingBITSQualified    OBJECT-TYPE
    SYNTAX      TmnxSETSRefQualified
    MAX-ACCESS  read-only
    STATUS      current
    DESCRIPTION
        "The value of tmnxSyncIfTimingBITSQualified indicates whether the BITS
         timing reference is qualified for use by the synchronous timing
         subsystem.  If tmnxSyncIfTimingBITSQualified is 'not-qualified', then
         the object tmnxSyncIfTimingBITSAlarm gives the reason for
         disqualification."
    ::= { tmnxSyncIfTimingEntry 20 }

tmnxSyncIfTimingBITSAlarm        OBJECT-TYPE
    SYNTAX      TmnxSETSRefAlarm
    MAX-ACCESS  read-only
    STATUS      current
    DESCRIPTION
        "The value of tmnxSyncIfTimingBITSAlarm indicates the alarms on the
         BITS reference.  If any of the bits is set to '1', then the BITS
         reference is disqualified by the timing subsystem and the value of
         tmnxSyncIfTimingBITSQualified is set to 'not-qualified'."
    ::= { tmnxSyncIfTimingEntry 21 }

tmnxSyncIfTimingRef1SrcHw        OBJECT-TYPE
    SYNTAX      TmnxHwIndexOrZero
    MAX-ACCESS  read-only
    STATUS      current
    DESCRIPTION
        "The value of tmnxSyncIfTimingRef1SrcHw indicates the source HW index
         of the first timing reference if source is not a port."
    ::= { tmnxSyncIfTimingEntry 22 }

tmnxSyncIfTimingRef1BITSIfType   OBJECT-TYPE
    SYNTAX      TmnxBITSIfType
    MAX-ACCESS  read-only
    STATUS      current
    DESCRIPTION
        "The value of tmnxSyncIfTimingRef1BITSIfType indicates the interface
         type of the first timing reference if the source is BITS.  It also
         indicates the framing type of the interface."
    ::= { tmnxSyncIfTimingEntry 23 }

tmnxSyncIfTimingRef2SrcHw        OBJECT-TYPE
    SYNTAX      TmnxHwIndexOrZero
    MAX-ACCESS  read-only
    STATUS      current
    DESCRIPTION
        "The value of tmnxSyncIfTimingRef2SrcHw indicates the source HW index
         of the second timing reference if source is not a port."
    ::= { tmnxSyncIfTimingEntry 24 }

tmnxSyncIfTimingRef2BITSIfType   OBJECT-TYPE
    SYNTAX      TmnxBITSIfType
    MAX-ACCESS  read-only
    STATUS      current
    DESCRIPTION
        "The value of tmnxSyncIfTimingRef2BITSIfType indicates the interface
         type of the second timing reference if the source is BITS. It also
         indicates the framing type of the interface."
    ::= { tmnxSyncIfTimingEntry 25 }

tmnxSyncIfTimingBITSOutAdmStatus OBJECT-TYPE
    SYNTAX      TmnxPortAdminStatus
    MAX-ACCESS  read-only
    STATUS      current
    DESCRIPTION
        "The value of tmnxSyncIfTimingBITSOutAdmStatus indicates administrative
         status of the BITS (Building Integrated Timing Supply) output timing
         reference."
    ::= { tmnxSyncIfTimingEntry 26 }

tmnxSyncIfTimingBITSOutLineLen   OBJECT-TYPE
    SYNTAX      INTEGER {
        lengthNotApplicable (0),
        length0To110        (1),
        length110To220      (2),
        length220To330      (3),
        length330To440      (4),
        length440To550      (5),
        length550To660      (6)
    }
    MAX-ACCESS  read-only
    STATUS      current
    DESCRIPTION
        "tmnxSyncIfTimingBITSOutLineLen indicates the length of the line
         (in feet) for the BITS (Building Integrated Timing Supply) output.
         The following values are valid:
             lengthNotApplicable (0) - When BITS output is not supported
             length0To110        (1) - For line length from 0 to 110 feet
             length110To220      (2) - For line length from 110 to 220 feet
             length220To330      (3) - For line length from 230 to 330 feet
             length330To440      (4) - For line length from 330 to 440 feet
             length440To550      (5) - For line length from 440 to 550 feet
             length550To660      (6) - For line length from 550 to 660 feet
         The default is 'lengthNotApplicable' on CPM cards which do not
         support line length.  Otherwise, the default is 'length0To110'."
    ::= { tmnxSyncIfTimingEntry 27 }

tmnxSyncIfTimingRef1CfgQltyLevel OBJECT-TYPE
    SYNTAX      TmnxSSMQualityLevel
    MAX-ACCESS  read-only
    STATUS      current
    DESCRIPTION
        "The value of tmnxSyncIfTimingRef1CfgQltyLevel indicates the configured
         Quality Level of Reference 1. A value of 'unknown (0)' indicates
         Reference 1 is not forced to a specific quality level."
    ::= { tmnxSyncIfTimingEntry 28 }

tmnxSyncIfTimingRef1RxQltyLevel  OBJECT-TYPE
    SYNTAX      TmnxSSMQualityLevel
    MAX-ACCESS  read-only
    STATUS      current
    DESCRIPTION
        "The value of tmnxSyncIfTimingRef1RxQltyLevel indicates the received
         SSM Quality Level of Reference 1."
    ::= { tmnxSyncIfTimingEntry 29 }

tmnxSyncIfTimingRef2CfgQltyLevel OBJECT-TYPE
    SYNTAX      TmnxSSMQualityLevel
    MAX-ACCESS  read-only
    STATUS      current
    DESCRIPTION
        "The value of tmnxSyncIfTimingRef2CfgQltyLevel indicates the configured
         Quality Level of Reference 2. A value of 'unknown (0)' indicates
         Reference 2 is not forced to a specific quality level."
    ::= { tmnxSyncIfTimingEntry 30 }

tmnxSyncIfTimingRef2RxQltyLevel  OBJECT-TYPE
    SYNTAX      TmnxSSMQualityLevel
    MAX-ACCESS  read-only
    STATUS      current
    DESCRIPTION
        "The value of tmnxSyncIfTimingRef2RxQltyLevel indicates the received
         SSM Quality Level of Reference 2."
    ::= { tmnxSyncIfTimingEntry 31 }

tmnxSyncIfTimingBITSCfgQltyLevel OBJECT-TYPE
    SYNTAX      TmnxSSMQualityLevel
    MAX-ACCESS  read-only
    STATUS      current
    DESCRIPTION
        "The value of tmnxSyncIfTimingBITSCfgQltyLevel indicates the configured
         Quality Level of the BITS interface. A value of 'unknown (0)'
         indicates the BITS interface is not forced to a specific quality
         level."
    ::= { tmnxSyncIfTimingEntry 32 }

tmnxSyncIfTimingBITSRxQltyLevel  OBJECT-TYPE
    SYNTAX      TmnxSSMQualityLevel
    MAX-ACCESS  read-only
    STATUS      current
    DESCRIPTION
        "The value of tmnxSyncIfTimingBITSRxQltyLevel indicates the received
         SSM Quality Level of the BITS interface."
    ::= { tmnxSyncIfTimingEntry 33 }

tmnxSyncIfTimingBITS2InUse       OBJECT-TYPE
    SYNTAX      TruthValue
    MAX-ACCESS  read-only
    STATUS      current
    DESCRIPTION
        "The value of tmnxSyncIfTimingBITS2InUse indicates whether the BITS2
         timing reference is presently being used by the synchronous timing
         subsystem.  If it is in use, tmnxSyncIfTimingFreqOffset indicates
         the frequency offset for this reference."
    ::= { tmnxSyncIfTimingEntry 34 }

tmnxSyncIfTimingBITS2Qualified   OBJECT-TYPE
    SYNTAX      TmnxSETSRefQualified
    MAX-ACCESS  read-only
    STATUS      current
    DESCRIPTION
        "The value of tmnxSyncIfTimingBITS2Qualified indicates whether the BITS2
         timing reference is qualified for use by the synchronous timing
         subsystem.  If tmnxSyncIfTimingBITS2Qualified is 'not-qualified', then
         the object tmnxSyncIfTimingBITS2Alarm gives the reason for
         disqualification."
    ::= { tmnxSyncIfTimingEntry 35 }

tmnxSyncIfTimingBITS2Alarm       OBJECT-TYPE
    SYNTAX      TmnxSETSRefAlarm
    MAX-ACCESS  read-only
    STATUS      current
    DESCRIPTION
        "The value of tmnxSyncIfTimingBITS2Alarm indicates the alarms on the
         BITS2 reference.  If any of the bits is set to '1', then the BITS2
         reference is disqualified by the timing subsystem and the value of
         tmnxSyncIfTimingBITSQualified is set to 'not-qualified'."
    ::= { tmnxSyncIfTimingEntry 36 }

tmnxSyncIfTimingBITS2RxQltyLevel OBJECT-TYPE
    SYNTAX      TmnxSSMQualityLevel
    MAX-ACCESS  read-only
    STATUS      current
    DESCRIPTION
        "The value of tmnxSyncIfTimingBITS2RxQltyLevel indicates the received
         SSM Rx Quality Level of the BITS2 interface."
    ::= { tmnxSyncIfTimingEntry 37 }

tmnxSyncIfTimingRef1State        OBJECT-TYPE
    SYNTAX      TmnxRefInState
    MAX-ACCESS  read-only
    STATUS      current
    DESCRIPTION
        "The value of tmnxSyncIfTimingRef1State indicates the operational state
         of the Reference 1 Timing."
    ::= { tmnxSyncIfTimingEntry 38 }

tmnxSyncIfTimingRef2State        OBJECT-TYPE
    SYNTAX      TmnxRefInState
    MAX-ACCESS  read-only
    STATUS      current
    DESCRIPTION
        "The value of tmnxSyncIfTimingRef2State indicates the operational state
         of the Reference 2 Timing."
    ::= { tmnxSyncIfTimingEntry 39 }

tmnxSyncIfTimingBITSState        OBJECT-TYPE
    SYNTAX      TmnxRefInState
    MAX-ACCESS  read-only
    STATUS      current
    DESCRIPTION
        "The value of tmnxSyncIfTimingBITSState indicates the operational state
         of the BITS Timing Interface."
    ::= { tmnxSyncIfTimingEntry 40 }

tmnxSyncIfTimingBITS2State       OBJECT-TYPE
    SYNTAX      TmnxRefInState
    MAX-ACCESS  read-only
    STATUS      current
    DESCRIPTION
        "The value of tmnxSyncIfTimingBITS2State indicates the operational
         state of the BITS2 Timing Interface."
    ::= { tmnxSyncIfTimingEntry 41 }

tmnxSyncIfTimingRef1NationalUse  OBJECT-TYPE
    SYNTAX      Unsigned32 (4..8)
    MAX-ACCESS  read-only
    STATUS      current
    DESCRIPTION
        "The value of tmnxSyncIfTimingRef1NationalUse indicates the national
         use bit to carry SSM Messages. This applies only to E1 BITS
         interfaces."
    DEFVAL      { 8 }
    ::= { tmnxSyncIfTimingEntry 42 }

tmnxSyncIfTimingRef2NationalUse  OBJECT-TYPE
    SYNTAX      Unsigned32 (4..8)
    MAX-ACCESS  read-only
    STATUS      current
    DESCRIPTION
        "The value of tmnxSyncIfTimingRef2NationalUse indicates the national
         use bit to carry SSM Messages. This applies only to E1 BITS
         interfaces."
    DEFVAL      { 8 }
    ::= { tmnxSyncIfTimingEntry 43 }

tmnxSyncIfTimingBITSNationalUse  OBJECT-TYPE
    SYNTAX      Unsigned32 (4..8)
    MAX-ACCESS  read-only
    STATUS      current
    DESCRIPTION
        "The value of tmnxSyncIfTimingBITSNationalUse indicates the national
         use bit to carry SSM Messages. This applies only to E1 BITS
         interfaces."
    DEFVAL      { 8 }
    ::= { tmnxSyncIfTimingEntry 44 }

tmnxSyncIfTimingQLSelection      OBJECT-TYPE
    SYNTAX      TmnxEnabledDisabled
    MAX-ACCESS  read-only
    STATUS      current
    DESCRIPTION
        "The value of tmnxSyncIfTimingQLSelection indicates whether or not the
         timing reference selection process uses the quality level of each
         timing reference when making the decision on which reference should
         provide system timing."
    REFERENCE
        "ITU-T Recommendation G.781, June 1999, Section 5.12"
    ::= { tmnxSyncIfTimingEntry 45 }

tmnxSyncIfTimingOtherCPMInUse    OBJECT-TYPE
    SYNTAX      TruthValue
    MAX-ACCESS  read-only
    STATUS      current
    DESCRIPTION
        "The value of tmnxSyncIfTimingOtherCPMInUse indicates whether the
         timing reference from the other CPM is presently being used by the
         synchronous timing subsystem on the this CPM."
    DEFVAL      { false }
    ::= { tmnxSyncIfTimingEntry 46 }

tmnxSyncIfTimingOtherCPMQual     OBJECT-TYPE
    SYNTAX      TmnxSETSRefQualified
    MAX-ACCESS  read-only
    STATUS      current
    DESCRIPTION
        "The value of tmnxSyncIfTimingOtherCPMQual indicates whether the
         timing reference from the other CPM is qualified for use by the
         synchronous timing subsystem on the local CPM.  If
         tmnxSyncIfTimingOtherCPMQual is 'not-qualified', then the object
         tmnxSyncIfTimingOtherCPMAlarm gives the reason for disqualification."
    DEFVAL      { not-qualified }
    ::= { tmnxSyncIfTimingEntry 47 }

tmnxSyncIfTimingOtherCPMAlarm    OBJECT-TYPE
    SYNTAX      TmnxSETSRefAlarm
    MAX-ACCESS  read-only
    STATUS      current
    DESCRIPTION
        "The value of tmnxSyncIfTimingOtherCPMAlarm indicates the alarms on the
         timing reference from the other CPM.  If any of the bits is set to
         '1', then the reference is disqualified by the timing subsystem and the
         value of tmnxSyncIfTimingOtherCPMQual is set to 'not-qualified'."
    DEFVAL      { {} }
    ::= { tmnxSyncIfTimingEntry 48 }

tmnxSyncIfTimingOtherCPMState    OBJECT-TYPE
    SYNTAX      TmnxRefInState
    MAX-ACCESS  read-only
    STATUS      current
    DESCRIPTION
        "The value of tmnxSyncIfTimingOtherCPMState indicates the operational
         state of the timing reference from the other CPM on the local CPM."
    DEFVAL      { disabled }
    ::= { tmnxSyncIfTimingEntry 49 }

tmnxSyncIfTimingBITSOutRefSel    OBJECT-TYPE
    SYNTAX      TmnxSETSRefSource
    MAX-ACCESS  read-only
    STATUS      current
    DESCRIPTION
        "The value of tmnxSyncIfTimingBITSOutRefSel indicates the reference
         source for BITS output."
    DEFVAL      { noReference }
    ::= { tmnxSyncIfTimingEntry 50 }

tmnxSyncIfTimingBITSTxQltyLevel  OBJECT-TYPE
    SYNTAX      TmnxSSMQualityLevel
    MAX-ACCESS  read-only
    STATUS      current
    DESCRIPTION
        "The value of tmnxSyncIfTimingBITSTxQltyLevel indicates the transmitted
         SSM Tx Quality Level of the BITS interface."
    ::= { tmnxSyncIfTimingEntry 51 }

tmnxSyncIfTimingBITS2AdminStatus OBJECT-TYPE
    SYNTAX      TmnxPortAdminStatus
    MAX-ACCESS  read-only
    STATUS      current
    DESCRIPTION
        "The value of tmnxSyncIfTimingBITS2AdminStatus indicates administrative
         status of the BITS2 (Building Integrated Timing Supply) input timing
         reference."
    ::= { tmnxSyncIfTimingEntry 52 }

tmnxSyncIfTimingSystemQltyLevel  OBJECT-TYPE
    SYNTAX      TmnxSSMQualityLevel
    MAX-ACCESS  read-only
    STATUS      current
    DESCRIPTION
        "The value of tmnxSyncIfTimingSystemQltyLevel indicates the quality
         level of the system timing reference.  This is normally the quality
         level of the selected timing reference.  If no timing reference has
         been selected, it indicates the freerun/holdover quality of the
         system."
    ::= { tmnxSyncIfTimingEntry 53 }

tmnxSyncIfTimingRefOrder4        OBJECT-TYPE
    SYNTAX      TmnxSETSRefSource
    MAX-ACCESS  read-only
    STATUS      current
    DESCRIPTION
        "The value of tmnxSyncIfTimingRefOrder4 is the fourth most preferred
         timing reference for the synchronous equipment timing subsystem."
    ::= { tmnxSyncIfTimingEntry 54 }

tmnxSyncIfTimingPTPAdminStatus   OBJECT-TYPE
    SYNTAX      TmnxPortAdminStatus
    MAX-ACCESS  read-only
    STATUS      current
    DESCRIPTION
        "The value of tmnxSyncIfTimingPTPAdminStatus indicates the
         administrative status of the Precision Timing Protocol (PTP) timing
         reference."
    ::= { tmnxSyncIfTimingEntry 55 }

tmnxSyncIfTimingPTPInUse         OBJECT-TYPE
    SYNTAX      TruthValue
    MAX-ACCESS  read-only
    STATUS      current
    DESCRIPTION
        "The value of tmnxSyncIfTimingPTPInUse indicates whether the Precision
         Timing Protocol (PTP) timing reference is presently being used by the
         synchronous timing subsystem.  If it is in use,
         tmnxSyncIfTimingFreqOffset indicates the frequency offset for this
         reference."
    ::= { tmnxSyncIfTimingEntry 56 }

tmnxSyncIfTimingPTPQualified     OBJECT-TYPE
    SYNTAX      TmnxSETSRefQualified
    MAX-ACCESS  read-only
    STATUS      current
    DESCRIPTION
        "The value of tmnxSyncIfTimingPTPQualified indicates whether the
         Precision Timing Protocol (PTP) timing reference is qualified for use
         by the synchronous timing subsystem.  If tmnxSyncIfTimingPTPQualified
         is set to 'not-qualified', then the object tmnxSyncIfTimingPTPAlarm
         gives the reason for the disqualification."
    ::= { tmnxSyncIfTimingEntry 57 }

tmnxSyncIfTimingPTPAlarm         OBJECT-TYPE
    SYNTAX      TmnxSETSRefAlarm
    MAX-ACCESS  read-only
    STATUS      current
    DESCRIPTION
        "The value of tmnxSyncIfTimingPTPAlarm indicates the alarms on the
         Precision Timing Protocol (PTP) reference.  If any of the bits is set
         to '1', then the PTP reference is disqualified by the timing subsystem
         and the value of tmnxSyncIfTimingPTPQualified is set to
         'not-qualified'.
         los     - loss of signal
         oof     - out of frequency range
         oopir   - out of pull in range"
    ::= { tmnxSyncIfTimingEntry 58 }

tmnxSyncIfTimingPTPCfgQltyLevel  OBJECT-TYPE
    SYNTAX      TmnxSSMQualityLevel
    MAX-ACCESS  read-only
    STATUS      current
    DESCRIPTION
        "The value of tmnxSyncIfTimingPTPCfgQltyLevel indicates the configured
         Quality Level of Precision Timing Protocol (PTP).  A value of
         'unknown (0)' indicates PTP is not forced to a specific quality level."
    ::= { tmnxSyncIfTimingEntry 59 }

tmnxSyncIfTimingPTPRxQltyLevel   OBJECT-TYPE
    SYNTAX      TmnxSSMQualityLevel
    MAX-ACCESS  read-only
    STATUS      current
    DESCRIPTION
        "The value of tmnxSyncIfTimingPTPRxQltyLevel indicates the received SSM
         RX Quality Level of the Precision Timing Protocol (PTP)."
    ::= { tmnxSyncIfTimingEntry 60 }

tmnxSyncIfTimingPTPState         OBJECT-TYPE
    SYNTAX      TmnxRefInState
    MAX-ACCESS  read-only
    STATUS      current
    DESCRIPTION
        "The value of tmnxSyncIfTimingPTPState indicates the operational state
         of the Precision Timing Protocol (PTP) Timing."
    ::= { tmnxSyncIfTimingEntry 61 }

tmnxSyncIfTimingBITSOutSource    OBJECT-TYPE
    SYNTAX      TmnxBITSOutSource
    MAX-ACCESS  read-only
    STATUS      current
    DESCRIPTION
        "The value of tmnxSyncIfTimingBITSOutSource indicates the source of the
         BITS (Building Integrated Timing Supply) output."
    ::= { tmnxSyncIfTimingEntry 62 }

tmnxSyncIfTimingBITSOutQlMin     OBJECT-TYPE
    SYNTAX      TmnxSSMQualityLevel
    MAX-ACCESS  read-only
    STATUS      current
    DESCRIPTION
        "The value of tmnxSyncIfTimingBITSOutQlMin indicates the minimum
         quality level that a signal must have for it to be selected for BITS
         output.

         A value of 'unknown (0)' indicates that there is no minimum quality
         level selected for the BITS output."
    ::= { tmnxSyncIfTimingEntry 63 }

tmnxSyncIfTimingBITSOutSquelch   OBJECT-TYPE
    SYNTAX      TruthValue
    MAX-ACCESS  read-only
    STATUS      current
    DESCRIPTION
        "The value of tmnxSyncIfTimingBITSOutSquelch indicates whether or not
         to squelch the output signal. This object is only valid when there is
         no valid reference selected.

         If the value is 'true (1)' and there is no valid reference, then no
         signal is sent out the port.

         If the value is 'false (2)' and there is no valid reference, then the
         AIS signal is presented along with the QL-DNU/QL-DUS SSM if the signal
         format supports SSM."
    ::= { tmnxSyncIfTimingEntry 64 }

tmnxSyncIfTimingQlMin            OBJECT-TYPE
    SYNTAX      TmnxSSMQualityLevel
    MAX-ACCESS  read-only
    STATUS      current
    DESCRIPTION
        "The value of tmnxSyncIfTimingQlMin indicates the minimum acceptable
         quality level that a signal must have for it to be considered for
         selection by the system timing module.

         A value of 'unknown (0)' indicates that there is no minimum quality
         level."
    ::= { tmnxSyncIfTimingEntry 66 }

tmnxSyncIfTimingWaitToRestorTime OBJECT-TYPE
    SYNTAX      Unsigned32 (0..12)
    UNITS       "minutes"
    MAX-ACCESS  read-only
    STATUS      current
    DESCRIPTION
        "The value of tmnxSyncIfTimingWaitToRestorTime indicates the time, in
         minutes, that a previously failed input reference must be valid before
         it will be used for either the BITS output or the central clock input
         reference.

         A value of '0' indicates that the wait-to-restore timer is disabled."
    ::= { tmnxSyncIfTimingEntry 67 }

tmnxCcagTable                    OBJECT-TYPE
    SYNTAX      SEQUENCE OF TmnxCcagEntry
    MAX-ACCESS  not-accessible
    STATUS      current
    DESCRIPTION
        "The tmnxCcagTable has an entry for each Cross Connect Aggregation
         Group,CCAG, configured on this system."
    ::= { tmnxCardObjs 12 }

tmnxCcagEntry                    OBJECT-TYPE
    SYNTAX      TmnxCcagEntry
    MAX-ACCESS  not-accessible
    STATUS      current
    DESCRIPTION
        "Each row entry represents a particular CCAG. Entries are
         created/deleted by the user. There is no StorageType object, entries
         have a presumed StorageType of nonVolatile."
    INDEX       { tmnxCcagId }
    ::= { tmnxCcagTable 1 }

TmnxCcagEntry                    ::= SEQUENCE
{
    tmnxCcagId                       TmnxCcagId,
    tmnxCcagRowStatus                RowStatus,
    tmnxCcagLastChanged              TimeStamp,
    tmnxCcagDescription              DisplayString,
    tmnxCcagAdminStatus              TmnxAdminState,
    tmnxCcagOperStatus               TmnxOperState,
    tmnxCcagCcaRate                  TmnxCcagRate,
    tmnxCcagAccessAdaptQos           INTEGER
}

tmnxCcagId                       OBJECT-TYPE
    SYNTAX      TmnxCcagId
    MAX-ACCESS  not-accessible
    STATUS      current
    DESCRIPTION
        "The value of tmnxCcagId is used to index into the tmnxCcagTable. It
         uniquely identifies a CCAG entry as configured on this system."
    ::= { tmnxCcagEntry 1 }

tmnxCcagRowStatus                OBJECT-TYPE
    SYNTAX      RowStatus
    MAX-ACCESS  read-create
    STATUS      current
    DESCRIPTION
        "The value of tmnxCcagRowStatus specifies the row status. It allows
         entries to be created and deleted in the tmnxCcagTable.
         tmnxCcagRowStatus does not support createAndWait. The status can only
         be active or notInService."
    ::= { tmnxCcagEntry 2 }

tmnxCcagLastChanged              OBJECT-TYPE
    SYNTAX      TimeStamp
    MAX-ACCESS  read-only
    STATUS      current
    DESCRIPTION
        "The value of tmnxCcagLastChanged indicates the time this row was last
         changed."
    ::= { tmnxCcagEntry 3 }

tmnxCcagDescription              OBJECT-TYPE
    SYNTAX      DisplayString
    MAX-ACCESS  read-create
    STATUS      current
    DESCRIPTION
        "The value of tmnxCcagDescription specifies a user provided description
         string of this CCAG entry."
    DEFVAL      { "" }
    ::= { tmnxCcagEntry 4 }

tmnxCcagAdminStatus              OBJECT-TYPE
    SYNTAX      TmnxAdminState
    MAX-ACCESS  read-create
    STATUS      current
    DESCRIPTION
        "The value of tmnxCcagAdminStatus specifies the desired state of this
         CCAG."
    DEFVAL      { inService }
    ::= { tmnxCcagEntry 5 }

tmnxCcagOperStatus               OBJECT-TYPE
    SYNTAX      TmnxOperState
    MAX-ACCESS  read-only
    STATUS      current
    DESCRIPTION
        "The value of tmnxCcagOperStatus indicates the operational state of
         this CCAG."
    ::= { tmnxCcagEntry 6 }

tmnxCcagCcaRate                  OBJECT-TYPE
    SYNTAX      TmnxCcagRate
    UNITS       "kilobits per second"
    MAX-ACCESS  read-create
    STATUS      current
    DESCRIPTION
        "The value of tmnxCcagCcaRate specifies the maximum forwarding rate for
         each CCA member within the CCAG."
    DEFVAL      { -1 }
    ::= { tmnxCcagEntry 7 }

tmnxCcagAccessAdaptQos           OBJECT-TYPE
    SYNTAX      INTEGER {
        link       (1),
        distribute (2),
        portFair   (3)
    }
    MAX-ACCESS  read-create
    STATUS      current
    DESCRIPTION
        "The value of tmnxCcagAccessAdaptQos specifies how the CCAG SAP queue
         and virtual scheduler buffering and rate parameters are adapted over
         multiple active CCAs.
         link           (1) - The CCAG will create the SAP queues and virtual
                              schedulers on each CCA with the actual parameters
                              specified in the tmnxCcagPathCcTable.
         distribute     (2) - Each CCA will receive a portion of the parameters
                              specified in the tmnxCcagPathCcTable.
         portFair       (3) - The LAG will create the SAP queues and virtual
                              schedulers with actual configuration parameters
                              on each port members in the LAG. The bandwidth is
                              distributed among the ports based on each port's
                              bandwidth relative to the total active bandwidth."
    DEFVAL      { distribute }
    ::= { tmnxCcagEntry 8 }

tmnxCcagPathTable                OBJECT-TYPE
    SYNTAX      SEQUENCE OF TmnxCcagPathEntry
    MAX-ACCESS  not-accessible
    STATUS      current
    DESCRIPTION
        "The tmnxCcagPathTable has an entry for each Cross Connect Aggregation
         Group, CCAG, path configured on this system."
    ::= { tmnxCardObjs 13 }

tmnxCcagPathEntry                OBJECT-TYPE
    SYNTAX      TmnxCcagPathEntry
    MAX-ACCESS  not-accessible
    STATUS      current
    DESCRIPTION
        "Each row entry represents a particular CCAG Path. Entries are
         created/deleted by the user. There is no StorageType object, entries
         have a presumed StorageType of nonVolatile."
    INDEX       {
        tmnxCcagId,
        tmnxCcagPathId
    }
    ::= { tmnxCcagPathTable 1 }

TmnxCcagPathEntry                ::= SEQUENCE
{
    tmnxCcagPathId                   INTEGER,
    tmnxCcagPathLastChanged          TimeStamp,
    tmnxCcagPathRate                 TmnxCcagRate,
    tmnxCcagPathRateOption           TmnxCcagRateOption,
    tmnxCcagPathWeight               Unsigned32
}

tmnxCcagPathId                   OBJECT-TYPE
    SYNTAX      INTEGER {
        alpha (1),
        beta  (2)
    }
    MAX-ACCESS  not-accessible
    STATUS      current
    DESCRIPTION
        "The value of tmnxCcagPathId is used as the secondary index into the
         tmnxCcagPathTable. Along with tmnxCcagId, it uniquely identifies a
         specific path, alpha or beta, on a CCAG."
    ::= { tmnxCcagPathEntry 1 }

tmnxCcagPathLastChanged          OBJECT-TYPE
    SYNTAX      TimeStamp
    MAX-ACCESS  read-only
    STATUS      current
    DESCRIPTION
        "The value of tmnxCcagPathLastChanged indicates the time this row was
         last changed."
    ::= { tmnxCcagPathEntry 2 }

tmnxCcagPathRate                 OBJECT-TYPE
    SYNTAX      TmnxCcagRate
    UNITS       "kilobits per second"
    MAX-ACCESS  read-create
    STATUS      current
    DESCRIPTION
        "The value of tmnxCcagPathRate specifies the bandwidth rate limitation
         for this path on each member cross connect adaptor, CCA, in the CCAG."
    DEFVAL      { -1 }
    ::= { tmnxCcagPathEntry 3 }

tmnxCcagPathRateOption           OBJECT-TYPE
    SYNTAX      TmnxCcagRateOption
    MAX-ACCESS  read-create
    STATUS      current
    DESCRIPTION
        "The value of tmnxCcagPathRateOption specifies whether the rate in
         tmnxCcagPathRate is defined as an aggregate path rate for all CCAs in
         the CCAG or as a per CCA path rate."
    DEFVAL      { aggregate }
    ::= { tmnxCcagPathEntry 4 }

tmnxCcagPathWeight               OBJECT-TYPE
    SYNTAX      Unsigned32 (1..100)
    MAX-ACCESS  read-create
    STATUS      current
    DESCRIPTION
        "The value of tmnxCcagPathWeight specifies the scheduling percentage
         for this path. It is applied to all CCAs in the CCAG membership list
         for this path."
    DEFVAL      { 50 }
    ::= { tmnxCcagPathEntry 5 }

tmnxCcagPathCcTable              OBJECT-TYPE
    SYNTAX      SEQUENCE OF TmnxCcagPathCcEntry
    MAX-ACCESS  not-accessible
    STATUS      current
    DESCRIPTION
        "The tmnxCcagPathCcTable has an entry for each type of Cross Connection
         on a Cross Connect Aggregation Group Path configured on this system."
    ::= { tmnxCardObjs 14 }

tmnxCcagPathCcEntry              OBJECT-TYPE
    SYNTAX      TmnxCcagPathCcEntry
    MAX-ACCESS  not-accessible
    STATUS      current
    DESCRIPTION
        "Each row entry represents a particular CCAG Path Cross Connect.
         Entries are created/deleted by the user. There is no StorageType
         object, entries have a presumed StorageType of nonVolatile."
    INDEX       {
        tmnxCcagId,
        tmnxCcagPathId,
        tmnxCcagPathCcType
    }
    ::= { tmnxCcagPathCcTable 1 }

TmnxCcagPathCcEntry              ::= SEQUENCE
{
    tmnxCcagPathCcType               INTEGER,
    tmnxCcagPathCcLastChanged        TimeStamp,
    tmnxCcagPathCcEgrPoolResvCbs     Integer32,
    tmnxCcagPathCcEgrPoolSlpPlcy     TNamedItem,
    tmnxCcagPathCcIngPoolResvCbs     Integer32,
    tmnxCcagPathCcIngPoolSlpPlcy     TNamedItem,
    tmnxCcagPathCcAcctPolicyId       Unsigned32,
    tmnxCcagPathCcCollectStats       TruthValue,
    tmnxCcagPathCcQueuePlcy          TNamedItem,
    tmnxCcagPathCcMac                MacAddress,
    tmnxCcagPathCcMtu                Unsigned32,
    tmnxCcagPathCcUserAssignedMac    TruthValue,
    tmnxCcagPathCcHwMac              MacAddress
}

tmnxCcagPathCcType               OBJECT-TYPE
    SYNTAX      INTEGER {
        sapsap (1),
        sapnet (2),
        netsap (3)
    }
    MAX-ACCESS  not-accessible
    STATUS      current
    DESCRIPTION
        "The value of tmnxCcagPathCcType is used as a third index into
         the tmnxCcagPathCcTable. Along with tmnxCcagId and tmnxCcagPathId,
         it uniquely identifies a cross connection type on a specific path
         in a particular CCAG. The types are:
         sapsap (1): the cross connection is between two saps, where both
                     services are access.
         sapnet (2): the cross connection is between a sap and a network
                     service.
         netsap (3): the cross connection is between a network and a sap
                     service."
    ::= { tmnxCcagPathCcEntry 1 }

tmnxCcagPathCcLastChanged        OBJECT-TYPE
    SYNTAX      TimeStamp
    MAX-ACCESS  read-only
    STATUS      current
    DESCRIPTION
        "The value of tmnxCcagPathCcLastChanged indicates the time this row was
         last changed."
    ::= { tmnxCcagPathCcEntry 2 }

tmnxCcagPathCcEgrPoolResvCbs     OBJECT-TYPE
    SYNTAX      Integer32 (-1..100)
    MAX-ACCESS  read-create
    STATUS      current
    DESCRIPTION
        "The value of tmnxCcagPathCcEgrPoolResvCbs specifies the percentage of
         pool size reserved for the committed burst size, CBS. The value '-1'
         implies that the reserved CBS should be computed as the sum of the CBS
         requested by the entities using this pool if the application point is
         'network'. For 'access' application points the value '-1' means a
         default of 30%."
    DEFVAL      { -1 }
    ::= { tmnxCcagPathCcEntry 3 }

tmnxCcagPathCcEgrPoolSlpPlcy     OBJECT-TYPE
    SYNTAX      TNamedItem
    MAX-ACCESS  read-create
    STATUS      current
    DESCRIPTION
        "The value of tmnxCcagPathCcEgrPoolSlpPlcy specifies the slope policy
         being used for the egress pool. The Slope policies define the nature
         of the RED Slopes for the high and the low priority traffic."
    DEFVAL      { "default" }
    ::= { tmnxCcagPathCcEntry 4 }

tmnxCcagPathCcIngPoolResvCbs     OBJECT-TYPE
    SYNTAX      Integer32 (-1..100)
    MAX-ACCESS  read-create
    STATUS      current
    DESCRIPTION
        "The value of tmnxCcagPathCcIngPoolResvCbs specifies the percentage of
         pool size reserved for the committed burst size, CBS. The value '-1'
         implies that the reserved CBS should be computed as the sum of the CBS
         requested by the entities using this pool if the application point is
         'network'. For 'access' application points the value '-1' means a
         default of 30%. tmnxCcagPathCcIngPoolResvCbs does not apply to
         tmnxCcagPathCcType 'netsap'."
    DEFVAL      { -1 }
    ::= { tmnxCcagPathCcEntry 5 }

tmnxCcagPathCcIngPoolSlpPlcy     OBJECT-TYPE
    SYNTAX      TNamedItem
    MAX-ACCESS  read-create
    STATUS      current
    DESCRIPTION
        "The value of tmnxCcagPathCcIngPoolSlpPlcy specifies the slope policy
         being used for the ingress pool. The Slope policies define the nature
         of the RED Slopes for the high and the low priority traffic.
         tmnxCcagPathCcIngPoolSlpPlcy does not apply to tmnxCcagPathCcType
         'netsap'."
    DEFVAL      { "default" }
    ::= { tmnxCcagPathCcEntry 6 }

tmnxCcagPathCcAcctPolicyId       OBJECT-TYPE
    SYNTAX      Unsigned32 (0..99)
    MAX-ACCESS  read-create
    STATUS      current
    DESCRIPTION
        "The value of tmnxCcagPathCcAcctPolicyId specifies the accounting
         policy which must be defined prior to associating it with the port.
         A non-zero value indicates the tmnxLogApPolicyId index identifying the
         policy entry in the tmnxLogApTable from the TIMETRA-LOG-MIB which is
         associated with this port.  A zero value indicates that there is no
         accounting policy associated with this port. It is only meaningful
         when the tmnxCcagPathCcType is 'netsap'."
    DEFVAL      { 0 }
    ::= { tmnxCcagPathCcEntry 7 }

tmnxCcagPathCcCollectStats       OBJECT-TYPE
    SYNTAX      TruthValue
    MAX-ACCESS  read-create
    STATUS      current
    DESCRIPTION
        "The value of tmnxCcagPathCcCollectStats specifies whether the
         collection of accounting and statistical data for the network port is
         enabled/disabled, 'true'/'false'. When applying accounting policies
         the data by default will be collected in the appropriate records and
         written to the designated billing file. When the value is set to
         false, the statistics are still accumulated by the IOM cards, however,
         the CPU will not obtain the results and write them to the billing
         file. If the value of tmnxCcagPathCcType is not 'netsap', the value of
         this object is meaningless and an attempt to set it will result in an
         inconsistentValue error."
    DEFVAL      { false }
    ::= { tmnxCcagPathCcEntry 8 }

tmnxCcagPathCcQueuePlcy          OBJECT-TYPE
    SYNTAX      TNamedItem
    MAX-ACCESS  read-create
    STATUS      current
    DESCRIPTION
        "The value of tmnxCcagPathCcQueuePlcy specifies the network egress
         queue policy. If the value of tmnxCcagPathCcType is not 'netsap', the
         value of this object is meaningless and an attempt to set it will
         result in an inconsistentValue error."
    DEFVAL      { "default" }
    ::= { tmnxCcagPathCcEntry 9 }

tmnxCcagPathCcMac                OBJECT-TYPE
    SYNTAX      MacAddress
    MAX-ACCESS  read-create
    STATUS      current
    DESCRIPTION
        "The value of tmnxCcagPathCcMac specifies the MAC address of the
         virtual LAG that maps to tmnxCcagPathId and tmnxCcagPathCcType. The
         default value of this object is derived from the chassis MAC address
         pool."
    DEFVAL      { '000000000000'H }
    ::= { tmnxCcagPathCcEntry 10 }

tmnxCcagPathCcMtu                OBJECT-TYPE
    SYNTAX      Unsigned32
    MAX-ACCESS  read-create
    STATUS      current
    DESCRIPTION
        "The value of tmnxCcagPathCcMtu specifies the MTU of the path indexed
         by tmnxCcagId, tmnxCcagPathId, and tmnxCcagPathCcType. When the value
         is '0', the real MTU is calculated internally."
    DEFVAL      { 0 }
    ::= { tmnxCcagPathCcEntry 11 }

tmnxCcagPathCcUserAssignedMac    OBJECT-TYPE
    SYNTAX      TruthValue
    MAX-ACCESS  read-only
    STATUS      current
    DESCRIPTION
        "The value of tmnxCcagPathCcUserAssignedMac indicates whether the value
         of tmnxCcagPathCcMac has been explicitly assigned or inherited from
         tmnxCcagPathCcHwMac, 'true' and 'false', respectively."
    DEFVAL      { false }
    ::= { tmnxCcagPathCcEntry 12 }

tmnxCcagPathCcHwMac              OBJECT-TYPE
    SYNTAX      MacAddress
    MAX-ACCESS  read-only
    STATUS      current
    DESCRIPTION
        "The value of tmnxCcagPathCcHwMac is the system assigned MAC address of
         the virtual LAG that maps to tmnxCcagPathId and tmnxCcagPathCcType.
         When tmnxCcagPathCcUserAssignedMac is 'false', tmnxCcagPathCcMac
         inherits its value from this object."
    ::= { tmnxCcagPathCcEntry 13 }

tmnxMcmTable                     OBJECT-TYPE
    SYNTAX      SEQUENCE OF TmnxMcmEntry
    MAX-ACCESS  not-accessible
    STATUS      current
    DESCRIPTION
        "The tmnxMcmTable has an entry for each Mda Carrier module (MCM) on the
         7710 system."
    ::= { tmnxCardObjs 15 }

tmnxMcmEntry                     OBJECT-TYPE
    SYNTAX      TmnxMcmEntry
    MAX-ACCESS  not-accessible
    STATUS      current
    DESCRIPTION
        "Each row entry represents a MCM in a chassis in the 7710 system.
         Entries in the table cannot be created and deleted via SNMP SET
         operations.  When a tmnxChassisEntry is created, a
         tmnxMcmEntry is created in the chassis.  Before a
         tmnxChassisEntry can be deleted, each tmnxMcmEntry
         for the chassis must be in the proper state for removal."
    INDEX       {
        tmnxChassisIndex,
        tmnxCardSlotNum,
        tmnxMcmSlotNum
    }
    ::= { tmnxMcmTable 1 }

TmnxMcmEntry                     ::= SEQUENCE
{
    tmnxMcmSlotNum                   Unsigned32,
    tmnxMcmSupportedTypes            TmnxMcmType,
    tmnxMcmAssignedType              TmnxMcmType,
    tmnxMcmEquippedType              TmnxMcmType,
    tmnxMcmHwIndex                   TmnxHwIndex
}

tmnxMcmSlotNum                   OBJECT-TYPE
    SYNTAX      Unsigned32 (0..16)
    MAX-ACCESS  not-accessible
    STATUS      current
    DESCRIPTION
        "The unique value which identifies this MDA slot within a specific
         IOM card in the system.  Since the MCM occupies two MDA slots in
         the chassis this value can only be an odd number."
    ::= { tmnxMcmEntry 1 }

tmnxMcmSupportedTypes            OBJECT-TYPE
    SYNTAX      TmnxMcmType
    MAX-ACCESS  read-only
    STATUS      current
    DESCRIPTION
        "A bit-mask that indicates what MCM types can be physically supported
         in this chassis."
    ::= { tmnxMcmEntry 2 }

tmnxMcmAssignedType              OBJECT-TYPE
    SYNTAX      TmnxMcmType
    MAX-ACCESS  read-write
    STATUS      current
    DESCRIPTION
        "A bit-mask that identifies the administratively assigned
         (pre-provisioned) MCM type that should occupy this chassis.
         If tmnxMcmAssignedType has a value of 'unassigned',
         this slot has not yet been pre-provisioned.  There must not be more
         than one bit set at a time in tmnxMcmAssignedType."
    DEFVAL      { 1 }
    ::= { tmnxMcmEntry 3 }

tmnxMcmEquippedType              OBJECT-TYPE
    SYNTAX      TmnxMcmType
    MAX-ACCESS  read-only
    STATUS      current
    DESCRIPTION
        "A bit-mask that identifies the MCM type that is physically
         inserted into this chassis.  If the chassis has been pre-provisioned,
         tmnxMcmAssignedType is not equal 'unassigned', and the
         value of tmnxMcmEquippedType is not the same as
         tmnxMcmAssignedType, a mismatch alarm will be raised.
         If the chassis has not been pre-provisioned, and the value of
         tmnxMcmEquippedType is not one of the supported types as
         specified by tmnxMcmSupportedTypes, a mismatch alarm will
         be raised.  There will not be more than one bit set at a time in
         tmnxMcmEquippedType."
    ::= { tmnxMcmEntry 4 }

tmnxMcmHwIndex                   OBJECT-TYPE
    SYNTAX      TmnxHwIndex
    MAX-ACCESS  read-only
    STATUS      current
    DESCRIPTION
        "The value of tmnxMcmHwIndex is the index into the tmnxHwTable for the
         row entry that represents the hardware component information for this
         MCM."
    ::= { tmnxMcmEntry 5 }

tmnxMcmTypeTable                 OBJECT-TYPE
    SYNTAX      SEQUENCE OF TmnxMcmTypeEntry
    MAX-ACCESS  not-accessible
    STATUS      current
    DESCRIPTION
        "The card type table has an entry for each Nokia 7710 series Mda
         Carrier Module (MCM) model."
    ::= { tmnxCardObjs 16 }

tmnxMcmTypeEntry                 OBJECT-TYPE
    SYNTAX      TmnxMcmTypeEntry
    MAX-ACCESS  not-accessible
    STATUS      current
    DESCRIPTION
        "Each row entry represents an Nokia 7710 series MCM model. Rows in this
         table are created by the agent at initialization and cannot be created
         or destroyed by SNMP Get or Set requests."
    INDEX       { tmnxMcmTypeIndex }
    ::= { tmnxMcmTypeTable 1 }

TmnxMcmTypeEntry                 ::= SEQUENCE
{
    tmnxMcmTypeIndex                 TmnxMcmType,
    tmnxMcmTypeName                  TNamedItemOrEmpty,
    tmnxMcmTypeDescription           TItemDescription,
    tmnxMcmTypeStatus                TruthValue
}

tmnxMcmTypeIndex                 OBJECT-TYPE
    SYNTAX      TmnxMcmType
    MAX-ACCESS  not-accessible
    STATUS      current
    DESCRIPTION
        "The unique index value which identifies this type of Nokia 7710 series
         MCM model."
    ::= { tmnxMcmTypeEntry 1 }

tmnxMcmTypeName                  OBJECT-TYPE
    SYNTAX      TNamedItemOrEmpty
    MAX-ACCESS  read-only
    STATUS      current
    DESCRIPTION
        "The administrative name that identifies this type of Nokia
         7710 series MCM model.  This name string may be used in CLI
         commands to specify a particular card model type."
    ::= { tmnxMcmTypeEntry 2 }

tmnxMcmTypeDescription           OBJECT-TYPE
    SYNTAX      TItemDescription
    MAX-ACCESS  read-only
    STATUS      current
    DESCRIPTION
        "A detailed description of this Nokia 7710 series MCM model."
    ::= { tmnxMcmTypeEntry 3 }

tmnxMcmTypeStatus                OBJECT-TYPE
    SYNTAX      TruthValue
    MAX-ACCESS  read-only
    STATUS      current
    DESCRIPTION
        "When tmnxMcmTypeStatus has a value of 'true' it
         indicates that this MCM is supported in this revision of the
         management software.  When it has a value of 'false' there is no
         support."
    ::= { tmnxMcmTypeEntry 4 }

tmnxIPsecIsaGrpTableLastChanged  OBJECT-TYPE
    SYNTAX      TimeStamp
    MAX-ACCESS  read-only
    STATUS      current
    DESCRIPTION
        "The value of tmnxIPsecIsaGrpTableLastChanged indicates the sysUpTime
         at the time of the last modification to tmnxIPsecIsaGrpTable by
         adding, deleting an entry or change to a writable object in the table.

         If no changes were made to the table since the last re-initialization
         of the local network management subsystem, then this object contains a
         zero value."
    ::= { tmnxCardObjs 17 }

tmnxIPsecIsaGrpTable             OBJECT-TYPE
    SYNTAX      SEQUENCE OF TmnxIPsecIsaGrpEntry
    MAX-ACCESS  not-accessible
    STATUS      current
    DESCRIPTION
        "Table to store entries for Groups of IPSec Integrated Service
         Adaptors. The table tmnxIPsecIsaGrpTable used to create and remove
         IPsec ISA groups. An IPsec ISA group is used to represent multiple
         hardware adaptors as a single entity. This allows for warm redundancy
         to be run between two IPsec ISAs."
    ::= { tmnxCardObjs 18 }

tmnxIPsecIsaGrpEntry             OBJECT-TYPE
    SYNTAX      TmnxIPsecIsaGrpEntry
    MAX-ACCESS  not-accessible
    STATUS      current
    DESCRIPTION
        "Information about a single IPsec group entry."
    INDEX       { tmnxIPsecIsaGrpId }
    ::= { tmnxIPsecIsaGrpTable 1 }

TmnxIPsecIsaGrpEntry             ::= SEQUENCE
{
    tmnxIPsecIsaGrpId                TmnxTunnelGroupId,
    tmnxIPsecIsaGrpRowStatus         RowStatus,
    tmnxIPsecIsaGrpLastChanged       TimeStamp,
    tmnxIPsecIsaGrpDescription       TItemDescription,
    tmnxIPsecIsaGrpAdminState        TmnxAdminState,
    tmnxIPsecIsaGrpOperState         TmnxOperState,
    tmnxIPsecIsaGrpIsaChassis        TmnxChassisIndex,
    tmnxIPsecIsaGrpPrimaryIsa        TmnxHwIndexOrZero,
    tmnxIPsecIsaGrpBackupIsa         TmnxHwIndexOrZero,
    tmnxIPsecIsaGrpActiveIsa         TmnxHwIndexOrZero,
    tmnxIPsecIsaGrpTunnels           Unsigned32,
    tmnxIPsecIsaGrpMaxTunnels        Unsigned32,
    tmnxIPsecIsaGrpTunnelReassembly  Integer32,
    tmnxIPsecIsaGrpOperFlags         TmnxIpSecIsaOperFlags,
    tmnxIPsecIsaGrpMultiActive       TruthValue,
    tmnxIPsecIsaGrpActiveMda         Unsigned32,
    tmnxIPsecIsaGrpIpTunnels         Unsigned32,
    tmnxIPsecIsaGrpIpMaxTunnels      Unsigned32,
    tmnxIPsecIsaGrpIPsecRespondOnly  TruthValue,
    tmnxIPsecIsaGrpIsaScaleMode      INTEGER
}

tmnxIPsecIsaGrpId                OBJECT-TYPE
    SYNTAX      TmnxTunnelGroupId
    MAX-ACCESS  not-accessible
    STATUS      current
    DESCRIPTION
        "The value of tmnxIPsecIsaGrpId specifies the id of a
         TmnxIPsecIsaGrpEntry and is the primary index for the table."
    ::= { tmnxIPsecIsaGrpEntry 1 }

tmnxIPsecIsaGrpRowStatus         OBJECT-TYPE
    SYNTAX      RowStatus
    MAX-ACCESS  read-create
    STATUS      current
    DESCRIPTION
        "The tmnxIPsecIsaGrpRowStatus object is used to create and delete rows
         in the tmnxIPsecIsaGrpTable."
    ::= { tmnxIPsecIsaGrpEntry 2 }

tmnxIPsecIsaGrpLastChanged       OBJECT-TYPE
    SYNTAX      TimeStamp
    MAX-ACCESS  read-only
    STATUS      current
    DESCRIPTION
        "The value of tmnxIPsecIsaGrpLastChanged indicates the sysUpTime at the
         time of the last modification of this entry.

         If no changes were made to the entry since the last re-initialization
         of the local network management subsystem, then this object contains a
         zero value."
    ::= { tmnxIPsecIsaGrpEntry 3 }

tmnxIPsecIsaGrpDescription       OBJECT-TYPE
    SYNTAX      TItemDescription
    MAX-ACCESS  read-create
    STATUS      current
    DESCRIPTION
        "The value of tmnxIPsecIsaGrpDescription specifies the user-provided
         description for each tmnxIPsecIsaGrpEntry in the table
         tmnxIPsecIsaGrpTable."
    DEFVAL      { "" }
    ::= { tmnxIPsecIsaGrpEntry 4 }

tmnxIPsecIsaGrpAdminState        OBJECT-TYPE
    SYNTAX      TmnxAdminState
    MAX-ACCESS  read-create
    STATUS      current
    DESCRIPTION
        "The value of tmnxIPsecIsaGrpAdminState specifies the administrative
         state of the tmnxIPsecIsaGrpEntry."
    DEFVAL      { outOfService }
    ::= { tmnxIPsecIsaGrpEntry 5 }

tmnxIPsecIsaGrpOperState         OBJECT-TYPE
    SYNTAX      TmnxOperState
    MAX-ACCESS  read-only
    STATUS      current
    DESCRIPTION
        "The value of tmnxIPsecIsaGrpOperState indicates the operational status
         of tmnxIPsecIsaGrpEntry."
    ::= { tmnxIPsecIsaGrpEntry 6 }

tmnxIPsecIsaGrpIsaChassis        OBJECT-TYPE
    SYNTAX      TmnxChassisIndex
    MAX-ACCESS  read-create
    STATUS      current
    DESCRIPTION
        "The value of tmnxIPsecIsaGrpIsaChassis specifies the chassis on which
         the tmnxIPsecIsaGrpPrimaryIsa and tmnxIPsecIsaGrpBackupIsa are
         present."
    DEFVAL      { 1 }
    ::= { tmnxIPsecIsaGrpEntry 7 }

tmnxIPsecIsaGrpPrimaryIsa        OBJECT-TYPE
    SYNTAX      TmnxHwIndexOrZero
    MAX-ACCESS  read-create
    STATUS      current
    DESCRIPTION
        "The value of tmnxIPsecIsaGrpPrimaryIsa specifies the primary IPsec ISA
         to be used for this module group."
    DEFVAL      { 0 }
    ::= { tmnxIPsecIsaGrpEntry 8 }

tmnxIPsecIsaGrpBackupIsa         OBJECT-TYPE
    SYNTAX      TmnxHwIndexOrZero
    MAX-ACCESS  read-create
    STATUS      current
    DESCRIPTION
        "The value of tmnxIPsecIsaGrpBackupIsa specifies the backup IPsec ISA
         to be used for this module group."
    DEFVAL      { 0 }
    ::= { tmnxIPsecIsaGrpEntry 9 }

tmnxIPsecIsaGrpActiveIsa         OBJECT-TYPE
    SYNTAX      TmnxHwIndexOrZero
    MAX-ACCESS  read-only
    STATUS      current
    DESCRIPTION
        "The value of tmnxIPsecIsaGrpActiveIsa indicates the active ISA that is
         being used for this module group."
    ::= { tmnxIPsecIsaGrpEntry 10 }

tmnxIPsecIsaGrpTunnels           OBJECT-TYPE
    SYNTAX      Unsigned32
    MAX-ACCESS  read-only
    STATUS      current
    DESCRIPTION
        "The value of tmnxIPsecIsaGrpTunnels indicates the number of IPSec
         tunnels being used for this module group."
    ::= { tmnxIPsecIsaGrpEntry 11 }

tmnxIPsecIsaGrpMaxTunnels        OBJECT-TYPE
    SYNTAX      Unsigned32
    MAX-ACCESS  read-only
    STATUS      current
    DESCRIPTION
        "The value of tmnxIPsecIsaGrpMaxTunnels indicates the maximum number of
         IPSec tunnels available for this module group."
    ::= { tmnxIPsecIsaGrpEntry 12 }

tmnxIPsecIsaGrpTunnelReassembly  OBJECT-TYPE
    SYNTAX      Integer32 (0..5000)
    UNITS       "milli-seconds"
    MAX-ACCESS  read-create
    STATUS      current
    DESCRIPTION
        "The value of tmnxIPsecIsaGrpTunnelReassembly specifies the maximum
         number of seconds to wait to receive all fragments of a particular
         IPSec or GRE packet for reassembly.

         The tmnxGreTunnelReassembly value set to zero indicates that
         reassembly is disabled.

         An 'inconsistentValue' error is returned if the value is not a
         multiple of 100 milli-seconds."
    DEFVAL      { 0 }
    ::= { tmnxIPsecIsaGrpEntry 13 }

tmnxIPsecIsaGrpOperFlags         OBJECT-TYPE
    SYNTAX      TmnxIpSecIsaOperFlags
    MAX-ACCESS  read-only
    STATUS      current
    DESCRIPTION
        "The value of tmnxIPsecIsaGrpOperFlags indicates the operational flags
         to determine the status of tmnxIPsecIsaGrpEntry."
    ::= { tmnxIPsecIsaGrpEntry 14 }

tmnxIPsecIsaGrpMultiActive       OBJECT-TYPE
    SYNTAX      TruthValue
    MAX-ACCESS  read-create
    STATUS      current
    DESCRIPTION
        "The value of tmnxIPsecIsaGrpMultiActive specifies whether this tunnel
         group will load-balance IPsec traffic on multiple MDAs."
    DEFVAL      { false }
    ::= { tmnxIPsecIsaGrpEntry 15 }

tmnxIPsecIsaGrpActiveMda         OBJECT-TYPE
    SYNTAX      Unsigned32 (1..16)
    MAX-ACCESS  read-create
    STATUS      current
    DESCRIPTION
        "The value of tmnxIPsecIsaGrpActiveMda specifies the number of active
         MDA to be used by this tunnel-group to load-balance IPsec traffic."
    DEFVAL      { 1 }
    ::= { tmnxIPsecIsaGrpEntry 16 }

tmnxIPsecIsaGrpIpTunnels         OBJECT-TYPE
    SYNTAX      Unsigned32
    MAX-ACCESS  read-only
    STATUS      current
    DESCRIPTION
        "The value of tmnxIPsecIsaGrpIpTunnels indicates the number of IP
         tunnels being used for this module group."
    ::= { tmnxIPsecIsaGrpEntry 17 }

tmnxIPsecIsaGrpIpMaxTunnels      OBJECT-TYPE
    SYNTAX      Unsigned32
    MAX-ACCESS  read-only
    STATUS      current
    DESCRIPTION
        "The value of tmnxIPsecIsaGrpIpMaxTunnels indicates the maximum number
         of IP tunnels available for this module group."
    ::= { tmnxIPsecIsaGrpEntry 18 }

tmnxIPsecIsaGrpIPsecRespondOnly  OBJECT-TYPE
    SYNTAX      TruthValue
    MAX-ACCESS  read-create
    STATUS      current
    DESCRIPTION
        "The value of tmnxIPsecIsaGrpIPsecRespondOnly specifies whether the
         IPsec tunnel will respond to requests only and does not initiate
         exchanges with the peer."
    DEFVAL      { false }
    ::= { tmnxIPsecIsaGrpEntry 19 }

tmnxIPsecIsaGrpIsaScaleMode      OBJECT-TYPE
    SYNTAX      INTEGER {
        tunnelLimit2k  (1),
        tunnelLimit32k (2),
        reserved3      (3),
        tunnelLimit8   (4)
    }
    MAX-ACCESS  read-create
    STATUS      current
    DESCRIPTION
        "The value of tmnxIPsecIsaGrpIsaScaleMode specifies the set of
         supported scaling modes for each ISA in this group.

         The scaling modes can be one of:
             tunnelLimit2k    (1) - maximum 2048 tunnels (e.g., IPsec, GRE and
                                    IP) per ISA
             tunnelLimit32k   (2) - maximum 32678 tunnels per ISA
             tunnelLimit8     (4) - maximum 8 tunnels per ISA

         When creating a row, this object must be specified in the same SNMP
         PDU as tmnxIPsecIsaGrpRowStatus. The value of this object cannot be
         changed once the row is created.

         Platform    tmnxIPsecIsaGrpIsaScaleMode Default
         ---------    -----------------------------------
         VSR         'tunnelLimit2k(1)'
         SAR-Hm      'tunnelLimit8(4)'
         Otherwise   'tunnelLimit32k(2)'"
    ::= { tmnxIPsecIsaGrpEntry 20 }

tmnxHsmdaMdaSchOvrTblLastChangd  OBJECT-TYPE
    SYNTAX      TimeStamp
    MAX-ACCESS  read-only
    STATUS      obsolete
    DESCRIPTION
        "The value of tmnxHsmdaMdaSchOvrTblLastChangd indicates the sysUpTime
         at the time of the last modification of tmnxHsmdaMdaSchOvrTable.

         If no changes were made to the table since the last re-initialization
         of the local network management subsystem, then this object contains a
         zero value.

         This object is obsoleted in 10.0 Release."
    ::= { tmnxCardObjs 19 }

tmnxHsmdaMdaSchOvrTable          OBJECT-TYPE
    SYNTAX      SEQUENCE OF TmnxHsmdaMdaSchOvrEntry
    MAX-ACCESS  not-accessible
    STATUS      obsolete
    DESCRIPTION
        "The tmnxHsmdaMdaSchOvrTable has an entry for each MDA-level HSMDA
         scheduler override configured on this system.

         This table is obsoleted in 10.0 Release."
    ::= { tmnxCardObjs 20 }

tmnxHsmdaMdaSchOvrEntry          OBJECT-TYPE
    SYNTAX      TmnxHsmdaMdaSchOvrEntry
    MAX-ACCESS  not-accessible
    STATUS      obsolete
    DESCRIPTION
        "Each row represents a particular MDA-level HSMDA scheduler override.
         Entries are created and deleted by the user."
    INDEX       {
        tmnxChassisIndex,
        tmnxCardSlotNum,
        tmnxMDASlotNum
    }
    ::= { tmnxHsmdaMdaSchOvrTable 1 }

TmnxHsmdaMdaSchOvrEntry          ::= SEQUENCE
{
    tmnxHsmdaMdaSchOvrRowStatus      RowStatus,
    tmnxHsmdaMdaSchOvrLastChanged    TimeStamp,
    tmnxHsmdaMdaSchOvrMaxRate        THsmdaPIRMRateOverride,
    tmnxHsmdaMdaSchOvrGrp1Rate       THsmdaPIRMRateOverride,
    tmnxHsmdaMdaSchOvrGrp2Rate       THsmdaPIRMRateOverride,
    tmnxHsmdaMdaSchOvrClass1Rate     THsmdaPIRMRateOverride,
    tmnxHsmdaMdaSchOvrClass1WtInGrp  THsmdaWeightOverride,
    tmnxHsmdaMdaSchOvrClass2Rate     THsmdaPIRMRateOverride,
    tmnxHsmdaMdaSchOvrClass2WtInGrp  THsmdaWeightOverride,
    tmnxHsmdaMdaSchOvrClass3Rate     THsmdaPIRMRateOverride,
    tmnxHsmdaMdaSchOvrClass3WtInGrp  THsmdaWeightOverride,
    tmnxHsmdaMdaSchOvrClass4Rate     THsmdaPIRMRateOverride,
    tmnxHsmdaMdaSchOvrClass4WtInGrp  THsmdaWeightOverride,
    tmnxHsmdaMdaSchOvrClass5Rate     THsmdaPIRMRateOverride,
    tmnxHsmdaMdaSchOvrClass5WtInGrp  THsmdaWeightOverride,
    tmnxHsmdaMdaSchOvrClass6Rate     THsmdaPIRMRateOverride,
    tmnxHsmdaMdaSchOvrClass6WtInGrp  THsmdaWeightOverride,
    tmnxHsmdaMdaSchOvrClass7Rate     THsmdaPIRMRateOverride,
    tmnxHsmdaMdaSchOvrClass7WtInGrp  THsmdaWeightOverride,
    tmnxHsmdaMdaSchOvrClass8Rate     THsmdaPIRMRateOverride,
    tmnxHsmdaMdaSchOvrClass8WtInGrp  THsmdaWeightOverride
}

tmnxHsmdaMdaSchOvrRowStatus      OBJECT-TYPE
    SYNTAX      RowStatus
    MAX-ACCESS  read-create
    STATUS      obsolete
    DESCRIPTION
        "The value of tmnxHsmdaMdaSchOvrRowStatus is used for the creation and
         deletion of MDA-level HSMDA scheduler overrides.

         When the tmnxMDAAssignedType of the tmnxMDAEntry indexed by the same
         indices of this table is a non-HSMDA MDA Type, creation will fail and
         return a 'noCreation' error."
    ::= { tmnxHsmdaMdaSchOvrEntry 1 }

tmnxHsmdaMdaSchOvrLastChanged    OBJECT-TYPE
    SYNTAX      TimeStamp
    MAX-ACCESS  read-only
    STATUS      obsolete
    DESCRIPTION
        "The value of tmnxHsmdaMdaSchOvrLastChanged indicates the sysUpTime at
         the time of the last modification of this entry.

         If no changes were made to the entry since the last re-initialization
         of the local network management subsystem, then this object contains a
         zero value."
    ::= { tmnxHsmdaMdaSchOvrEntry 2 }

tmnxHsmdaMdaSchOvrMaxRate        OBJECT-TYPE
    SYNTAX      THsmdaPIRMRateOverride
    UNITS       "Mbps"
    MAX-ACCESS  read-create
    STATUS      obsolete
    DESCRIPTION
        "The value of tmnxHsmdaMdaSchOvrMaxRate specifies the explicit maximum
         frame based bandwidth limit, in megabits per second, for this HSMDA
         scheduler.

         A value of -2 indicates no override.

         This object overrides TIMETRA-QOS-MIB::tHsmdaSchedulerPlcyMaxRate."
    DEFVAL      { -2 }
    ::= { tmnxHsmdaMdaSchOvrEntry 3 }

tmnxHsmdaMdaSchOvrGrp1Rate       OBJECT-TYPE
    SYNTAX      THsmdaPIRMRateOverride
    UNITS       "Mbps"
    MAX-ACCESS  read-create
    STATUS      obsolete
    DESCRIPTION
        "The value of tmnxHsmdaMdaSchOvrGrp1Rate specifies the explicit maximum
         frame based bandwidth limit, in megabits per second, for group 1 for
         this HSMDA scheduler.

         A value of -2 indicates no override.

         This object overrides TIMETRA-QOS-MIB::tHsmdaSchedulerPlcyGrp1Rate."
    DEFVAL      { -2 }
    ::= { tmnxHsmdaMdaSchOvrEntry 4 }

tmnxHsmdaMdaSchOvrGrp2Rate       OBJECT-TYPE
    SYNTAX      THsmdaPIRMRateOverride
    UNITS       "Mbps"
    MAX-ACCESS  read-create
    STATUS      obsolete
    DESCRIPTION
        "The value of tmnxHsmdaMdaSchOvrGrp2Rate specifies the explicit maximum
         frame based bandwidth limit, in megabits per second, for group 2 for
         this HSMDA scheduler.

         A value of -2 indicates no override.

         This object overrides TIMETRA-QOS-MIB::tHsmdaSchedulerPlcyGrp2Rate."
    DEFVAL      { -2 }
    ::= { tmnxHsmdaMdaSchOvrEntry 5 }

tmnxHsmdaMdaSchOvrClass1Rate     OBJECT-TYPE
    SYNTAX      THsmdaPIRMRateOverride
    UNITS       "Mbps"
    MAX-ACCESS  read-create
    STATUS      obsolete
    DESCRIPTION
        "The value of tmnxHsmdaMdaSchOvrClass1Rate specifies the explicit
         maximum frame based bandwidth limit, in megabits per second, for this
         HSMDA scheduler policy level.

         A value of -2 indicates no override.

         This object overrides TIMETRA-QOS-MIB::tHsmdaSchedulerPlcyLvl1Rate."
    DEFVAL      { -2 }
    ::= { tmnxHsmdaMdaSchOvrEntry 6 }

tmnxHsmdaMdaSchOvrClass1WtInGrp  OBJECT-TYPE
    SYNTAX      THsmdaWeightOverride
    MAX-ACCESS  read-create
    STATUS      obsolete
    DESCRIPTION
        "The value of tmnxHsmdaMdaSchOvrClass1WtInGrp specifies the weight the
         HSMDA scheduler policy should apply to this policy level within the
         group it belongs to.

         The value of tmnxHsmdaMdaSchOvrClass1WtInGrp will only be used if this
         policy level has been assigned to a group by setting
         tHsmdaSchedulerPlcyLvl1GrpId to a non-zero value.

         A value of -2 indicates no override.

         This object overrides
         TIMETRA-QOS-MIB::tHsmdaSchedulerPlcyLvl1WgtInGrp."
    DEFVAL      { -2 }
    ::= { tmnxHsmdaMdaSchOvrEntry 7 }

tmnxHsmdaMdaSchOvrClass2Rate     OBJECT-TYPE
    SYNTAX      THsmdaPIRMRateOverride
    UNITS       "Mbps"
    MAX-ACCESS  read-create
    STATUS      obsolete
    DESCRIPTION
        "The value of tmnxHsmdaMdaSchOvrClass2Rate specifies the explicit
         maximum frame based bandwidth limit, in megabits per second, for this
         HSMDA scheduler policy level.

         A value of -2 indicates no override.

         This object overrides TIMETRA-QOS-MIB::tHsmdaSchedulerPlcyLvl2Rate."
    DEFVAL      { -2 }
    ::= { tmnxHsmdaMdaSchOvrEntry 8 }

tmnxHsmdaMdaSchOvrClass2WtInGrp  OBJECT-TYPE
    SYNTAX      THsmdaWeightOverride
    MAX-ACCESS  read-create
    STATUS      obsolete
    DESCRIPTION
        "The value of tmnxHsmdaMdaSchOvrClass2WtInGrp specifies the weight the
         HSMDA scheduler policy should apply to this policy level within the
         group it belongs to.

         The value of tmnxHsmdaMdaSchOvrClass2WtInGrp will only be used if this
         policy level has been assigned to a group by setting
         tHsmdaSchedulerPlcyLvl2GrpId to a non-zero value.

         A value of -2 indicates no override.

         This object overrides
         TIMETRA-QOS-MIB::tHsmdaSchedulerPlcyLvl2WgtInGrp."
    DEFVAL      { -2 }
    ::= { tmnxHsmdaMdaSchOvrEntry 9 }

tmnxHsmdaMdaSchOvrClass3Rate     OBJECT-TYPE
    SYNTAX      THsmdaPIRMRateOverride
    UNITS       "Mbps"
    MAX-ACCESS  read-create
    STATUS      obsolete
    DESCRIPTION
        "The value of tmnxHsmdaMdaSchOvrClass3Rate specifies the explicit
         maximum frame based bandwidth limit, in megabits per second, for this
         HSMDA scheduler policy level.

         A value of -2 indicates no override.

         This object overrides TIMETRA-QOS-MIB::tHsmdaSchedulerPlcyLvl3Rate."
    DEFVAL      { -2 }
    ::= { tmnxHsmdaMdaSchOvrEntry 10 }

tmnxHsmdaMdaSchOvrClass3WtInGrp  OBJECT-TYPE
    SYNTAX      THsmdaWeightOverride
    MAX-ACCESS  read-create
    STATUS      obsolete
    DESCRIPTION
        "The value of tmnxHsmdaMdaSchOvrClass3WtInGrp specifies the weight the
         HSMDA scheduler policy should apply to this policy level within the
         group it belongs to.

         The value of tmnxHsmdaMdaSchOvrClass3WtInGrp will only be used if this
         policy level has been assigned to a group by setting
         tHsmdaSchedulerPlcyLvl3GrpId to a non-zero value.

         A value of -2 indicates no override.

         This object overrides
         TIMETRA-QOS-MIB::tHsmdaSchedulerPlcyLvl3WgtInGrp."
    DEFVAL      { -2 }
    ::= { tmnxHsmdaMdaSchOvrEntry 11 }

tmnxHsmdaMdaSchOvrClass4Rate     OBJECT-TYPE
    SYNTAX      THsmdaPIRMRateOverride
    UNITS       "Mbps"
    MAX-ACCESS  read-create
    STATUS      obsolete
    DESCRIPTION
        "The value of tmnxHsmdaMdaSchOvrClass4Rate specifies the explicit
         maximum frame based bandwidth limit, in megabits per second, for this
         HSMDA scheduler policy level.

         A value of -2 indicates no override.

         This object overrides TIMETRA-QOS-MIB::tHsmdaSchedulerPlcyLvl4Rate."
    DEFVAL      { -2 }
    ::= { tmnxHsmdaMdaSchOvrEntry 12 }

tmnxHsmdaMdaSchOvrClass4WtInGrp  OBJECT-TYPE
    SYNTAX      THsmdaWeightOverride
    MAX-ACCESS  read-create
    STATUS      obsolete
    DESCRIPTION
        "The value of tmnxHsmdaMdaSchOvrClass4WtInGrp specifies the weight the
         HSMDA scheduler policy should apply to this policy level within the
         group it belongs to.

         The value of tmnxHsmdaMdaSchOvrClass4WtInGrp will only be used if this
         policy level has been assigned to a group by setting
         tHsmdaSchedulerPlcyLvl4GrpId to a non-zero value.

         A value of -2 indicates no override.

         This object overrides
         TIMETRA-QOS-MIB::tHsmdaSchedulerPlcyLvl4WgtInGrp."
    DEFVAL      { -2 }
    ::= { tmnxHsmdaMdaSchOvrEntry 13 }

tmnxHsmdaMdaSchOvrClass5Rate     OBJECT-TYPE
    SYNTAX      THsmdaPIRMRateOverride
    UNITS       "Mbps"
    MAX-ACCESS  read-create
    STATUS      obsolete
    DESCRIPTION
        "The value of tmnxHsmdaMdaSchOvrClass5Rate specifies the explicit
         maximum frame based bandwidth limit, in megabits per second, for this
         HSMDA scheduler policy level.

         A value of -2 indicates no override.

         This object overrides TIMETRA-QOS-MIB::tHsmdaSchedulerPlcyLvl5Rate."
    DEFVAL      { -2 }
    ::= { tmnxHsmdaMdaSchOvrEntry 14 }

tmnxHsmdaMdaSchOvrClass5WtInGrp  OBJECT-TYPE
    SYNTAX      THsmdaWeightOverride
    MAX-ACCESS  read-create
    STATUS      obsolete
    DESCRIPTION
        "The value of tmnxHsmdaMdaSchOvrClass5WtInGrp specifies the weight the
         HSMDA scheduler policy should apply to this policy level within the
         group it belongs to.

         The value of tmnxHsmdaMdaSchOvrClass5WtInGrp will only be used if this
         policy level has been assigned to a group by setting
         tHsmdaSchedulerPlcyLvl5GrpId to a non-zero value.

         A value of -2 indicates no override.

         This object overrides
         TIMETRA-QOS-MIB::tHsmdaSchedulerPlcyLvl5WgtInGrp."
    DEFVAL      { -2 }
    ::= { tmnxHsmdaMdaSchOvrEntry 15 }

tmnxHsmdaMdaSchOvrClass6Rate     OBJECT-TYPE
    SYNTAX      THsmdaPIRMRateOverride
    UNITS       "Mbps"
    MAX-ACCESS  read-create
    STATUS      obsolete
    DESCRIPTION
        "The value of tmnxHsmdaMdaSchOvrClass6Rate specifies the explicit
         maximum frame based bandwidth limit, in megabits per second, for this
         HSMDA scheduler policy level.

         A value of -2 indicates no override.

         This object overrides TIMETRA-QOS-MIB::tHsmdaSchedulerPlcyLvl6Rate."
    DEFVAL      { -2 }
    ::= { tmnxHsmdaMdaSchOvrEntry 16 }

tmnxHsmdaMdaSchOvrClass6WtInGrp  OBJECT-TYPE
    SYNTAX      THsmdaWeightOverride
    MAX-ACCESS  read-create
    STATUS      obsolete
    DESCRIPTION
        "The value of tmnxHsmdaMdaSchOvrClass6WtInGrp specifies the weight the
         HSMDA scheduler policy should apply to this policy level within the
         group it belongs to.

         The value of tmnxHsmdaMdaSchOvrClass6WtInGrp will only be used if this
         policy level has been assigned to a group by setting
         tHsmdaSchedulerPlcyLvl6GrpId to a non-zero value.

         A value of -2 indicates no override.

         This object overrides
         TIMETRA-QOS-MIB::tHsmdaSchedulerPlcyLvl6WgtInGrp."
    DEFVAL      { -2 }
    ::= { tmnxHsmdaMdaSchOvrEntry 17 }

tmnxHsmdaMdaSchOvrClass7Rate     OBJECT-TYPE
    SYNTAX      THsmdaPIRMRateOverride
    UNITS       "Mbps"
    MAX-ACCESS  read-create
    STATUS      obsolete
    DESCRIPTION
        "The value of tmnxHsmdaMdaSchOvrClass7Rate specifies the explicit
         maximum frame based bandwidth limit, in megabits per second, for this
         HSMDA scheduler policy level.

         A value of -2 indicates no override.

         This object overrides TIMETRA-QOS-MIB::tHsmdaSchedulerPlcyLvl7Rate."
    DEFVAL      { -2 }
    ::= { tmnxHsmdaMdaSchOvrEntry 18 }

tmnxHsmdaMdaSchOvrClass7WtInGrp  OBJECT-TYPE
    SYNTAX      THsmdaWeightOverride
    MAX-ACCESS  read-create
    STATUS      obsolete
    DESCRIPTION
        "The value of tmnxHsmdaMdaSchOvrClass7WtInGrp specifies the weight the
         HSMDA scheduler policy should apply to this policy level within the
         group it belongs to.

         The value of tmnxHsmdaMdaSchOvrClass7WtInGrp will only be used if this
         policy level has been assigned to a group by setting
         tHsmdaSchedulerPlcyLvl7GrpId to a non-zero value.

         A value of -2 indicates no override.

         This object overrides
         TIMETRA-QOS-MIB::tHsmdaSchedulerPlcyLvl7WgtInGrp."
    DEFVAL      { -2 }
    ::= { tmnxHsmdaMdaSchOvrEntry 19 }

tmnxHsmdaMdaSchOvrClass8Rate     OBJECT-TYPE
    SYNTAX      THsmdaPIRMRateOverride
    UNITS       "Mbps"
    MAX-ACCESS  read-create
    STATUS      obsolete
    DESCRIPTION
        "The value of tmnxHsmdaMdaSchOvrClass8Rate specifies the explicit
         maximum frame based bandwidth limit, in megabits per second, for this
         HSMDA scheduler policy level.

         A value of -2 indicates no override.

         This object overrides TIMETRA-QOS-MIB::tHsmdaSchedulerPlcyLvl8Rate."
    DEFVAL      { -2 }
    ::= { tmnxHsmdaMdaSchOvrEntry 20 }

tmnxHsmdaMdaSchOvrClass8WtInGrp  OBJECT-TYPE
    SYNTAX      THsmdaWeightOverride
    MAX-ACCESS  read-create
    STATUS      obsolete
    DESCRIPTION
        "The value of tmnxHsmdaMdaSchOvrClass8WtInGrp specifies the weight the
         HSMDA scheduler policy should apply to this policy level within the
         group it belongs to.

         The value of tmnxHsmdaMdaSchOvrClass8WtInGrp will only be used if this
         policy level has been assigned to a group by setting
         tHsmdaSchedulerPlcyLvl8GrpId to a non-zero value.

         A value of -2 indicates no override.

         This object overrides
         TIMETRA-QOS-MIB::tHsmdaSchedulerPlcyLvl8WgtInGrp."
    DEFVAL      { -2 }
    ::= { tmnxHsmdaMdaSchOvrEntry 21 }

tmnxFPTable                      OBJECT-TYPE
    SYNTAX      SEQUENCE OF TmnxFPEntry
    MAX-ACCESS  not-accessible
    STATUS      current
    DESCRIPTION
        "The tmnxFPTable has an entry for each Forwarding Plane configuration.
         An entry is created in this table whenever an entry for card is
         created in tmnxCardTable. This entry is relevant only for IOM3/IMM."
    ::= { tmnxCardObjs 21 }

tmnxFPEntry                      OBJECT-TYPE
    SYNTAX      TmnxFPEntry
    MAX-ACCESS  not-accessible
    STATUS      current
    DESCRIPTION
        "Each row entry represents a Forwarding Plane (FP) configuration."
    INDEX       {
        tmnxChassisIndex,
        tmnxCardSlotNum,
        tmnxFPNum
    }
    ::= { tmnxFPTable 1 }

TmnxFPEntry                      ::= SEQUENCE
{
    tmnxFPNum                        Unsigned32,
    tmnxFPMcPathMgmtBwPlcyName       TNamedItem,
    tmnxFPMcPathMgmtAdminState       TmnxAdminState,
    tmnxFPLastChanged                TimeStamp,
    tmnxFPHiBwMcastSource            TruthValue,
    tmnxFPHiBwMcastAlarm             TruthValue,
    tmnxFPHiBwMcastTapCount          Gauge32,
    tmnxFPHiBwMcastGroup             Unsigned32,
    tmnxFPWredBufAllocMin            Unsigned32,
    tmnxFPWredBufAllocMax            Unsigned32,
    tmnxFPWredResvCbsMin             Unsigned32,
    tmnxFPWredResvCbsMax             Unsigned32,
    tmnxFPWredSlopePolicy            TNamedItemOrEmpty,
    tmnxFPWredAdminState             TmnxAdminState,
    tmnxFPHiBwMcastDefaultPathsOnly  TruthValue,
    tmnxFPDCpuProtDynEnfrcPlcrPool   Integer32,
    tmnxFPStablePoolSizing           TruthValue,
    tmnxFPIngressBufferAllocation    Unsigned32,
    tmnxFPPlcyAcctStatsPool          Unsigned32,
    tmnxFPPlcyAcctStatsInUse         Unsigned32,
    tmnxFPInitExtractDropPrioMode    INTEGER,
    tmnxFPEgrHsPoolPolicy            TNamedItemOrEmpty,
    tmnxFPEgrHsFixedHighThreshDelta  Integer32,
    tmnxFPMcPathMgmtPriInUseBw       Gauge32,
    tmnxFPMcPathMgmtSecInUseBw       Gauge32,
    tmnxFPMcPathMgmtBlkHoleInUseBw   Gauge32,
    tmnxFPGeneration                 TmnxFpGeneration
}

tmnxFPNum                        OBJECT-TYPE
    SYNTAX      Unsigned32
    MAX-ACCESS  not-accessible
    STATUS      current
    DESCRIPTION
        "The value of tmnxFPNum identifies the Forwarding Plane."
    ::= { tmnxFPEntry 1 }

tmnxFPMcPathMgmtBwPlcyName       OBJECT-TYPE
    SYNTAX      TNamedItem
    MAX-ACCESS  read-write
    STATUS      current
    DESCRIPTION
        "The value of tmnxFPMcPathMgmtBwPlcyName specifies the multicast policy
         name configured for the FP. tmnxFPMcPathMgmtBwPlcyName can be set only
         if the policy exists in
         TIMETRA-MCAST-PATH-MGMT-MIB::tmnxMcPathBwPlcyTable."
    DEFVAL      { "default" }
    ::= { tmnxFPEntry 2 }

tmnxFPMcPathMgmtAdminState       OBJECT-TYPE
    SYNTAX      TmnxAdminState
    MAX-ACCESS  read-write
    STATUS      current
    DESCRIPTION
        "The value of tmnxFPMcPathMgmtAdminState specifies administrative state
         of the multicast path for the FP."
    DEFVAL      { outOfService }
    ::= { tmnxFPEntry 3 }

tmnxFPLastChanged                OBJECT-TYPE
    SYNTAX      TimeStamp
    MAX-ACCESS  read-only
    STATUS      current
    DESCRIPTION
        "The value of tmnxFPLastChanged indicates the timestamp of last change
         to this row in tmnxFPTable."
    ::= { tmnxFPEntry 4 }

tmnxFPHiBwMcastSource            OBJECT-TYPE
    SYNTAX      TruthValue
    MAX-ACCESS  read-write
    STATUS      current
    DESCRIPTION
        "The value of tmnxFPHiBwMcastSource specifies if this FP should attempt
         to allocate separate fabric planes to allocate high bandwidth
         multicast traffic taps.

         tmnxFPHiBwMcastGroup must be set in the same SNMP request PDU with
         tmnxFPHiBwMcastSource or an 'inconsistentValue' error will be
         returned."
    DEFVAL      { false }
    ::= { tmnxFPEntry 5 }

tmnxFPHiBwMcastAlarm             OBJECT-TYPE
    SYNTAX      TruthValue
    MAX-ACCESS  read-write
    STATUS      current
    DESCRIPTION
        "The value of tmnxFPHiBwMcastAlarm specifies if a
         tmnxChassisHiBwMcastAlarm alarm is raised if there are more than one
         high bandwidth multicast traffic taps sharing a plane."
    DEFVAL      { false }
    ::= { tmnxFPEntry 6 }

tmnxFPHiBwMcastTapCount          OBJECT-TYPE
    SYNTAX      Gauge32
    MAX-ACCESS  read-only
    STATUS      current
    DESCRIPTION
        "The value of tmnxFPHiBwMcastTapCount indicates the number of high
         bandwidth multicast traffic taps on this FP."
    ::= { tmnxFPEntry 7 }

tmnxFPHiBwMcastGroup             OBJECT-TYPE
    SYNTAX      Unsigned32 (0..32)
    MAX-ACCESS  read-write
    STATUS      current
    DESCRIPTION
        "The value of tmnxFPHiBwMcastGroup specifies the group of high
         bandwidth multicast traffic taps to which this tap belongs.

         A value of '0' specifies that this tap is not a member of any High
         Bandwidth Multicast group.

         tmnxFPHiBwMcastGroup must be set in the same SNMP request PDU with
         tmnxFPHiBwMcastSource or an 'inconsistentValue' error will be
         returned."
    DEFVAL      { 0 }
    ::= { tmnxFPEntry 8 }

tmnxFPWredBufAllocMin            OBJECT-TYPE
    SYNTAX      Unsigned32 (0..9999)
    UNITS       "Hundredths of a percent"
    MAX-ACCESS  read-write
    STATUS      current
    DESCRIPTION
        "The value of tmnxFPWredBufAllocMin specifies the minimum WRED
         (Weighted Random Early Detection) queue aggregate buffer allocation
         which will be set aside for WRED queue buffer pools."
    DEFVAL      { 2500 }
    ::= { tmnxFPEntry 9 }

tmnxFPWredBufAllocMax            OBJECT-TYPE
    SYNTAX      Unsigned32 (1..9999)
    UNITS       "Hundredths of a percent"
    MAX-ACCESS  read-write
    STATUS      current
    DESCRIPTION
        "The value of tmnxFPWredBufAllocMax specifies the maximum WRED queue
         aggregate buffer allocation which will be set aside for WRED queue
         buffer pools."
    DEFVAL      { 2500 }
    ::= { tmnxFPEntry 10 }

tmnxFPWredResvCbsMin             OBJECT-TYPE
    SYNTAX      Unsigned32 (0..9999)
    UNITS       "Hundredths of a percent"
    MAX-ACCESS  read-write
    STATUS      current
    DESCRIPTION
        "The value of tmnxFPWredResvCbsMin specifies the minimum buffers within
         the WRED pool that will be set aside for WRED queues operating within
         their configured CBS (Committed Buffer Size) thresholds."
    DEFVAL      { 2500 }
    ::= { tmnxFPEntry 11 }

tmnxFPWredResvCbsMax             OBJECT-TYPE
    SYNTAX      Unsigned32 (1..9999)
    UNITS       "Hundredths of a percent"
    MAX-ACCESS  read-write
    STATUS      current
    DESCRIPTION
        "The value of tmnxFPWredResvCbsMax specifies the maximum buffers within
         the WRED pool that will be set aside for WRED queues operating within
         their configured CBS (Committed Buffer Size) thresholds."
    DEFVAL      { 2500 }
    ::= { tmnxFPEntry 12 }

tmnxFPWredSlopePolicy            OBJECT-TYPE
    SYNTAX      TNamedItemOrEmpty
    MAX-ACCESS  read-write
    STATUS      current
    DESCRIPTION
        "The value of tmnxFPWredSlopePolicy specifies the name of slope policy
         being used within WRED pool."
    DEFVAL      { "default" }
    ::= { tmnxFPEntry 13 }

tmnxFPWredAdminState             OBJECT-TYPE
    SYNTAX      TmnxAdminState
    MAX-ACCESS  read-write
    STATUS      current
    DESCRIPTION
        "The value of tmnxFPWredAdminState specifies administrative state of
         the egress WRED queue support on the card."
    DEFVAL      { outOfService }
    ::= { tmnxFPEntry 14 }

tmnxFPHiBwMcastDefaultPathsOnly  OBJECT-TYPE
    SYNTAX      TruthValue
    MAX-ACCESS  read-write
    STATUS      current
    DESCRIPTION
        "The value of tmnxFPHiBwMcastDefaultPathsOnly specifies whether only
         the default paths are to be High Bandwidth Multicast (HBM) (typically
         paths 0 and 15) and the remaining paths are non-HBM 'true (1)', or all
         paths are configured HBM on the forwarding path 'false (2)'.

         This object is only meaningful if tmnxFPHiBwMcastSource is set to the
         value 'true (1)'."
    DEFVAL      { false }
    ::= { tmnxFPEntry 15 }

tmnxFPDCpuProtDynEnfrcPlcrPool   OBJECT-TYPE
    SYNTAX      Integer32 (0 | 1000..32000)
    MAX-ACCESS  read-write
    STATUS      current
    DESCRIPTION
        "The value of tmnxFPDCpuProtDynEnfrcPlcrPool specifies number of
         policers that are set aside that can be instantiated as dynamic
         enforcement policers when Distributed CPU Protection is configured
         with dynamic enforcement."
    DEFVAL      { 0 }
    ::= { tmnxFPEntry 16 }

tmnxFPStablePoolSizing           OBJECT-TYPE
    SYNTAX      TruthValue
    MAX-ACCESS  read-write
    STATUS      current
    DESCRIPTION
        "The value of tmnxFPStablePoolSizing specifies whether the forwarding
         plane (FP) should split the buffers in a fixed way. When the value of
         tmnxFPStablePoolSizing is set to 'true', the forwarding plane will
         evenly split the buffers between all possible MDAs. Then, each MDA
         buffers will be split between all possible ports based on port max
         bandwidth adjusted by the port's modify-buffer-allocation-rate
         percentages.

         The value of tmnxFPStablePoolSizing cannot be set to 'true' when
         either tmnxCardNamedPoolAdminMode or tmnxCardNamedPoolOperMode is set
         to 'inService'. Likewise, the value of tmnxCardNamedPoolAdminMode or
         tmnxCardNamedPoolOperMode cannot be set to 'inService' when
         tmnxFPStablePoolSizing is set to 'true'."
    DEFVAL      { false }
    ::= { tmnxFPEntry 17 }

tmnxFPIngressBufferAllocation    OBJECT-TYPE
    SYNTAX      Unsigned32 (2000..8000)
    UNITS       "Hundredths of a percent"
    MAX-ACCESS  read-write
    STATUS      current
    DESCRIPTION
        "The value of tmnxFPIngressBufferAllocation specifies the buffer
         allocation on a given forwarding plane (FP) which will be set aside
         for ingress pools."
    DEFVAL      { 5000 }
    ::= { tmnxFPEntry 18 }

tmnxFPPlcyAcctStatsPool          OBJECT-TYPE
    SYNTAX      Unsigned32 (0 | 1000..128000)
    MAX-ACCESS  read-write
    STATUS      current
    DESCRIPTION
        "The value of tmnxFPPlcyAcctStatsPool specifies the number of stats
         resources to reserve for policy-accounting on this forwarding plane
         (FP).

         The value of zero indicates no stats resources are allocated to policy
         accounting."
    DEFVAL      { 0 }
    ::= { tmnxFPEntry 19 }

tmnxFPPlcyAcctStatsInUse         OBJECT-TYPE
    SYNTAX      Unsigned32
    MAX-ACCESS  read-only
    STATUS      current
    DESCRIPTION
        "The value of tmnxFPPlcyAcctStatsInUse indicates the total number of
         statistics resources currently in use."
    ::= { tmnxFPEntry 20 }

tmnxFPInitExtractDropPrioMode    OBJECT-TYPE
    SYNTAX      INTEGER {
        uniform    (1),
        l3Classify (2)
    }
    MAX-ACCESS  read-write
    STATUS      current
    DESCRIPTION
        "The value of tmnxFPInitExtractDropPrioMode specifies the scheme used
         to select the initial drop priority of extracted control plane
         traffic. The initial drop priority of extracted packets can either be
         of low or high priority. The drop priority can be subsequently altered
         by mechanisms such as cpu-protection. High priority traffic receives
         preferential treatment in control plane congestion situations at the
         expense of low priority traffic.

         Values:
             uniform    (1) - initialize the drop priority of all extracted
                              control traffic as high priority
             l3Classify (2) - initialize the drop priority of all layer 3
                              extracted control traffic based on the QoS
                              classification of the packets
                            - this is useful in networks where the DSCP and EXP
                              markings can be trusted as the primary method to
                              distinguish, protect and isolate good terminating
                              protocol traffic from unknown or potentially
                              harmful protocol traffic"
    DEFVAL      { uniform }
    ::= { tmnxFPEntry 21 }

tmnxFPEgrHsPoolPolicy            OBJECT-TYPE
    SYNTAX      TNamedItemOrEmpty
    MAX-ACCESS  read-write
    STATUS      current
    DESCRIPTION
        "The value of tmnxFPEgrHsPoolPolicy specifies the egress QoS High Scale
         scheduler policy for this port. This object must correspond to the
         index of a row in TIMETRA-QOS-MIB::tHsPoolPolicyTable, otherwise an
         'inconsistentValue' error will be returned.

         When this forwarding plane is on non-High Scale card type, the value
         for tmnxFPEgrHsPoolPolicy will be ignored. If this forwarding plane is
         on High Scale card type, the default for this object will be the
         string 'default'."
    DEFVAL      { "" }
    ::= { tmnxFPEntry 22 }

tmnxFPEgrHsFixedHighThreshDelta  OBJECT-TYPE
    SYNTAX      Integer32 (-1 | 0..65536)
    MAX-ACCESS  read-write
    STATUS      current
    DESCRIPTION
        "The value of tmnxFPEgrHsFixedHighThreshDelta specifies the egress QoS
         High threshold delta for this port. This object must correspond."
    DEFVAL      { -1 }
    ::= { tmnxFPEntry 23 }

tmnxFPMcPathMgmtPriInUseBw       OBJECT-TYPE
    SYNTAX      Gauge32
    UNITS       "Kbps"
    MAX-ACCESS  read-only
    STATUS      current
    DESCRIPTION
        "The value of tmnxFPMcPathMgmtPriInUseBw indicates the in use ingress
         multicast bandwidth for the primary forwarding path."
    ::= { tmnxFPEntry 24 }

tmnxFPMcPathMgmtSecInUseBw       OBJECT-TYPE
    SYNTAX      Gauge32
    UNITS       "Kbps"
    MAX-ACCESS  read-only
    STATUS      current
    DESCRIPTION
        "The value of tmnxFPMcPathMgmtSecInUseBw indicates the in use ingress
         multicast bandwidth for the secondary forwarding path."
    ::= { tmnxFPEntry 25 }

tmnxFPMcPathMgmtBlkHoleInUseBw   OBJECT-TYPE
    SYNTAX      Gauge32
    UNITS       "Kbps"
    MAX-ACCESS  read-only
    STATUS      current
    DESCRIPTION
        "The value of tmnxFPMcPathMgmtBlkHoleInUseBw indicates the bandwidth of
         the ingress multicast traffic that is being black holed on the FP."
    ::= { tmnxFPEntry 26 }

tmnxFPGeneration                 OBJECT-TYPE
    SYNTAX      TmnxFpGeneration
    MAX-ACCESS  read-only
    STATUS      current
    DESCRIPTION
        "The value of tmnxFPGeneration indicates the generation of the FP
         network processor."
    ::= { tmnxFPEntry 27 }

tmnxFPAccIngQGrpTableLastChgd    OBJECT-TYPE
    SYNTAX      TimeStamp
    MAX-ACCESS  read-only
    STATUS      current
    DESCRIPTION
        "The value of tmnxFPAccIngQGrpTableLastChgd indicates the timestamp of
         last change to the tmnxFPAccIngQGrpTable."
    ::= { tmnxCardObjs 22 }

tmnxFPAccIngQGrpTable            OBJECT-TYPE
    SYNTAX      SEQUENCE OF TmnxFPAccIngQGrpEntry
    MAX-ACCESS  not-accessible
    STATUS      current
    DESCRIPTION
        "The value of tmnxFPAccIngQGrpTable defines access Ingress Queue Group
         Table for providing, via SNMP, the capability of defining the
         forwarding-plane specific queue groups from the queue-groups existing
         in the TIMETRA-QOS-MIB::tQosIngQGroupTable."
    ::= { tmnxCardObjs 23 }

tmnxFPAccIngQGrpEntry            OBJECT-TYPE
    SYNTAX      TmnxFPAccIngQGrpEntry
    MAX-ACCESS  not-accessible
    STATUS      current
    DESCRIPTION
        "The value of tmnxFPAccIngQGrpEntry defines an entry in the
         tmnxFPAccIngQGrpTable.

         Entries are created/deleted in this table by SNMP sets to
         tmnxFPAccIngQGrpRowStatus."
    INDEX       {
        tmnxChassisIndex,
        tmnxCardSlotNum,
        tmnxFPNum,
        tmnxFPAccIngQGrpName,
        tmnxFPAccIngQGrpInstanceId
    }
    ::= { tmnxFPAccIngQGrpTable 1 }

TmnxFPAccIngQGrpEntry            ::= SEQUENCE
{
    tmnxFPAccIngQGrpName             TNamedItem,
    tmnxFPAccIngQGrpInstanceId       Unsigned32,
    tmnxFPAccIngQGrpRowStatus        RowStatus,
    tmnxFPAccIngQGrpLastChgd         TimeStamp,
    tmnxFPAccIngQGrpAcctgPolId       Unsigned32,
    tmnxFPAccIngQGrpCollectStats     TruthValue,
    tmnxFPAccIngQGrpDescr            TItemDescription,
    tmnxFPAccIngQGrpPolicerPol       TNamedItemOrEmpty
}

tmnxFPAccIngQGrpName             OBJECT-TYPE
    SYNTAX      TNamedItem
    MAX-ACCESS  not-accessible
    STATUS      current
    DESCRIPTION
        "The value of tmnxFPAccIngQGrpName defines the forwarding-plane Ingress
         Queue Group name.  It, along with tmnxFPAccIngQGrpInstanceId uniquely
         identifies a forwarding-plane ingress queue group in the managed
         system."
    ::= { tmnxFPAccIngQGrpEntry 1 }

tmnxFPAccIngQGrpInstanceId       OBJECT-TYPE
    SYNTAX      Unsigned32 (1..65535)
    MAX-ACCESS  not-accessible
    STATUS      current
    DESCRIPTION
        "The value of tmnxFPAccIngQGrpInstanceId defines the unique instance of
         the forwarding-plane ingress Queue Group. It, along with
         tmnxFPAccIngQGrpName, uniquely identifies a forwarding-plane ingress
         queue group in the managed system."
    ::= { tmnxFPAccIngQGrpEntry 2 }

tmnxFPAccIngQGrpRowStatus        OBJECT-TYPE
    SYNTAX      RowStatus
    MAX-ACCESS  read-create
    STATUS      current
    DESCRIPTION
        "The value of tmnxFPAccIngQGrpRowStatus allows entries to be created
         and deleted in the tmnxFPAccIngQGrpTable.

         The creation of an entry in this table will succeed only if the
         queue-group being created exists in
         TIMETRA-QOS-MIB::tQosIngQGroupTable."
    REFERENCE
        "See definition of RowStatus in RFC 2579, 'Textual Conventions for
         SMIv2.'"
    ::= { tmnxFPAccIngQGrpEntry 3 }

tmnxFPAccIngQGrpLastChgd         OBJECT-TYPE
    SYNTAX      TimeStamp
    MAX-ACCESS  read-only
    STATUS      current
    DESCRIPTION
        "The value of tmnxFPAccIngQGrpLastChgd indicates the value of sysUpTime
         when the queue entry was last modified."
    ::= { tmnxFPAccIngQGrpEntry 4 }

tmnxFPAccIngQGrpAcctgPolId       OBJECT-TYPE
    SYNTAX      Unsigned32 (0..99)
    MAX-ACCESS  read-create
    STATUS      current
    DESCRIPTION
        "The value of tmnxFPAccIngQGrpAcctgPolId specifies the
         accounting-policy to be used with this forwarding-plane ingress
         queue-group.

         A non-zero value indicates the tmnxLogApPolicyId index identifying the
         policy entry in the tmnxLogApTable from the TIMETRA-LOG-MIB which is
         associated with this queue-group.

         The value zero indicates that the agent should use the default
         accounting policy, if one exists."
    DEFVAL      { 0 }
    ::= { tmnxFPAccIngQGrpEntry 5 }

tmnxFPAccIngQGrpCollectStats     OBJECT-TYPE
    SYNTAX      TruthValue
    MAX-ACCESS  read-create
    STATUS      current
    DESCRIPTION
        "The value of tmnxFPAccIngQGrpCollectStats specifies whether statistics
         should be collected on this forwarding-plane ingress queue-group."
    DEFVAL      { false }
    ::= { tmnxFPAccIngQGrpEntry 6 }

tmnxFPAccIngQGrpDescr            OBJECT-TYPE
    SYNTAX      TItemDescription
    MAX-ACCESS  read-create
    STATUS      current
    DESCRIPTION
        "The value of tmnxFPAccIngQGrpDescr specifies the description for this
         forwarding-plane queue-group."
    DEFVAL      { "" }
    ::= { tmnxFPAccIngQGrpEntry 7 }

tmnxFPAccIngQGrpPolicerPol       OBJECT-TYPE
    SYNTAX      TNamedItemOrEmpty
    MAX-ACCESS  read-create
    STATUS      current
    DESCRIPTION
        "The value of tmnxFPAccIngQGrpPolicerPol specifies the name of the
         policer control policy to be used with this forwarding-plane ingress
         queue-group."
    DEFVAL      { "" }
    ::= { tmnxFPAccIngQGrpEntry 8 }

tmnxFPNetIngQGrpTableLastChgd    OBJECT-TYPE
    SYNTAX      TimeStamp
    MAX-ACCESS  read-only
    STATUS      current
    DESCRIPTION
        "The value of tmnxFPNetIngQGrpTableLastChgd indicates the timestamp of
         last change to the tmnxFPNetIngQGrpTable."
    ::= { tmnxCardObjs 24 }

tmnxFPNetIngQGrpTable            OBJECT-TYPE
    SYNTAX      SEQUENCE OF TmnxFPNetIngQGrpEntry
    MAX-ACCESS  not-accessible
    STATUS      current
    DESCRIPTION
        "The value of tmnxFPNetIngQGrpTable defines access Ingress Queue Group
         Table for providing, via SNMP, the capability of defining the
         forwarding-plane specific queue groups from the queue-groups existing
         in the TIMETRA-QOS-MIB::tQosIngQGroupTable."
    ::= { tmnxCardObjs 25 }

tmnxFPNetIngQGrpEntry            OBJECT-TYPE
    SYNTAX      TmnxFPNetIngQGrpEntry
    MAX-ACCESS  not-accessible
    STATUS      current
    DESCRIPTION
        "The value of tmnxFPNetIngQGrpEntry defines an entry in the
         tmnxFPNetIngQGrpTable.

         Entries are created/deleted in this table by SNMP sets to
         tmnxFPNetIngQGrpRowStatus."
    INDEX       {
        tmnxChassisIndex,
        tmnxCardSlotNum,
        tmnxFPNum,
        tmnxFPNetIngQGrpName,
        tmnxFPNetIngQGrpInstanceId
    }
    ::= { tmnxFPNetIngQGrpTable 1 }

TmnxFPNetIngQGrpEntry            ::= SEQUENCE
{
    tmnxFPNetIngQGrpName             TNamedItem,
    tmnxFPNetIngQGrpInstanceId       Unsigned32,
    tmnxFPNetIngQGrpRowStatus        RowStatus,
    tmnxFPNetIngQGrpLastChgd         TimeStamp,
    tmnxFPNetIngQGrpAcctgPolId       Unsigned32,
    tmnxFPNetIngQGrpCollectStats     TruthValue,
    tmnxFPNetIngQGrpDescr            TItemDescription,
    tmnxFPNetIngQGrpPolicerPol       TNamedItemOrEmpty
}

tmnxFPNetIngQGrpName             OBJECT-TYPE
    SYNTAX      TNamedItem
    MAX-ACCESS  not-accessible
    STATUS      current
    DESCRIPTION
        "The value of tmnxFPNetIngQGrpName defines the forwarding-plane Ingress
         Queue Group name.  It, along with tmnxFPNetIngQGrpInstanceId uniquely
         identifies a forwarding-plane ingress queue group in the managed
         system."
    ::= { tmnxFPNetIngQGrpEntry 1 }

tmnxFPNetIngQGrpInstanceId       OBJECT-TYPE
    SYNTAX      Unsigned32 (1..65535)
    MAX-ACCESS  not-accessible
    STATUS      current
    DESCRIPTION
        "The value of tmnxFPNetIngQGrpInstanceId defines the unique instance of
         the forwarding-plane ingress Queue Group. It, along with
         tmnxFPNetIngQGrpName, uniquely identifies a forwarding-plane ingress
         queue group in the managed system."
    ::= { tmnxFPNetIngQGrpEntry 2 }

tmnxFPNetIngQGrpRowStatus        OBJECT-TYPE
    SYNTAX      RowStatus
    MAX-ACCESS  read-create
    STATUS      current
    DESCRIPTION
        "The value of tmnxFPNetIngQGrpRowStatus allows entries to be created
         and deleted in the tmnxFPNetIngQGrpTable.

         The creation of an entry in this table will succeed only if the
         queue-group being created exists in
         TIMETRA-QOS-MIB::tQosIngQGroupTable."
    REFERENCE
        "See definition of RowStatus in RFC 2579, 'Textual Conventions for
         SMIv2.'"
    ::= { tmnxFPNetIngQGrpEntry 3 }

tmnxFPNetIngQGrpLastChgd         OBJECT-TYPE
    SYNTAX      TimeStamp
    MAX-ACCESS  read-only
    STATUS      current
    DESCRIPTION
        "The value of tmnxFPNetIngQGrpLastChgd indicates the value of sysUpTime
         when the queue entry was last modified."
    ::= { tmnxFPNetIngQGrpEntry 4 }

tmnxFPNetIngQGrpAcctgPolId       OBJECT-TYPE
    SYNTAX      Unsigned32 (0..99)
    MAX-ACCESS  read-create
    STATUS      current
    DESCRIPTION
        "The value of tmnxFPNetIngQGrpAcctgPolId specifies the
         accounting-policy to be used with this forwarding-plane ingress
         queue-group.

         A non-zero value indicates the tmnxLogApPolicyId index identifying the
         policy entry in the tmnxLogApTable from the TIMETRA-LOG-MIB which is
         associated with this queue-group.

         The value zero indicates that the agent should use the default
         accounting policy, if one exists."
    DEFVAL      { 0 }
    ::= { tmnxFPNetIngQGrpEntry 5 }

tmnxFPNetIngQGrpCollectStats     OBJECT-TYPE
    SYNTAX      TruthValue
    MAX-ACCESS  read-create
    STATUS      current
    DESCRIPTION
        "The value of tmnxFPNetIngQGrpCollectStats specifies whether statistics
         should be collected on this forwarding-plane ingress queue-group."
    DEFVAL      { false }
    ::= { tmnxFPNetIngQGrpEntry 6 }

tmnxFPNetIngQGrpDescr            OBJECT-TYPE
    SYNTAX      TItemDescription
    MAX-ACCESS  read-create
    STATUS      current
    DESCRIPTION
        "The value of tmnxFPNetIngQGrpDescr specifies the description for this
         forwarding-plane queue-group."
    DEFVAL      { "" }
    ::= { tmnxFPNetIngQGrpEntry 7 }

tmnxFPNetIngQGrpPolicerPol       OBJECT-TYPE
    SYNTAX      TNamedItemOrEmpty
    MAX-ACCESS  read-create
    STATUS      current
    DESCRIPTION
        "The value of tmnxFPNetIngQGrpPolicerPol specifies the name of the
         policer control policy to be used with this forwarding-plane ingress
         queue-group."
    DEFVAL      { "" }
    ::= { tmnxFPNetIngQGrpEntry 8 }

tmnxFabricTypeTable              OBJECT-TYPE
    SYNTAX      SEQUENCE OF TmnxFabricTypeEntry
    MAX-ACCESS  not-accessible
    STATUS      current
    DESCRIPTION
        "The fabric type table has an entry for each Nokia SROS series Fabric
         card type."
    ::= { tmnxCardObjs 26 }

tmnxFabricTypeEntry              OBJECT-TYPE
    SYNTAX      TmnxFabricTypeEntry
    MAX-ACCESS  not-accessible
    STATUS      current
    DESCRIPTION
        "Each row entry represents an Nokia SROS series Fabric card. Rows in
         this table are created by the agent at initialization and cannot be
         created or destroyed by SNMP Get or Set requests."
    INDEX       { tmnxFabricTypeIndex }
    ::= { tmnxFabricTypeTable 1 }

TmnxFabricTypeEntry              ::= SEQUENCE
{
    tmnxFabricTypeIndex              TmnxFabricType,
    tmnxFabricTypeName               TNamedItemOrEmpty,
    tmnxFabricTypeDescription        TItemDescription,
    tmnxFabricTypeStatus             TruthValue
}

tmnxFabricTypeIndex              OBJECT-TYPE
    SYNTAX      TmnxFabricType
    MAX-ACCESS  not-accessible
    STATUS      current
    DESCRIPTION
        "The unique index value which identifies this type of Nokia SROS series
         Fabric card type."
    ::= { tmnxFabricTypeEntry 1 }

tmnxFabricTypeName               OBJECT-TYPE
    SYNTAX      TNamedItemOrEmpty
    MAX-ACCESS  read-only
    STATUS      current
    DESCRIPTION
        "The administrative name that identifies this type of Nokia
         SROS series Fabric card.  This name string may be used in CLI
         commands to specify a particular fabric card type."
    ::= { tmnxFabricTypeEntry 2 }

tmnxFabricTypeDescription        OBJECT-TYPE
    SYNTAX      TItemDescription
    MAX-ACCESS  read-only
    STATUS      current
    DESCRIPTION
        "A detailed description of this Nokia SROS series Fabric card."
    ::= { tmnxFabricTypeEntry 3 }

tmnxFabricTypeStatus             OBJECT-TYPE
    SYNTAX      TruthValue
    MAX-ACCESS  read-only
    STATUS      current
    DESCRIPTION
        "When tmnxFabricTypeStatus has a value of 'true' it
         indicates that this Fabric is supported in this revision of the
         management software.  When it has a value of 'false' there is no
         support."
    ::= { tmnxFabricTypeEntry 4 }

tmnxFPNetIngQGrpPStatTable       OBJECT-TYPE
    SYNTAX      SEQUENCE OF TmnxFPNetIngQGrpPStatEntry
    MAX-ACCESS  not-accessible
    STATUS      current
    DESCRIPTION
        "The tmnxFPNetIngQGrpPStatTable contains forwarding-plane ingress QoS
         queue group policer statistics on network side."
    ::= { tmnxCardObjs 27 }

tmnxFPNetIngQGrpPStatEntry       OBJECT-TYPE
    SYNTAX      TmnxFPNetIngQGrpPStatEntry
    MAX-ACCESS  not-accessible
    STATUS      current
    DESCRIPTION
        "The value of tmnxFPNetIngQGrpPStatEntry defines an entry in the
         tmnxFPNetIngQGrpPStatTable. It represents statistics about a specific
         QoS ingress queue group policer."
    INDEX       {
        tmnxChassisIndex,
        tmnxCardSlotNum,
        tmnxFPNum,
        tmnxFPNetIngQGrpName,
        tmnxFPNetIngQGrpInstanceId,
        tmnxFPNetIngQGrpPStatPolicerId
    }
    ::= { tmnxFPNetIngQGrpPStatTable 1 }

TmnxFPNetIngQGrpPStatEntry       ::= SEQUENCE
{
    tmnxFPNetIngQGrpPStatPolicerId   TIngPolicerId,
    tmnxFPNetIngQGrpPStatMode        TmnxIngPolicerStatMode,
    tmnxFPNetIngQgPStOffHPrioPkts    Counter64,
    tmnxFPNetIngQgPStOffHPrioPktsL   Counter32,
    tmnxFPNetIngQgPStOffHPrioPktsH   Counter32,
    tmnxFPNetIngQgPStDrpHPrioPkts    Counter64,
    tmnxFPNetIngQgPStDrpHPrioPktsL   Counter32,
    tmnxFPNetIngQgPStDrpHPrioPktsH   Counter32,
    tmnxFPNetIngQgPStOffLPrioPkts    Counter64,
    tmnxFPNetIngQgPStOffLPrioPktsL   Counter32,
    tmnxFPNetIngQgPStOffLPrioPktsH   Counter32,
    tmnxFPNetIngQgPStDrpLPrioPkts    Counter64,
    tmnxFPNetIngQgPStDrpLPrioPktsL   Counter32,
    tmnxFPNetIngQgPStDrpLPrioPktsH   Counter32,
    tmnxFPNetIngQgPStOffHPrioOcts    Counter64,
    tmnxFPNetIngQgPStOffHPrioOctsL   Counter32,
    tmnxFPNetIngQgPStOffHPrioOctsH   Counter32,
    tmnxFPNetIngQgPStDrpHPrioOcts    Counter64,
    tmnxFPNetIngQgPStDrpHPrioOctsL   Counter32,
    tmnxFPNetIngQgPStDrpHPrioOctsH   Counter32,
    tmnxFPNetIngQgPStOffLPrioOcts    Counter64,
    tmnxFPNetIngQgPStOffLPrioOctsL   Counter32,
    tmnxFPNetIngQgPStOffLPrioOctsH   Counter32,
    tmnxFPNetIngQgPStDrpLPrioOcts    Counter64,
    tmnxFPNetIngQgPStDrpLPrioOctsL   Counter32,
    tmnxFPNetIngQgPStDrpLPrioOctsH   Counter32,
    tmnxFPNetIngQgPStFwdInProfPkts   Counter64,
    tmnxFPNetIngQgPStFwdInProfPktsL  Counter32,
    tmnxFPNetIngQgPStFwdInProfPktsH  Counter32,
    tmnxFPNetIngQgPStFwdOutProfPkts  Counter64,
    tmnxFPNetIngQgPStFwdOutProfPktsL Counter32,
    tmnxFPNetIngQgPStFwdOutProfPktsH Counter32,
    tmnxFPNetIngQgPStFwdInProfOcts   Counter64,
    tmnxFPNetIngQgPStFwdInProfOctsL  Counter32,
    tmnxFPNetIngQgPStFwdInProfOctsH  Counter32,
    tmnxFPNetIngQgPStFwdOutProfOcts  Counter64,
    tmnxFPNetIngQgPStFwdOutProfOctsL Counter32,
    tmnxFPNetIngQgPStFwdOutProfOctsH Counter32,
    tmnxFPNetIngQgPStUncolPktsOff    Counter64,
    tmnxFPNetIngQgPStUncolPktsOffL   Counter32,
    tmnxFPNetIngQgPStUncolPktsOffH   Counter32,
    tmnxFPNetIngQgPStUncolOctsOff    Counter64,
    tmnxFPNetIngQgPStUncolOctsOffL   Counter32,
    tmnxFPNetIngQgPStUncolOctsOffH   Counter32
}

tmnxFPNetIngQGrpPStatPolicerId   OBJECT-TYPE
    SYNTAX      TIngPolicerId
    MAX-ACCESS  not-accessible
    STATUS      current
    DESCRIPTION
        "The value of tmnxFPNetIngQGrpPStatPolicerId specifies the index of the
         ingress QoS policer of this forwarding-plane queue group on network."
    ::= { tmnxFPNetIngQGrpPStatEntry 1 }

tmnxFPNetIngQGrpPStatMode        OBJECT-TYPE
    SYNTAX      TmnxIngPolicerStatMode
    MAX-ACCESS  read-only
    STATUS      current
    DESCRIPTION
        "The value of tmnxFPNetIngQGrpPStatMode indicates the stat mode used by
         this policer."
    ::= { tmnxFPNetIngQGrpPStatEntry 2 }

tmnxFPNetIngQgPStOffHPrioPkts    OBJECT-TYPE
    SYNTAX      Counter64
    MAX-ACCESS  read-only
    STATUS      current
    DESCRIPTION
        "The value of tmnxFPNetIngQgPStOffHPrioPkts indicates the number of
         high priority packets, as determined by the ingress queue group
         policer, offered by the Pchip to the Qchip."
    ::= { tmnxFPNetIngQGrpPStatEntry 3 }

tmnxFPNetIngQgPStOffHPrioPktsL   OBJECT-TYPE
    SYNTAX      Counter32
    MAX-ACCESS  read-only
    STATUS      current
    DESCRIPTION
        "The value of tmnxFPNetIngQgPStOffHPrioPktsL indicates the lower 32
         bits of tmnxFPNetIngQgPStOffHPrioPkts."
    ::= { tmnxFPNetIngQGrpPStatEntry 4 }

tmnxFPNetIngQgPStOffHPrioPktsH   OBJECT-TYPE
    SYNTAX      Counter32
    MAX-ACCESS  read-only
    STATUS      current
    DESCRIPTION
        "The value of tmnxFPNetIngQgPStOffHPrioPktsH indicates the upper 32
         bits of tmnxFPNetIngQgPStOffHPrioPkts."
    ::= { tmnxFPNetIngQGrpPStatEntry 5 }

tmnxFPNetIngQgPStDrpHPrioPkts    OBJECT-TYPE
    SYNTAX      Counter64
    MAX-ACCESS  read-only
    STATUS      current
    DESCRIPTION
        "The value of tmnxFPNetIngQgPStDrpHPrioPkts indicates the number of
         high priority packets, as determined by the ingress queue group
         policer, dropped by the Pchip due to: MBS exceeded, buffer pool limit
         exceeded, etc."
    ::= { tmnxFPNetIngQGrpPStatEntry 6 }

tmnxFPNetIngQgPStDrpHPrioPktsL   OBJECT-TYPE
    SYNTAX      Counter32
    MAX-ACCESS  read-only
    STATUS      current
    DESCRIPTION
        "The value of tmnxFPNetIngQgPStDrpHPrioPktsL indicates the lower 32
         bits of tmnxFPNetIngQgPStDrpHPrioPkts."
    ::= { tmnxFPNetIngQGrpPStatEntry 7 }

tmnxFPNetIngQgPStDrpHPrioPktsH   OBJECT-TYPE
    SYNTAX      Counter32
    MAX-ACCESS  read-only
    STATUS      current
    DESCRIPTION
        "The value of tmnxFPNetIngQgPStDrpHPrioPktsH indicates the upper 32
         bits of tmnxFPNetIngQgPStDrpHPrioPkts."
    ::= { tmnxFPNetIngQGrpPStatEntry 8 }

tmnxFPNetIngQgPStOffLPrioPkts    OBJECT-TYPE
    SYNTAX      Counter64
    MAX-ACCESS  read-only
    STATUS      current
    DESCRIPTION
        "The value of tmnxFPNetIngQgPStOffLPrioPkts indicates the number of low
         priority packets, as determined by the ingress queue group policer,
         offered by the Pchip to the Qchip."
    ::= { tmnxFPNetIngQGrpPStatEntry 9 }

tmnxFPNetIngQgPStOffLPrioPktsL   OBJECT-TYPE
    SYNTAX      Counter32
    MAX-ACCESS  read-only
    STATUS      current
    DESCRIPTION
        "The value of tmnxFPNetIngQgPStOffLPrioPktsL indicates the lower 32
         bits of tmnxFPNetIngQgPStOffLPrioPkts."
    ::= { tmnxFPNetIngQGrpPStatEntry 10 }

tmnxFPNetIngQgPStOffLPrioPktsH   OBJECT-TYPE
    SYNTAX      Counter32
    MAX-ACCESS  read-only
    STATUS      current
    DESCRIPTION
        "The value of tmnxFPNetIngQgPStOffLPrioPktsH indicates the upper 32
         bits of tmnxFPNetIngQgPStOffLPrioPkts."
    ::= { tmnxFPNetIngQGrpPStatEntry 11 }

tmnxFPNetIngQgPStDrpLPrioPkts    OBJECT-TYPE
    SYNTAX      Counter64
    MAX-ACCESS  read-only
    STATUS      current
    DESCRIPTION
        "The value of tmnxFPNetIngQgPStDrpLPrioPkts indicates the number of low
         priority packets, as determined by the ingress queue group policer,
         dropped by the Pchip due to: MBS exceeded, buffer pool limit exceeded,
         etc."
    ::= { tmnxFPNetIngQGrpPStatEntry 12 }

tmnxFPNetIngQgPStDrpLPrioPktsL   OBJECT-TYPE
    SYNTAX      Counter32
    MAX-ACCESS  read-only
    STATUS      current
    DESCRIPTION
        "The value of tmnxFPNetIngQgPStDrpLPrioPktsL indicates the lower 32
         bits of tmnxFPNetIngQgPStDrpLPrioPkts."
    ::= { tmnxFPNetIngQGrpPStatEntry 13 }

tmnxFPNetIngQgPStDrpLPrioPktsH   OBJECT-TYPE
    SYNTAX      Counter32
    MAX-ACCESS  read-only
    STATUS      current
    DESCRIPTION
        "The value of tmnxFPNetIngQgPStDrpLPrioPktsH indicates the upper 32
         bits of tmnxFPNetIngQgPStDrpLPrioPkts."
    ::= { tmnxFPNetIngQGrpPStatEntry 14 }

tmnxFPNetIngQgPStOffHPrioOcts    OBJECT-TYPE
    SYNTAX      Counter64
    MAX-ACCESS  read-only
    STATUS      current
    DESCRIPTION
        "The value of tmnxFPNetIngQgPStOffHPrioOcts indicates the number of
         high priority octets, as determined by the ingress queue group
         policer, offered by the Pchip to the Qchip."
    ::= { tmnxFPNetIngQGrpPStatEntry 15 }

tmnxFPNetIngQgPStOffHPrioOctsL   OBJECT-TYPE
    SYNTAX      Counter32
    MAX-ACCESS  read-only
    STATUS      current
    DESCRIPTION
        "The value of tmnxFPNetIngQgPStOffHPrioOctsL indicates the lower 32
         bits of tmnxFPNetIngQgPStOffHPrioOcts."
    ::= { tmnxFPNetIngQGrpPStatEntry 16 }

tmnxFPNetIngQgPStOffHPrioOctsH   OBJECT-TYPE
    SYNTAX      Counter32
    MAX-ACCESS  read-only
    STATUS      current
    DESCRIPTION
        "The value of tmnxFPNetIngQgPStOffHPrioOctsH indicates the upper 32
         bits of tmnxFPNetIngQgPStOffHPrioOcts."
    ::= { tmnxFPNetIngQGrpPStatEntry 17 }

tmnxFPNetIngQgPStDrpHPrioOcts    OBJECT-TYPE
    SYNTAX      Counter64
    MAX-ACCESS  read-only
    STATUS      current
    DESCRIPTION
        "The value of tmnxFPNetIngQgPStDrpHPrioOcts indicates the number of
         high priority octets, as determined by the ingress queue group
         policer, dropped by the Pchip due to: MBS exceeded, buffer pool limit
         exceeded, etc."
    ::= { tmnxFPNetIngQGrpPStatEntry 18 }

tmnxFPNetIngQgPStDrpHPrioOctsL   OBJECT-TYPE
    SYNTAX      Counter32
    MAX-ACCESS  read-only
    STATUS      current
    DESCRIPTION
        "The value of tmnxFPNetIngQgPStDrpHPrioOctsL indicates the lower 32
         bits of tmnxFPNetIngQgPStDrpHPrioOcts."
    ::= { tmnxFPNetIngQGrpPStatEntry 19 }

tmnxFPNetIngQgPStDrpHPrioOctsH   OBJECT-TYPE
    SYNTAX      Counter32
    MAX-ACCESS  read-only
    STATUS      current
    DESCRIPTION
        "The value of tmnxFPNetIngQgPStDrpHPrioOctsH indicates the upper 32
         bits of tmnxFPNetIngQgPStDrpHPrioOcts."
    ::= { tmnxFPNetIngQGrpPStatEntry 20 }

tmnxFPNetIngQgPStOffLPrioOcts    OBJECT-TYPE
    SYNTAX      Counter64
    MAX-ACCESS  read-only
    STATUS      current
    DESCRIPTION
        "The value of tmnxFPNetIngQgPStOffLPrioOcts indicates the number of low
         priority octets, as determined by the ingress queue group policer,
         offered by the Pchip to the Pchip."
    ::= { tmnxFPNetIngQGrpPStatEntry 21 }

tmnxFPNetIngQgPStOffLPrioOctsL   OBJECT-TYPE
    SYNTAX      Counter32
    MAX-ACCESS  read-only
    STATUS      current
    DESCRIPTION
        "The value of tmnxFPNetIngQgPStOffLPrioOctsL indicates the lower 32
         bits of tmnxFPNetIngQgPStOffLPrioOcts."
    ::= { tmnxFPNetIngQGrpPStatEntry 22 }

tmnxFPNetIngQgPStOffLPrioOctsH   OBJECT-TYPE
    SYNTAX      Counter32
    MAX-ACCESS  read-only
    STATUS      current
    DESCRIPTION
        "The value of tmnxFPNetIngQgPStOffLPrioOctsH indicates the upper 32
         bits of tmnxFPNetIngQgPStOffLPrioOcts."
    ::= { tmnxFPNetIngQGrpPStatEntry 23 }

tmnxFPNetIngQgPStDrpLPrioOcts    OBJECT-TYPE
    SYNTAX      Counter64
    MAX-ACCESS  read-only
    STATUS      current
    DESCRIPTION
        "The value of tmnxFPNetIngQgPStDrpLPrioOcts indicates the number of low
         priority octets, as determined by the ingress queue group policer,
         dropped by the Pchip due to: MBS exceeded, buffer pool limit exceeded,
         etc."
    ::= { tmnxFPNetIngQGrpPStatEntry 24 }

tmnxFPNetIngQgPStDrpLPrioOctsL   OBJECT-TYPE
    SYNTAX      Counter32
    MAX-ACCESS  read-only
    STATUS      current
    DESCRIPTION
        "The value of tmnxFPNetIngQgPStDrpLPrioOctsL indicates the lower 32
         bits of tmnxFPNetIngQgPStDrpLPrioOcts."
    ::= { tmnxFPNetIngQGrpPStatEntry 25 }

tmnxFPNetIngQgPStDrpLPrioOctsH   OBJECT-TYPE
    SYNTAX      Counter32
    MAX-ACCESS  read-only
    STATUS      current
    DESCRIPTION
        "The value of tmnxFPNetIngQgPStDrpLPrioOctsH indicates the upper 32
         bits of tmnxFPNetIngQgPStDrpLPrioOcts."
    ::= { tmnxFPNetIngQGrpPStatEntry 26 }

tmnxFPNetIngQgPStFwdInProfPkts   OBJECT-TYPE
    SYNTAX      Counter64
    MAX-ACCESS  read-only
    STATUS      current
    DESCRIPTION
        "The value of tmnxFPNetIngQgPStFwdInProfPkts indicates the number of
         in-profile packets (rate below CIR) forwarded by the ingress Pchip."
    ::= { tmnxFPNetIngQGrpPStatEntry 27 }

tmnxFPNetIngQgPStFwdInProfPktsL  OBJECT-TYPE
    SYNTAX      Counter32
    MAX-ACCESS  read-only
    STATUS      current
    DESCRIPTION
        "The value of tmnxFPNetIngQgPStFwdInProfPktsL indicates the lower 32
         bits of tmnxFPNetIngQgPStFwdInProfPkts."
    ::= { tmnxFPNetIngQGrpPStatEntry 28 }

tmnxFPNetIngQgPStFwdInProfPktsH  OBJECT-TYPE
    SYNTAX      Counter32
    MAX-ACCESS  read-only
    STATUS      current
    DESCRIPTION
        "The value of tmnxFPNetIngQgPStFwdInProfPktsH indicates the upper 32
         bits of tmnxFPNetIngQgPStFwdInProfPkts."
    ::= { tmnxFPNetIngQGrpPStatEntry 29 }

tmnxFPNetIngQgPStFwdOutProfPkts  OBJECT-TYPE
    SYNTAX      Counter64
    MAX-ACCESS  read-only
    STATUS      current
    DESCRIPTION
        "The value of tmnxFPNetIngQgPStFwdOutProfPkts indicates the number of
         out-of-profile packets (rate above CIR) forwarded by the ingress
         Pchip."
    ::= { tmnxFPNetIngQGrpPStatEntry 30 }

tmnxFPNetIngQgPStFwdOutProfPktsL OBJECT-TYPE
    SYNTAX      Counter32
    MAX-ACCESS  read-only
    STATUS      current
    DESCRIPTION
        "The value of tmnxFPNetIngQgPStFwdOutProfPktsL indicates the lower 32
         bits of tmnxFPNetIngQgPStFwdOutProfPkts."
    ::= { tmnxFPNetIngQGrpPStatEntry 31 }

tmnxFPNetIngQgPStFwdOutProfPktsH OBJECT-TYPE
    SYNTAX      Counter32
    MAX-ACCESS  read-only
    STATUS      current
    DESCRIPTION
        "The value of tmnxFPNetIngQgPStFwdOutProfPktsH indicates the upper 32
         bits of tmnxFPNetIngQgPStFwdOutProfPkts."
    ::= { tmnxFPNetIngQGrpPStatEntry 32 }

tmnxFPNetIngQgPStFwdInProfOcts   OBJECT-TYPE
    SYNTAX      Counter64
    MAX-ACCESS  read-only
    STATUS      current
    DESCRIPTION
        "The value of tmnxFPNetIngQgPStFwdInProfOcts indicates the number of
         in-profile octets (rate below CIR) forwarded by the ingress Pchip."
    ::= { tmnxFPNetIngQGrpPStatEntry 33 }

tmnxFPNetIngQgPStFwdInProfOctsL  OBJECT-TYPE
    SYNTAX      Counter32
    MAX-ACCESS  read-only
    STATUS      current
    DESCRIPTION
        "The value of tmnxFPNetIngQgPStFwdInProfOctsL indicates the lower 32
         bits of tmnxFPNetIngQgPStFwdInProfOcts."
    ::= { tmnxFPNetIngQGrpPStatEntry 34 }

tmnxFPNetIngQgPStFwdInProfOctsH  OBJECT-TYPE
    SYNTAX      Counter32
    MAX-ACCESS  read-only
    STATUS      current
    DESCRIPTION
        "The value of tmnxFPNetIngQgPStFwdInProfOctsH indicates the upper 32
         bits of tmnxFPNetIngQgPStFwdInProfOcts."
    ::= { tmnxFPNetIngQGrpPStatEntry 35 }

tmnxFPNetIngQgPStFwdOutProfOcts  OBJECT-TYPE
    SYNTAX      Counter64
    MAX-ACCESS  read-only
    STATUS      current
    DESCRIPTION
        "The value of tmnxFPNetIngQgPStFwdOutProfOcts indicates the number of
         out-of-profile octets (rate above CIR) forwarded by the ingress Pchip."
    ::= { tmnxFPNetIngQGrpPStatEntry 36 }

tmnxFPNetIngQgPStFwdOutProfOctsL OBJECT-TYPE
    SYNTAX      Counter32
    MAX-ACCESS  read-only
    STATUS      current
    DESCRIPTION
        "The value of tmnxFPNetIngQgPStFwdOutProfOctsL indicates the lower 32
         bits of tmnxFPNetIngQgPStFwdOutProfOcts."
    ::= { tmnxFPNetIngQGrpPStatEntry 37 }

tmnxFPNetIngQgPStFwdOutProfOctsH OBJECT-TYPE
    SYNTAX      Counter32
    MAX-ACCESS  read-only
    STATUS      current
    DESCRIPTION
        "The value of tmnxFPNetIngQgPStFwdOutProfOctsH indicates the upper 32
         bits of tmnxFPNetIngQgPStFwdOutProfOcts."
    ::= { tmnxFPNetIngQGrpPStatEntry 38 }

tmnxFPNetIngQgPStUncolPktsOff    OBJECT-TYPE
    SYNTAX      Counter64
    MAX-ACCESS  read-only
    STATUS      current
    DESCRIPTION
        "The value of tmnxFPNetIngQgPStUncolPktsOff indicates the number of
         uncolored packets offered to the ingress Pchip."
    ::= { tmnxFPNetIngQGrpPStatEntry 39 }

tmnxFPNetIngQgPStUncolPktsOffL   OBJECT-TYPE
    SYNTAX      Counter32
    MAX-ACCESS  read-only
    STATUS      current
    DESCRIPTION
        "The value of tmnxFPNetIngQgPStUncolPktsOffL indicates the lower 32
         bits of tmnxFPNetIngQgPStUncolPktsOff."
    ::= { tmnxFPNetIngQGrpPStatEntry 40 }

tmnxFPNetIngQgPStUncolPktsOffH   OBJECT-TYPE
    SYNTAX      Counter32
    MAX-ACCESS  read-only
    STATUS      current
    DESCRIPTION
        "The value of tmnxFPNetIngQgPStUncolPktsOffH indicates the upper 32
         bits of tmnxFPNetIngQgPStUncolPktsOff."
    ::= { tmnxFPNetIngQGrpPStatEntry 41 }

tmnxFPNetIngQgPStUncolOctsOff    OBJECT-TYPE
    SYNTAX      Counter64
    MAX-ACCESS  read-only
    STATUS      current
    DESCRIPTION
        "The value of tmnxFPNetIngQgPStUncolOctsOff indicates the number of
         uncolored octets offered to the ingress Pchip."
    ::= { tmnxFPNetIngQGrpPStatEntry 42 }

tmnxFPNetIngQgPStUncolOctsOffL   OBJECT-TYPE
    SYNTAX      Counter32
    MAX-ACCESS  read-only
    STATUS      current
    DESCRIPTION
        "The value of tmnxFPNetIngQgPStUncolOctsOffL indicates the lower 32
         bits of tmnxFPNetIngQgPStUncolOctsOff."
    ::= { tmnxFPNetIngQGrpPStatEntry 43 }

tmnxFPNetIngQgPStUncolOctsOffH   OBJECT-TYPE
    SYNTAX      Counter32
    MAX-ACCESS  read-only
    STATUS      current
    DESCRIPTION
        "The value of tmnxFPNetIngQgPStUncolOctsOffH indicates the higher 32
         bits of the value of tmnxFPNetIngQgPStUncolOctsOff."
    ::= { tmnxFPNetIngQGrpPStatEntry 44 }

tmnxFPAccIngQGrpPStatTable       OBJECT-TYPE
    SYNTAX      SEQUENCE OF TmnxFPAccIngQGrpPStatEntry
    MAX-ACCESS  not-accessible
    STATUS      current
    DESCRIPTION
        "The tmnxFPAccIngQGrpPStatTable contains forwarding-plane ingress QoS
         queue group policer statistics on access side."
    ::= { tmnxCardObjs 28 }

tmnxFPAccIngQGrpPStatEntry       OBJECT-TYPE
    SYNTAX      TmnxFPAccIngQGrpPStatEntry
    MAX-ACCESS  not-accessible
    STATUS      current
    DESCRIPTION
        "The value of tmnxFPAccIngQGrpPStatEntry defines an entry in the
         tmnxFPAccIngQGrpPStatTable. It represents statistics about a specific
         QoS ingress queue group policer."
    INDEX       {
        tmnxChassisIndex,
        tmnxCardSlotNum,
        tmnxFPNum,
        tmnxFPAccIngQGrpName,
        tmnxFPAccIngQGrpInstanceId,
        tmnxFPAccIngQGrpPStatPolicerId
    }
    ::= { tmnxFPAccIngQGrpPStatTable 1 }

TmnxFPAccIngQGrpPStatEntry       ::= SEQUENCE
{
    tmnxFPAccIngQGrpPStatPolicerId   TIngPolicerId,
    tmnxFPAccIngQGrpPStatMode        TmnxIngPolicerStatMode,
    tmnxFPAccIngQgPStOffHPrioPkts    Counter64,
    tmnxFPAccIngQgPStOffHPrioPktsL   Counter32,
    tmnxFPAccIngQgPStOffHPrioPktsH   Counter32,
    tmnxFPAccIngQgPStDrpHPrioPkts    Counter64,
    tmnxFPAccIngQgPStDrpHPrioPktsL   Counter32,
    tmnxFPAccIngQgPStDrpHPrioPktsH   Counter32,
    tmnxFPAccIngQgPStOffLPrioPkts    Counter64,
    tmnxFPAccIngQgPStOffLPrioPktsL   Counter32,
    tmnxFPAccIngQgPStOffLPrioPktsH   Counter32,
    tmnxFPAccIngQgPStDrpLPrioPkts    Counter64,
    tmnxFPAccIngQgPStDrpLPrioPktsL   Counter32,
    tmnxFPAccIngQgPStDrpLPrioPktsH   Counter32,
    tmnxFPAccIngQgPStOffHPrioOcts    Counter64,
    tmnxFPAccIngQgPStOffHPrioOctsL   Counter32,
    tmnxFPAccIngQgPStOffHPrioOctsH   Counter32,
    tmnxFPAccIngQgPStDrpHPrioOcts    Counter64,
    tmnxFPAccIngQgPStDrpHPrioOctsL   Counter32,
    tmnxFPAccIngQgPStDrpHPrioOctsH   Counter32,
    tmnxFPAccIngQgPStOffLPrioOcts    Counter64,
    tmnxFPAccIngQgPStOffLPrioOctsL   Counter32,
    tmnxFPAccIngQgPStOffLPrioOctsH   Counter32,
    tmnxFPAccIngQgPStDrpLPrioOcts    Counter64,
    tmnxFPAccIngQgPStDrpLPrioOctsL   Counter32,
    tmnxFPAccIngQgPStDrpLPrioOctsH   Counter32,
    tmnxFPAccIngQgPStFwdInProfPkts   Counter64,
    tmnxFPAccIngQgPStFwdInProfPktsL  Counter32,
    tmnxFPAccIngQgPStFwdInProfPktsH  Counter32,
    tmnxFPAccIngQgPStFwdOutProfPkts  Counter64,
    tmnxFPAccIngQgPStFwdOutProfPktsL Counter32,
    tmnxFPAccIngQgPStFwdOutProfPktsH Counter32,
    tmnxFPAccIngQgPStFwdInProfOcts   Counter64,
    tmnxFPAccIngQgPStFwdInProfOctsL  Counter32,
    tmnxFPAccIngQgPStFwdInProfOctsH  Counter32,
    tmnxFPAccIngQgPStFwdOutProfOcts  Counter64,
    tmnxFPAccIngQgPStFwdOutProfOctsL Counter32,
    tmnxFPAccIngQgPStFwdOutProfOctsH Counter32,
    tmnxFPAccIngQgPStUncolPktsOff    Counter64,
    tmnxFPAccIngQgPStUncolPktsOffL   Counter32,
    tmnxFPAccIngQgPStUncolPktsOffH   Counter32,
    tmnxFPAccIngQgPStUncolOctsOff    Counter64,
    tmnxFPAccIngQgPStUncolOctsOffL   Counter32,
    tmnxFPAccIngQgPStUncolOctsOffH   Counter32
}

tmnxFPAccIngQGrpPStatPolicerId   OBJECT-TYPE
    SYNTAX      TIngPolicerId
    MAX-ACCESS  not-accessible
    STATUS      current
    DESCRIPTION
        "The value of tmnxFPAccIngQGrpPStatPolicerId specifies the index of the
         ingress QoS policer of this forwarding-plane queue group on access."
    ::= { tmnxFPAccIngQGrpPStatEntry 1 }

tmnxFPAccIngQGrpPStatMode        OBJECT-TYPE
    SYNTAX      TmnxIngPolicerStatMode
    MAX-ACCESS  read-only
    STATUS      current
    DESCRIPTION
        "The value of tmnxFPAccIngQGrpPStatMode indicates the stat mode used by
         this policer."
    ::= { tmnxFPAccIngQGrpPStatEntry 2 }

tmnxFPAccIngQgPStOffHPrioPkts    OBJECT-TYPE
    SYNTAX      Counter64
    MAX-ACCESS  read-only
    STATUS      current
    DESCRIPTION
        "The value of tmnxFPAccIngQgPStOffHPrioPkts indicates the number of
         high priority packets, as determined by the ingress queue group
         policer, offered by the Pchip to the Qchip."
    ::= { tmnxFPAccIngQGrpPStatEntry 3 }

tmnxFPAccIngQgPStOffHPrioPktsL   OBJECT-TYPE
    SYNTAX      Counter32
    MAX-ACCESS  read-only
    STATUS      current
    DESCRIPTION
        "The value of tmnxFPAccIngQgPStOffHPrioPktsL indicates the lower 32
         bits of tmnxFPAccIngQgPStOffHPrioPkts."
    ::= { tmnxFPAccIngQGrpPStatEntry 4 }

tmnxFPAccIngQgPStOffHPrioPktsH   OBJECT-TYPE
    SYNTAX      Counter32
    MAX-ACCESS  read-only
    STATUS      current
    DESCRIPTION
        "The value of tmnxFPAccIngQgPStOffHPrioPktsH indicates the upper 32
         bits of tmnxFPAccIngQgPStOffHPrioPkts."
    ::= { tmnxFPAccIngQGrpPStatEntry 5 }

tmnxFPAccIngQgPStDrpHPrioPkts    OBJECT-TYPE
    SYNTAX      Counter64
    MAX-ACCESS  read-only
    STATUS      current
    DESCRIPTION
        "The value of tmnxFPAccIngQgPStDrpHPrioPkts indicates the number of
         high priority packets, as determined by the ingress queue group
         policer, dropped by the Pchip due to: MBS exceeded, buffer pool limit
         exceeded, etc."
    ::= { tmnxFPAccIngQGrpPStatEntry 6 }

tmnxFPAccIngQgPStDrpHPrioPktsL   OBJECT-TYPE
    SYNTAX      Counter32
    MAX-ACCESS  read-only
    STATUS      current
    DESCRIPTION
        "The value of tmnxFPAccIngQgPStDrpHPrioPktsL indicates the lower 32
         bits of tmnxFPAccIngQgPStDrpHPrioPkts."
    ::= { tmnxFPAccIngQGrpPStatEntry 7 }

tmnxFPAccIngQgPStDrpHPrioPktsH   OBJECT-TYPE
    SYNTAX      Counter32
    MAX-ACCESS  read-only
    STATUS      current
    DESCRIPTION
        "The value of tmnxFPAccIngQgPStDrpHPrioPktsH indicates the upper 32
         bits of tmnxFPAccIngQgPStDrpHPrioPkts."
    ::= { tmnxFPAccIngQGrpPStatEntry 8 }

tmnxFPAccIngQgPStOffLPrioPkts    OBJECT-TYPE
    SYNTAX      Counter64
    MAX-ACCESS  read-only
    STATUS      current
    DESCRIPTION
        "The value of tmnxFPAccIngQgPStOffLPrioPkts indicates the number of low
         priority packets, as determined by the ingress queue group policer,
         offered by the Pchip to the Qchip."
    ::= { tmnxFPAccIngQGrpPStatEntry 9 }

tmnxFPAccIngQgPStOffLPrioPktsL   OBJECT-TYPE
    SYNTAX      Counter32
    MAX-ACCESS  read-only
    STATUS      current
    DESCRIPTION
        "The value of tmnxFPAccIngQgPStOffLPrioPktsL indicates the lower 32
         bits of tmnxFPAccIngQgPStOffLPrioPkts."
    ::= { tmnxFPAccIngQGrpPStatEntry 10 }

tmnxFPAccIngQgPStOffLPrioPktsH   OBJECT-TYPE
    SYNTAX      Counter32
    MAX-ACCESS  read-only
    STATUS      current
    DESCRIPTION
        "The value of tmnxFPAccIngQgPStOffLPrioPktsH indicates the upper 32
         bits of tmnxFPAccIngQgPStOffLPrioPkts."
    ::= { tmnxFPAccIngQGrpPStatEntry 11 }

tmnxFPAccIngQgPStDrpLPrioPkts    OBJECT-TYPE
    SYNTAX      Counter64
    MAX-ACCESS  read-only
    STATUS      current
    DESCRIPTION
        "The value of tmnxFPAccIngQgPStDrpLPrioPkts indicates the number of low
         priority packets, as determined by the ingress queue group policer,
         dropped by the Pchip due to: MBS exceeded, buffer pool limit exceeded,
         etc."
    ::= { tmnxFPAccIngQGrpPStatEntry 12 }

tmnxFPAccIngQgPStDrpLPrioPktsL   OBJECT-TYPE
    SYNTAX      Counter32
    MAX-ACCESS  read-only
    STATUS      current
    DESCRIPTION
        "The value of tmnxFPAccIngQgPStDrpLPrioPktsL indicates the lower 32
         bits of tmnxFPAccIngQgPStDrpLPrioPkts."
    ::= { tmnxFPAccIngQGrpPStatEntry 13 }

tmnxFPAccIngQgPStDrpLPrioPktsH   OBJECT-TYPE
    SYNTAX      Counter32
    MAX-ACCESS  read-only
    STATUS      current
    DESCRIPTION
        "The value of tmnxFPAccIngQgPStDrpLPrioPktsH indicates the upper 32
         bits of tmnxFPAccIngQgPStDrpLPrioPkts."
    ::= { tmnxFPAccIngQGrpPStatEntry 14 }

tmnxFPAccIngQgPStOffHPrioOcts    OBJECT-TYPE
    SYNTAX      Counter64
    MAX-ACCESS  read-only
    STATUS      current
    DESCRIPTION
        "The value of tmnxFPAccIngQgPStOffHPrioOcts indicates the number of
         high priority octets, as determined by the ingress queue group
         policer, offered by the Pchip to the Qchip."
    ::= { tmnxFPAccIngQGrpPStatEntry 15 }

tmnxFPAccIngQgPStOffHPrioOctsL   OBJECT-TYPE
    SYNTAX      Counter32
    MAX-ACCESS  read-only
    STATUS      current
    DESCRIPTION
        "The value of tmnxFPAccIngQgPStOffHPrioOctsL indicates the lower 32
         bits of tmnxFPAccIngQgPStOffHPrioOcts."
    ::= { tmnxFPAccIngQGrpPStatEntry 16 }

tmnxFPAccIngQgPStOffHPrioOctsH   OBJECT-TYPE
    SYNTAX      Counter32
    MAX-ACCESS  read-only
    STATUS      current
    DESCRIPTION
        "The value of tmnxFPAccIngQgPStOffHPrioOctsH indicates the upper 32
         bits of tmnxFPAccIngQgPStOffHPrioOcts."
    ::= { tmnxFPAccIngQGrpPStatEntry 17 }

tmnxFPAccIngQgPStDrpHPrioOcts    OBJECT-TYPE
    SYNTAX      Counter64
    MAX-ACCESS  read-only
    STATUS      current
    DESCRIPTION
        "The value of tmnxFPAccIngQgPStDrpHPrioOcts indicates the number of
         high priority octets, as determined by the ingress queue group
         policer, dropped by the Pchip due to: MBS exceeded, buffer pool limit
         exceeded, etc."
    ::= { tmnxFPAccIngQGrpPStatEntry 18 }

tmnxFPAccIngQgPStDrpHPrioOctsL   OBJECT-TYPE
    SYNTAX      Counter32
    MAX-ACCESS  read-only
    STATUS      current
    DESCRIPTION
        "The value of tmnxFPAccIngQgPStDrpHPrioOctsL indicates the lower 32
         bits of tmnxFPAccIngQgPStDrpHPrioOcts."
    ::= { tmnxFPAccIngQGrpPStatEntry 19 }

tmnxFPAccIngQgPStDrpHPrioOctsH   OBJECT-TYPE
    SYNTAX      Counter32
    MAX-ACCESS  read-only
    STATUS      current
    DESCRIPTION
        "The value of tmnxFPAccIngQgPStDrpHPrioOctsH indicates the upper 32
         bits of tmnxFPAccIngQgPStDrpHPrioOcts."
    ::= { tmnxFPAccIngQGrpPStatEntry 20 }

tmnxFPAccIngQgPStOffLPrioOcts    OBJECT-TYPE
    SYNTAX      Counter64
    MAX-ACCESS  read-only
    STATUS      current
    DESCRIPTION
        "The value of tmnxFPAccIngQgPStOffLPrioOcts indicates the number of low
         priority octets, as determined by the ingress queue group policer,
         offered by the Pchip to the Pchip."
    ::= { tmnxFPAccIngQGrpPStatEntry 21 }

tmnxFPAccIngQgPStOffLPrioOctsL   OBJECT-TYPE
    SYNTAX      Counter32
    MAX-ACCESS  read-only
    STATUS      current
    DESCRIPTION
        "The value of tmnxFPAccIngQgPStOffLPrioOctsL indicates the lower 32
         bits of tmnxFPAccIngQgPStOffLPrioOcts."
    ::= { tmnxFPAccIngQGrpPStatEntry 22 }

tmnxFPAccIngQgPStOffLPrioOctsH   OBJECT-TYPE
    SYNTAX      Counter32
    MAX-ACCESS  read-only
    STATUS      current
    DESCRIPTION
        "The value of tmnxFPAccIngQgPStOffLPrioOctsH indicates the upper 32
         bits of tmnxFPAccIngQgPStOffLPrioOcts."
    ::= { tmnxFPAccIngQGrpPStatEntry 23 }

tmnxFPAccIngQgPStDrpLPrioOcts    OBJECT-TYPE
    SYNTAX      Counter64
    MAX-ACCESS  read-only
    STATUS      current
    DESCRIPTION
        "The value of tmnxFPAccIngQgPStDrpLPrioOcts indicates the number of low
         priority octets, as determined by the ingress queue group policer,
         dropped by the Pchip due to: MBS exceeded, buffer pool limit exceeded,
         etc."
    ::= { tmnxFPAccIngQGrpPStatEntry 24 }

tmnxFPAccIngQgPStDrpLPrioOctsL   OBJECT-TYPE
    SYNTAX      Counter32
    MAX-ACCESS  read-only
    STATUS      current
    DESCRIPTION
        "The value of tmnxFPAccIngQgPStDrpLPrioOctsL indicates the lower 32
         bits of tmnxFPAccIngQgPStDrpLPrioOcts."
    ::= { tmnxFPAccIngQGrpPStatEntry 25 }

tmnxFPAccIngQgPStDrpLPrioOctsH   OBJECT-TYPE
    SYNTAX      Counter32
    MAX-ACCESS  read-only
    STATUS      current
    DESCRIPTION
        "The value of tmnxFPAccIngQgPStDrpLPrioOctsH indicates the upper 32
         bits of tmnxFPAccIngQgPStDrpLPrioOcts."
    ::= { tmnxFPAccIngQGrpPStatEntry 26 }

tmnxFPAccIngQgPStFwdInProfPkts   OBJECT-TYPE
    SYNTAX      Counter64
    MAX-ACCESS  read-only
    STATUS      current
    DESCRIPTION
        "The value of tmnxFPAccIngQgPStFwdInProfPkts indicates the number of
         in-profile packets (rate below CIR) forwarded by the ingress Pchip."
    ::= { tmnxFPAccIngQGrpPStatEntry 27 }

tmnxFPAccIngQgPStFwdInProfPktsL  OBJECT-TYPE
    SYNTAX      Counter32
    MAX-ACCESS  read-only
    STATUS      current
    DESCRIPTION
        "The value of tmnxFPAccIngQgPStFwdInProfPktsL indicates the lower 32
         bits of tmnxFPAccIngQgPStFwdInProfPkts."
    ::= { tmnxFPAccIngQGrpPStatEntry 28 }

tmnxFPAccIngQgPStFwdInProfPktsH  OBJECT-TYPE
    SYNTAX      Counter32
    MAX-ACCESS  read-only
    STATUS      current
    DESCRIPTION
        "The value of tmnxFPAccIngQgPStFwdInProfPktsH indicates the upper 32
         bits of tmnxFPAccIngQgPStFwdInProfPkts."
    ::= { tmnxFPAccIngQGrpPStatEntry 29 }

tmnxFPAccIngQgPStFwdOutProfPkts  OBJECT-TYPE
    SYNTAX      Counter64
    MAX-ACCESS  read-only
    STATUS      current
    DESCRIPTION
        "The value of tmnxFPAccIngQgPStFwdOutProfPkts indicates the number of
         out-of-profile packets (rate above CIR) forwarded by the ingress
         Pchip."
    ::= { tmnxFPAccIngQGrpPStatEntry 30 }

tmnxFPAccIngQgPStFwdOutProfPktsL OBJECT-TYPE
    SYNTAX      Counter32
    MAX-ACCESS  read-only
    STATUS      current
    DESCRIPTION
        "The value of tmnxFPAccIngQgPStFwdOutProfPktsL indicates the lower 32
         bits of tmnxFPAccIngQgPStFwdOutProfPkts."
    ::= { tmnxFPAccIngQGrpPStatEntry 31 }

tmnxFPAccIngQgPStFwdOutProfPktsH OBJECT-TYPE
    SYNTAX      Counter32
    MAX-ACCESS  read-only
    STATUS      current
    DESCRIPTION
        "The value of tmnxFPAccIngQgPStFwdOutProfPktsH indicates the upper 32
         bits of tmnxFPAccIngQgPStFwdOutProfPkts."
    ::= { tmnxFPAccIngQGrpPStatEntry 32 }

tmnxFPAccIngQgPStFwdInProfOcts   OBJECT-TYPE
    SYNTAX      Counter64
    MAX-ACCESS  read-only
    STATUS      current
    DESCRIPTION
        "The value of tmnxFPAccIngQgPStFwdInProfOcts indicates the number of
         in-profile octets (rate below CIR) forwarded by the ingress Pchip."
    ::= { tmnxFPAccIngQGrpPStatEntry 33 }

tmnxFPAccIngQgPStFwdInProfOctsL  OBJECT-TYPE
    SYNTAX      Counter32
    MAX-ACCESS  read-only
    STATUS      current
    DESCRIPTION
        "The value of tmnxFPAccIngQgPStFwdInProfOctsL indicates the lower 32
         bits of tmnxFPAccIngQgPStFwdInProfOcts."
    ::= { tmnxFPAccIngQGrpPStatEntry 34 }

tmnxFPAccIngQgPStFwdInProfOctsH  OBJECT-TYPE
    SYNTAX      Counter32
    MAX-ACCESS  read-only
    STATUS      current
    DESCRIPTION
        "The value of tmnxFPAccIngQgPStFwdInProfOctsH indicates the upper 32
         bits of tmnxFPAccIngQgPStFwdInProfOcts."
    ::= { tmnxFPAccIngQGrpPStatEntry 35 }

tmnxFPAccIngQgPStFwdOutProfOcts  OBJECT-TYPE
    SYNTAX      Counter64
    MAX-ACCESS  read-only
    STATUS      current
    DESCRIPTION
        "The value of tmnxFPAccIngQgPStFwdOutProfOcts indicates the number of
         out-of-profile octets (rate above CIR) forwarded by the ingress Pchip."
    ::= { tmnxFPAccIngQGrpPStatEntry 36 }

tmnxFPAccIngQgPStFwdOutProfOctsL OBJECT-TYPE
    SYNTAX      Counter32
    MAX-ACCESS  read-only
    STATUS      current
    DESCRIPTION
        "The value of tmnxFPAccIngQgPStFwdOutProfOctsL indicates the lower 32
         bits of tmnxFPAccIngQgPStFwdOutProfOcts."
    ::= { tmnxFPAccIngQGrpPStatEntry 37 }

tmnxFPAccIngQgPStFwdOutProfOctsH OBJECT-TYPE
    SYNTAX      Counter32
    MAX-ACCESS  read-only
    STATUS      current
    DESCRIPTION
        "The value of tmnxFPAccIngQgPStFwdOutProfOctsH indicates the upper 32
         bits of tmnxFPAccIngQgPStFwdOutProfOcts."
    ::= { tmnxFPAccIngQGrpPStatEntry 38 }

tmnxFPAccIngQgPStUncolPktsOff    OBJECT-TYPE
    SYNTAX      Counter64
    MAX-ACCESS  read-only
    STATUS      current
    DESCRIPTION
        "The value of tmnxFPAccIngQgPStUncolPktsOff indicates the number of
         uncolored packets offered to the ingress Pchip."
    ::= { tmnxFPAccIngQGrpPStatEntry 39 }

tmnxFPAccIngQgPStUncolPktsOffL   OBJECT-TYPE
    SYNTAX      Counter32
    MAX-ACCESS  read-only
    STATUS      current
    DESCRIPTION
        "The value of tmnxFPAccIngQgPStUncolPktsOffL indicates the lower 32
         bits of tmnxFPAccIngQgPStUncolPktsOff."
    ::= { tmnxFPAccIngQGrpPStatEntry 40 }

tmnxFPAccIngQgPStUncolPktsOffH   OBJECT-TYPE
    SYNTAX      Counter32
    MAX-ACCESS  read-only
    STATUS      current
    DESCRIPTION
        "The value of tmnxFPAccIngQgPStUncolPktsOffH indicates the upper 32
         bits of tmnxFPAccIngQgPStUncolPktsOff."
    ::= { tmnxFPAccIngQGrpPStatEntry 41 }

tmnxFPAccIngQgPStUncolOctsOff    OBJECT-TYPE
    SYNTAX      Counter64
    MAX-ACCESS  read-only
    STATUS      current
    DESCRIPTION
        "The value of tmnxFPAccIngQgPStUncolOctsOff indicates the number of
         uncolored octets offered to the ingress Pchip."
    ::= { tmnxFPAccIngQGrpPStatEntry 42 }

tmnxFPAccIngQgPStUncolOctsOffL   OBJECT-TYPE
    SYNTAX      Counter32
    MAX-ACCESS  read-only
    STATUS      current
    DESCRIPTION
        "The value of tmnxFPAccIngQgPStUncolOctsOffL indicates the lower 32
         bits of tmnxFPAccIngQgPStUncolOctsOff."
    ::= { tmnxFPAccIngQGrpPStatEntry 43 }

tmnxFPAccIngQgPStUncolOctsOffH   OBJECT-TYPE
    SYNTAX      Counter32
    MAX-ACCESS  read-only
    STATUS      current
    DESCRIPTION
        "The value of tmnxFPAccIngQgPStUncolOctsOffH indicates the higher 32
         bits of the value of tmnxFPAccIngQgPStUncolOctsOff."
    ::= { tmnxFPAccIngQGrpPStatEntry 44 }

tFPAccIngQGrpPlcrOvrTblLstChgd   OBJECT-TYPE
    SYNTAX      TimeStamp
    MAX-ACCESS  read-only
    STATUS      current
    DESCRIPTION
        "The value of tFPAccIngQGrpPlcrOvrTblLstChgd indicates the timestamp of
         last change to the tFPAccIngQGrpPlcrOvrTable."
    ::= { tmnxCardObjs 29 }

tFPAccIngQGrpPlcrOvrTable        OBJECT-TYPE
    SYNTAX      SEQUENCE OF TFPAccIngQGrpPlcrOvrEntry
    MAX-ACCESS  not-accessible
    STATUS      current
    DESCRIPTION
        "The value of tFPAccIngQGrpPlcrOvrTable contains forwarding-plane QoS
         ingress queue group policer overrides on access side."
    ::= { tmnxCardObjs 30 }

tFPAccIngQGrpPlcrOvrEntry        OBJECT-TYPE
    SYNTAX      TFPAccIngQGrpPlcrOvrEntry
    MAX-ACCESS  not-accessible
    STATUS      current
    DESCRIPTION
        "The value of tFPAccIngQGrpPlcrOvrEntry defines an entry in the
         tFPAccIngQGrpPlcrOvrTable. It represents policer overrides about a
         specific forwarding-plane QoS ingress queue group policer."
    INDEX       {
        tmnxChassisIndex,
        tmnxCardSlotNum,
        tmnxFPNum,
        tmnxFPAccIngQGrpName,
        tmnxFPAccIngQGrpInstanceId,
        tFPAccIngQGrpPlcrOvrPolicerId
    }
    ::= { tFPAccIngQGrpPlcrOvrTable 1 }

TFPAccIngQGrpPlcrOvrEntry        ::= SEQUENCE
{
    tFPAccIngQGrpPlcrOvrPolicerId    TIngPolicerId,
    tFPAccIngQGrpPlcrOvrRowStatus    RowStatus,
    tFPAccIngQGrpPlcrOvrLastChgd     TimeStamp,
    tFPAccIngQGrpPlcrOvrAdminPIR     THPolPIRRateOverride,
    tFPAccIngQGrpPlcrOvrAdminCIR     THPolCIRRateOverride,
    tFPAccIngQGrpPlcrOvrStatMode     TmnxIngPolicerStatModeOverride,
    tFPAccIngQGrpPlcrOvrMBS          TPlcrBurstSizeBytesOverride,
    tFPAccIngQGrpPlcrOvrCBS          TPlcrBurstSizeBytesOverride,
    tFPAccIngQGrpPlcrOvrPktOffset    TPerPacketOffsetOvr
}

tFPAccIngQGrpPlcrOvrPolicerId    OBJECT-TYPE
    SYNTAX      TIngPolicerId
    MAX-ACCESS  not-accessible
    STATUS      current
    DESCRIPTION
        "The value of tFPAccIngQGrpPlcrOvrPolicerId specifies the index of the
         ingress QoS policer of this forwarding-plane queue group on access."
    ::= { tFPAccIngQGrpPlcrOvrEntry 1 }

tFPAccIngQGrpPlcrOvrRowStatus    OBJECT-TYPE
    SYNTAX      RowStatus
    MAX-ACCESS  read-create
    STATUS      current
    DESCRIPTION
        "The value of tFPAccIngQGrpPlcrOvrRowStatus specifies the Row Status of
         the entry.

         This tFPAccIngQGrpPlcrOvrRowStatus object allows creation/deletion of
         rows in this table."
    ::= { tFPAccIngQGrpPlcrOvrEntry 2 }

tFPAccIngQGrpPlcrOvrLastChgd     OBJECT-TYPE
    SYNTAX      TimeStamp
    MAX-ACCESS  read-only
    STATUS      current
    DESCRIPTION
        "The value of tFPAccIngQGrpPlcrOvrLastChgd indicates the timestamp of
         last change to this row in tFPAccIngQGrpPlcrOvrTable."
    ::= { tFPAccIngQGrpPlcrOvrEntry 3 }

tFPAccIngQGrpPlcrOvrAdminPIR     OBJECT-TYPE
    SYNTAX      THPolPIRRateOverride
    UNITS       "kbps"
    MAX-ACCESS  read-create
    STATUS      current
    DESCRIPTION
        "The value of tFPAccIngQGrpPlcrOvrAdminPIR specifies the administrative
         PIR specified by the user."
    DEFVAL      { -2 }
    ::= { tFPAccIngQGrpPlcrOvrEntry 4 }

tFPAccIngQGrpPlcrOvrAdminCIR     OBJECT-TYPE
    SYNTAX      THPolCIRRateOverride
    UNITS       "kbps"
    MAX-ACCESS  read-create
    STATUS      current
    DESCRIPTION
        "The value of tFPAccIngQGrpPlcrOvrAdminCIR specifies the administrative
         CIR specified by the user."
    DEFVAL      { -2 }
    ::= { tFPAccIngQGrpPlcrOvrEntry 5 }

tFPAccIngQGrpPlcrOvrStatMode     OBJECT-TYPE
    SYNTAX      TmnxIngPolicerStatModeOverride
    MAX-ACCESS  read-create
    STATUS      current
    DESCRIPTION
        "The value of tFPAccIngQGrpPlcrOvrStatMode specifies the mode of
         statistics collected by the policer on this forwarding-plane QoS
         ingress queue group."
    DEFVAL      { noOverride }
    ::= { tFPAccIngQGrpPlcrOvrEntry 6 }

tFPAccIngQGrpPlcrOvrMBS          OBJECT-TYPE
    SYNTAX      TPlcrBurstSizeBytesOverride
    UNITS       "bytes"
    MAX-ACCESS  read-create
    STATUS      current
    DESCRIPTION
        "The value of tFPAccIngQGrpPlcrOvrMBS specifies the maximum amount of
         buffer space (in bytes) allowed for the queue by the policer on this
         forwarding-plane QoS ingress queue group."
    DEFVAL      { -2 }
    ::= { tFPAccIngQGrpPlcrOvrEntry 7 }

tFPAccIngQGrpPlcrOvrCBS          OBJECT-TYPE
    SYNTAX      TPlcrBurstSizeBytesOverride
    UNITS       "bytes"
    MAX-ACCESS  read-create
    STATUS      current
    DESCRIPTION
        "The value of tFPAccIngQGrpPlcrOvrCBS specifies the amount of reserved
         buffer space (in bytes) set by the policer on this forwarding-plane
         QoS ingress queue group."
    DEFVAL      { -2 }
    ::= { tFPAccIngQGrpPlcrOvrEntry 8 }

tFPAccIngQGrpPlcrOvrPktOffset    OBJECT-TYPE
    SYNTAX      TPerPacketOffsetOvr
    UNITS       "bytes"
    MAX-ACCESS  read-create
    STATUS      current
    DESCRIPTION
        "The value of tFPAccIngQGrpPlcrOvrPktOffset specifies the packet byte
         offset for addition of policing information by the policer on this
         forwarding-plane QoS ingress queue group."
    DEFVAL      { -128 }
    ::= { tFPAccIngQGrpPlcrOvrEntry 9 }

tFPAccIngQGrpArbitStatTable      OBJECT-TYPE
    SYNTAX      SEQUENCE OF TFPAccIngQGrpArbitStatEntry
    MAX-ACCESS  not-accessible
    STATUS      current
    DESCRIPTION
        "The value of tFPAccIngQGrpArbitStatTable contains forwarding-plane
         ingress QoS queue group policer statistics on access side."
    ::= { tmnxCardObjs 31 }

tFPAccIngQGrpArbitStatEntry      OBJECT-TYPE
    SYNTAX      TFPAccIngQGrpArbitStatEntry
    MAX-ACCESS  not-accessible
    STATUS      current
    DESCRIPTION
        "The value of tFPAccIngQGrpArbitStatEntry defines an entry in the
         tFPAccIngQGrpArbitStatTable. It represents statistics about a specific
         QoS ingress queue group policer."
    INDEX       {
        tmnxChassisIndex,
        tmnxCardSlotNum,
        tmnxFPNum,
        tmnxFPAccIngQGrpName,
        tmnxFPAccIngQGrpInstanceId,
        tFPAccIngQGrpArbitStatName
    }
    ::= { tFPAccIngQGrpArbitStatTable 1 }

TFPAccIngQGrpArbitStatEntry      ::= SEQUENCE
{
    tFPAccIngQGrpArbitStatName       TNamedItem,
    tFPAccIngQGrpArbitStatFwdPkts    Counter64,
    tFPAccIngQGrpArbitStatFwdPktsL   Counter32,
    tFPAccIngQGrpArbitStatFwdPktsH   Counter32,
    tFPAccIngQGrpArbitStatFwdOcts    Counter64,
    tFPAccIngQGrpArbitStatFwdOctsL   Counter32,
    tFPAccIngQGrpArbitStatFwdOctsH   Counter32
}

tFPAccIngQGrpArbitStatName       OBJECT-TYPE
    SYNTAX      TNamedItem
    MAX-ACCESS  not-accessible
    STATUS      current
    DESCRIPTION
        "The value of tFPAccIngQGrpArbitStatName specifies the name of the
         ingress QoS arbiter of this forwarding-plane queue group on access."
    ::= { tFPAccIngQGrpArbitStatEntry 1 }

tFPAccIngQGrpArbitStatFwdPkts    OBJECT-TYPE
    SYNTAX      Counter64
    MAX-ACCESS  read-only
    STATUS      current
    DESCRIPTION
        "The value of tFPAccIngQGrpArbitStatFwdPkts indicates the number of
         forwarded packets by the ingress queue group arbiter Pchip."
    ::= { tFPAccIngQGrpArbitStatEntry 2 }

tFPAccIngQGrpArbitStatFwdPktsL   OBJECT-TYPE
    SYNTAX      Counter32
    MAX-ACCESS  read-only
    STATUS      current
    DESCRIPTION
        "The value of tFPAccIngQGrpArbitStatFwdPktsL indicates the lower 32
         bits of tFPAccIngQGrpArbitStatFwdPkts."
    ::= { tFPAccIngQGrpArbitStatEntry 3 }

tFPAccIngQGrpArbitStatFwdPktsH   OBJECT-TYPE
    SYNTAX      Counter32
    MAX-ACCESS  read-only
    STATUS      current
    DESCRIPTION
        "The value of tFPAccIngQGrpArbitStatFwdPktsH indicates the upper 32
         bits of tFPAccIngQGrpArbitStatFwdPkts."
    ::= { tFPAccIngQGrpArbitStatEntry 4 }

tFPAccIngQGrpArbitStatFwdOcts    OBJECT-TYPE
    SYNTAX      Counter64
    MAX-ACCESS  read-only
    STATUS      current
    DESCRIPTION
        "The value of tFPAccIngQGrpArbitStatFwdOcts indicates the number of
         forwarded octets by the ingress queue group arbiter Pchip."
    ::= { tFPAccIngQGrpArbitStatEntry 5 }

tFPAccIngQGrpArbitStatFwdOctsL   OBJECT-TYPE
    SYNTAX      Counter32
    MAX-ACCESS  read-only
    STATUS      current
    DESCRIPTION
        "The value of tFPAccIngQGrpArbitStatFwdOctsL indicates the lower 32
         bits of tFPAccIngQGrpArbitStatFwdOcts."
    ::= { tFPAccIngQGrpArbitStatEntry 6 }

tFPAccIngQGrpArbitStatFwdOctsH   OBJECT-TYPE
    SYNTAX      Counter32
    MAX-ACCESS  read-only
    STATUS      current
    DESCRIPTION
        "The value of tFPAccIngQGrpArbitStatFwdOctsH indicates the upper 32
         bits of tFPAccIngQGrpArbitStatFwdOcts."
    ::= { tFPAccIngQGrpArbitStatEntry 7 }

tFPNetIngQGrpArbitStatTable      OBJECT-TYPE
    SYNTAX      SEQUENCE OF TFPNetIngQGrpArbitStatEntry
    MAX-ACCESS  not-accessible
    STATUS      current
    DESCRIPTION
        "The value of tFPNetIngQGrpArbitStatTable contains forwarding-plane
         ingress QoS queue group arbiter statistics on network side."
    ::= { tmnxCardObjs 32 }

tFPNetIngQGrpArbitStatEntry      OBJECT-TYPE
    SYNTAX      TFPNetIngQGrpArbitStatEntry
    MAX-ACCESS  not-accessible
    STATUS      current
    DESCRIPTION
        "The value of tFPNetIngQGrpArbitStatEntry defines an entry in the
         tFPNetIngQGrpArbitStatTable. It represents statistics about a specific
         QoS ingress queue group arbiter."
    INDEX       {
        tmnxChassisIndex,
        tmnxCardSlotNum,
        tmnxFPNum,
        tmnxFPNetIngQGrpName,
        tmnxFPNetIngQGrpInstanceId,
        tFPNetIngQGrpArbitStatName
    }
    ::= { tFPNetIngQGrpArbitStatTable 1 }

TFPNetIngQGrpArbitStatEntry      ::= SEQUENCE
{
    tFPNetIngQGrpArbitStatName       TNamedItem,
    tFPNetIngQGrpArbitStatFwdPkts    Counter64,
    tFPNetIngQGrpArbitStatFwdPktsL   Counter32,
    tFPNetIngQGrpArbitStatFwdPktsH   Counter32,
    tFPNetIngQGrpArbitStatFwdOcts    Counter64,
    tFPNetIngQGrpArbitStatFwdOctsL   Counter32,
    tFPNetIngQGrpArbitStatFwdOctsH   Counter32
}

tFPNetIngQGrpArbitStatName       OBJECT-TYPE
    SYNTAX      TNamedItem
    MAX-ACCESS  not-accessible
    STATUS      current
    DESCRIPTION
        "The value of tFPNetIngQGrpArbitStatName specifies the name of the
         ingress QoS arbiter of this forwarding-plane queue group on network."
    ::= { tFPNetIngQGrpArbitStatEntry 1 }

tFPNetIngQGrpArbitStatFwdPkts    OBJECT-TYPE
    SYNTAX      Counter64
    MAX-ACCESS  read-only
    STATUS      current
    DESCRIPTION
        "The value of tFPNetIngQGrpArbitStatFwdPkts indicates the number of
         forwarded packets by the ingress queue group arbiter Pchip."
    ::= { tFPNetIngQGrpArbitStatEntry 2 }

tFPNetIngQGrpArbitStatFwdPktsL   OBJECT-TYPE
    SYNTAX      Counter32
    MAX-ACCESS  read-only
    STATUS      current
    DESCRIPTION
        "The value of tFPNetIngQGrpArbitStatFwdPktsL indicates the lower 32
         bits of tFPNetIngQGrpArbitStatFwdPkts."
    ::= { tFPNetIngQGrpArbitStatEntry 3 }

tFPNetIngQGrpArbitStatFwdPktsH   OBJECT-TYPE
    SYNTAX      Counter32
    MAX-ACCESS  read-only
    STATUS      current
    DESCRIPTION
        "The value of tFPNetIngQGrpArbitStatFwdPktsH indicates the upper 32
         bits of tFPNetIngQGrpArbitStatFwdPkts."
    ::= { tFPNetIngQGrpArbitStatEntry 4 }

tFPNetIngQGrpArbitStatFwdOcts    OBJECT-TYPE
    SYNTAX      Counter64
    MAX-ACCESS  read-only
    STATUS      current
    DESCRIPTION
        "The value of tFPNetIngQGrpArbitStatFwdOcts indicates the number of
         forwarded octets by the ingress queue group arbiter Pchip."
    ::= { tFPNetIngQGrpArbitStatEntry 5 }

tFPNetIngQGrpArbitStatFwdOctsL   OBJECT-TYPE
    SYNTAX      Counter32
    MAX-ACCESS  read-only
    STATUS      current
    DESCRIPTION
        "The value of tFPNetIngQGrpArbitStatFwdOctsL indicates the lower 32
         bits of tFPNetIngQGrpArbitStatFwdOcts."
    ::= { tFPNetIngQGrpArbitStatEntry 6 }

tFPNetIngQGrpArbitStatFwdOctsH   OBJECT-TYPE
    SYNTAX      Counter32
    MAX-ACCESS  read-only
    STATUS      current
    DESCRIPTION
        "The value of tFPNetIngQGrpArbitStatFwdOctsH indicates the upper 32
         bits of tFPNetIngQGrpArbitStatFwdOcts."
    ::= { tFPNetIngQGrpArbitStatEntry 7 }

tmnxVirtualSchedulerAdjTable     OBJECT-TYPE
    SYNTAX      SEQUENCE OF TmnxVirtualSchedulerAdjEntry
    MAX-ACCESS  not-accessible
    STATUS      current
    DESCRIPTION
        "The tmnxVirtualSchedulerAdjTable has an entry to fine tune Quality of
         Service (QoS) parameters."
    ::= { tmnxCardObjs 33 }

tmnxVirtualSchedulerAdjEntry     OBJECT-TYPE
    SYNTAX      TmnxVirtualSchedulerAdjEntry
    MAX-ACCESS  not-accessible
    STATUS      current
    DESCRIPTION
        "The tmnxVirtualSchedulerAdjEntry allows fine tune Quality of Service
         (QoS) parameters on the corresponding card.

         The row exists only if the associated card instance identified by
         tmnxCardSlotNum exists in the tmnxCardTable."
    INDEX       {
        tmnxChassisIndex,
        tmnxCardSlotNum
    }
    ::= { tmnxVirtualSchedulerAdjTable 1 }

TmnxVirtualSchedulerAdjEntry     ::= SEQUENCE
{
    tmnxCardRateCalcFastQueue        Unsigned32,
    tmnxCardRateCalcSlowQueue        Unsigned32,
    tmnxCardSchedRun                 Unsigned32,
    tmnxCardTaskScheduling           Unsigned32,
    tmnxCardSlowQueueThresh          Integer32,
    tmnxCardInternalSchedWghtMode    TmnxInternalSchedWeightMode
}

tmnxCardRateCalcFastQueue        OBJECT-TYPE
    SYNTAX      Unsigned32 (1..100000)
    UNITS       "thousandths of a percent"
    MAX-ACCESS  read-write
    STATUS      current
    DESCRIPTION
        "The value of tmnxCardRateCalcFastQueue specifies the percentage by
         which fine tuning of Quality of Service (QoS) parameter 'Fast-Queue'
         is modified."
    DEFVAL      { 10000 }
    ::= { tmnxVirtualSchedulerAdjEntry 1 }

tmnxCardRateCalcSlowQueue        OBJECT-TYPE
    SYNTAX      Unsigned32 (1..100000)
    UNITS       "thousandths of a percent"
    MAX-ACCESS  read-write
    STATUS      current
    DESCRIPTION
        "The value of tmnxCardRateCalcSlowQueue specifies the percentage by
         which fine tuning of Quality of Service (QoS) parameter 'Slow-Queue'
         is modified."
    DEFVAL      { 10000 }
    ::= { tmnxVirtualSchedulerAdjEntry 2 }

tmnxCardSchedRun                 OBJECT-TYPE
    SYNTAX      Unsigned32 (1..100000)
    UNITS       "thousandths of a percent"
    MAX-ACCESS  read-write
    STATUS      current
    DESCRIPTION
        "The value of tmnxCardSchedRun specifies the percentage by which the
         minimum amount of time required between the iterations of bandwidth
         distribution by an Quality of Service (QoS) virtual scheduler is
         modified."
    DEFVAL      { 10000 }
    ::= { tmnxVirtualSchedulerAdjEntry 3 }

tmnxCardTaskScheduling           OBJECT-TYPE
    SYNTAX      Unsigned32 (1..100000)
    UNITS       "thousandths of a percent"
    MAX-ACCESS  read-write
    STATUS      current
    DESCRIPTION
        "The value of tmnxCardTaskScheduling specifies the percentage change in
         virtual scheduling task wake up interval."
    DEFVAL      { 10000 }
    ::= { tmnxVirtualSchedulerAdjEntry 4 }

tmnxCardSlowQueueThresh          OBJECT-TYPE
    SYNTAX      Integer32 (0..1000000)
    UNITS       "kbps"
    MAX-ACCESS  read-write
    STATUS      current
    DESCRIPTION
        "The value of tmnxCardSlowQueueThresh specifies the rate at which
         queues are placed in the 'slow-queue' category."
    DEFVAL      { 1000 }
    ::= { tmnxVirtualSchedulerAdjEntry 5 }

tmnxCardInternalSchedWghtMode    OBJECT-TYPE
    SYNTAX      TmnxInternalSchedWeightMode
    MAX-ACCESS  read-write
    STATUS      current
    DESCRIPTION
        "The value of tmnxCardInternalSchedWghtMode specifies the weight-mode
         adjustment applied on this card."
    DEFVAL      { default }
    ::= { tmnxVirtualSchedulerAdjEntry 6 }

tmnxFpDcpDynEnfrcPlcrStatTable   OBJECT-TYPE
    SYNTAX      SEQUENCE OF TmnxFpDcpDynEnfrcPlcrStatEntry
    MAX-ACCESS  not-accessible
    STATUS      current
    DESCRIPTION
        "The tmnxFpDcpDynEnfrcPlcrStatTable has the statistics information of
         the dynamic enforcement policer per forwarding plane."
    ::= { tmnxCardObjs 34 }

tmnxFpDcpDynEnfrcPlcrStatEntry   OBJECT-TYPE
    SYNTAX      TmnxFpDcpDynEnfrcPlcrStatEntry
    MAX-ACCESS  not-accessible
    STATUS      current
    DESCRIPTION
        "The value of tmnxFpDcpDynEnfrcPlcrStatEntry represents statistics
         information per forwarding plane for the dynamic enforcement policer."
    INDEX       {
        tmnxChassisIndex,
        tmnxCardSlotNum,
        tmnxFPNum
    }
    ::= { tmnxFpDcpDynEnfrcPlcrStatTable 1 }

TmnxFpDcpDynEnfrcPlcrStatEntry   ::= SEQUENCE
{
    tmnxFpDcpDynPlcrHiWtrMrkHitCnt   Counter32,
    tmnxFpDcpDynPlcrHiWtrMrkTime     TimeStamp,
    tmnxFpDcpDynPlcrAllocFailCount   Counter32,
    tmnxFpDcpDynPlcrInUse            Counter32
}

tmnxFpDcpDynPlcrHiWtrMrkHitCnt   OBJECT-TYPE
    SYNTAX      Counter32
    MAX-ACCESS  read-only
    STATUS      current
    DESCRIPTION
        "The value of tmnxFpDcpDynPlcrHiWtrMrkHitCnt indicates the maximum
         number of dynamic enforcement policers in use at any point of time."
    ::= { tmnxFpDcpDynEnfrcPlcrStatEntry 1 }

tmnxFpDcpDynPlcrHiWtrMrkTime     OBJECT-TYPE
    SYNTAX      TimeStamp
    MAX-ACCESS  read-only
    STATUS      current
    DESCRIPTION
        "The value of tmnxFpDcpDynPlcrHiWtrMrkTime indicates the time at which
         maximum number of dynamic enforcement policers was hit."
    ::= { tmnxFpDcpDynEnfrcPlcrStatEntry 2 }

tmnxFpDcpDynPlcrAllocFailCount   OBJECT-TYPE
    SYNTAX      Counter32
    MAX-ACCESS  read-only
    STATUS      current
    DESCRIPTION
        "The value of tmnxFpDcpDynPlcrAllocFailCount indicated the number of
         times the system failed to allocate dynamic enforcement policers."
    ::= { tmnxFpDcpDynEnfrcPlcrStatEntry 3 }

tmnxFpDcpDynPlcrInUse            OBJECT-TYPE
    SYNTAX      Counter32
    MAX-ACCESS  read-only
    STATUS      current
    DESCRIPTION
        "The value of tmnxFpDcpDynPlcrInUse indicated the number of dynamic
         enforcement policers currently in use by the system."
    ::= { tmnxFpDcpDynEnfrcPlcrStatEntry 4 }

tFPNetIngQGrpPlcrOvrTblLstChgd   OBJECT-TYPE
    SYNTAX      TimeStamp
    MAX-ACCESS  read-only
    STATUS      current
    DESCRIPTION
        "The value of tFPNetIngQGrpPlcrOvrTblLstChgd indicates the timestamp of
         last change to the tFPNetIngQGrpPlcrOvrTable."
    ::= { tmnxCardObjs 35 }

tFPNetIngQGrpPlcrOvrTable        OBJECT-TYPE
    SYNTAX      SEQUENCE OF TFPNetIngQGrpPlcrOvrEntry
    MAX-ACCESS  not-accessible
    STATUS      current
    DESCRIPTION
        "The value of tFPNetIngQGrpPlcrOvrTable contains forwarding-plane QoS
         ingress queue group policer overrides on network side."
    ::= { tmnxCardObjs 36 }

tFPNetIngQGrpPlcrOvrEntry        OBJECT-TYPE
    SYNTAX      TFPNetIngQGrpPlcrOvrEntry
    MAX-ACCESS  not-accessible
    STATUS      current
    DESCRIPTION
        "The value of tFPNetIngQGrpPlcrOvrEntry defines an entry in the
         tFPNetIngQGrpPlcrOvrTable. It represents policer overrides about a
         specific forwarding-plane QoS ingress queue group policer."
    INDEX       {
        tmnxChassisIndex,
        tmnxCardSlotNum,
        tmnxFPNum,
        tmnxFPNetIngQGrpName,
        tmnxFPNetIngQGrpInstanceId,
        tFPNetIngQGrpPlcrOvrPolicerId
    }
    ::= { tFPNetIngQGrpPlcrOvrTable 1 }

TFPNetIngQGrpPlcrOvrEntry        ::= SEQUENCE
{
    tFPNetIngQGrpPlcrOvrPolicerId    TIngPolicerId,
    tFPNetIngQGrpPlcrOvrRowStatus    RowStatus,
    tFPNetIngQGrpPlcrOvrLastChgd     TimeStamp,
    tFPNetIngQGrpPlcrOvrAdminPIR     THPolPIRRateOverride,
    tFPNetIngQGrpPlcrOvrAdminCIR     THPolCIRRateOverride,
    tFPNetIngQGrpPlcrOvrStatMode     TmnxIngPolicerStatModeOverride,
    tFPNetIngQGrpPlcrOvrMBS          TPlcrBurstSizeBytesOverride,
    tFPNetIngQGrpPlcrOvrCBS          TPlcrBurstSizeBytesOverride,
    tFPNetIngQGrpPlcrOvrPktOffset    TPerPacketOffsetOvr
}

tFPNetIngQGrpPlcrOvrPolicerId    OBJECT-TYPE
    SYNTAX      TIngPolicerId
    MAX-ACCESS  not-accessible
    STATUS      current
    DESCRIPTION
        "The value of tFPNetIngQGrpPlcrOvrPolicerId specifies the index of the
         ingress QoS policer of this forwarding-plane queue group on network."
    ::= { tFPNetIngQGrpPlcrOvrEntry 1 }

tFPNetIngQGrpPlcrOvrRowStatus    OBJECT-TYPE
    SYNTAX      RowStatus
    MAX-ACCESS  read-create
    STATUS      current
    DESCRIPTION
        "The value of tFPNetIngQGrpPlcrOvrRowStatus specifies the Row Status of
         the entry.

         This tFPNetIngQGrpPlcrOvrRowStatus object allows creation/deletion of
         rows in this table."
    ::= { tFPNetIngQGrpPlcrOvrEntry 2 }

tFPNetIngQGrpPlcrOvrLastChgd     OBJECT-TYPE
    SYNTAX      TimeStamp
    MAX-ACCESS  read-only
    STATUS      current
    DESCRIPTION
        "The value of tFPNetIngQGrpPlcrOvrLastChgd indicates the timestamp of
         last change to this row in tFPNetIngQGrpPlcrOvrTable."
    ::= { tFPNetIngQGrpPlcrOvrEntry 3 }

tFPNetIngQGrpPlcrOvrAdminPIR     OBJECT-TYPE
    SYNTAX      THPolPIRRateOverride
    UNITS       "kbps"
    MAX-ACCESS  read-create
    STATUS      current
    DESCRIPTION
        "The value of tFPNetIngQGrpPlcrOvrAdminPIR specifies the administrative
         PIR specified by the user."
    DEFVAL      { -2 }
    ::= { tFPNetIngQGrpPlcrOvrEntry 4 }

tFPNetIngQGrpPlcrOvrAdminCIR     OBJECT-TYPE
    SYNTAX      THPolCIRRateOverride
    UNITS       "kbps"
    MAX-ACCESS  read-create
    STATUS      current
    DESCRIPTION
        "The value of tFPNetIngQGrpPlcrOvrAdminCIR specifies the administrative
         CIR specified by the user."
    DEFVAL      { -2 }
    ::= { tFPNetIngQGrpPlcrOvrEntry 5 }

tFPNetIngQGrpPlcrOvrStatMode     OBJECT-TYPE
    SYNTAX      TmnxIngPolicerStatModeOverride
    MAX-ACCESS  read-create
    STATUS      current
    DESCRIPTION
        "The value of tFPNetIngQGrpPlcrOvrStatMode specifies the mode of
         statistics collected by the policer on this forwarding-plane QoS
         ingress queue group."
    DEFVAL      { noOverride }
    ::= { tFPNetIngQGrpPlcrOvrEntry 6 }

tFPNetIngQGrpPlcrOvrMBS          OBJECT-TYPE
    SYNTAX      TPlcrBurstSizeBytesOverride
    UNITS       "bytes"
    MAX-ACCESS  read-create
    STATUS      current
    DESCRIPTION
        "The value of tFPNetIngQGrpPlcrOvrMBS specifies the maximum amount of
         buffer space (in bytes) allowed for the queue by the policer on this
         forwarding-plane QoS ingress queue group."
    DEFVAL      { -2 }
    ::= { tFPNetIngQGrpPlcrOvrEntry 7 }

tFPNetIngQGrpPlcrOvrCBS          OBJECT-TYPE
    SYNTAX      TPlcrBurstSizeBytesOverride
    UNITS       "bytes"
    MAX-ACCESS  read-create
    STATUS      current
    DESCRIPTION
        "The value of tFPNetIngQGrpPlcrOvrCBS specifies the amount of reserved
         buffer space (in bytes) set by the policer on this forwarding-plane
         QoS ingress queue group."
    DEFVAL      { -2 }
    ::= { tFPNetIngQGrpPlcrOvrEntry 8 }

tFPNetIngQGrpPlcrOvrPktOffset    OBJECT-TYPE
    SYNTAX      TPerPacketOffsetOvr
    UNITS       "bytes"
    MAX-ACCESS  read-create
    STATUS      current
    DESCRIPTION
        "The value of tFPNetIngQGrpPlcrOvrPktOffset specifies the packet byte
         offset for addition of policing information by the policer on this
         forwarding-plane QoS ingress queue group."
    DEFVAL      { -128 }
    ::= { tFPNetIngQGrpPlcrOvrEntry 9 }

tFPAccIngQGrpPCPOvrTblLastChgd   OBJECT-TYPE
    SYNTAX      TimeStamp
    MAX-ACCESS  read-only
    STATUS      current
    DESCRIPTION
        "tFPAccIngQGrpPCPOvrTblLastChgd indicates the timestamp of last change
         to the tFPAccIngQGrpPCPOvrTable."
    ::= { tmnxCardObjs 37 }

tFPAccIngQGrpPCPOvrTable         OBJECT-TYPE
    SYNTAX      SEQUENCE OF TFPAccIngQGrpPCPOvrEntry
    MAX-ACCESS  not-accessible
    STATUS      current
    DESCRIPTION
        "A table that contains forwarding plane ingress policer control
         override information."
    ::= { tmnxCardObjs 38 }

tFPAccIngQGrpPCPOvrEntry         OBJECT-TYPE
    SYNTAX      TFPAccIngQGrpPCPOvrEntry
    MAX-ACCESS  not-accessible
    STATUS      current
    DESCRIPTION
        "Policer control override information about a specific forwarding plane
         on the access ingress side."
    INDEX       {
        tmnxChassisIndex,
        tmnxCardSlotNum,
        tmnxFPNum,
        tmnxFPAccIngQGrpName,
        tmnxFPAccIngQGrpInstanceId
    }
    ::= { tFPAccIngQGrpPCPOvrTable 1 }

TFPAccIngQGrpPCPOvrEntry         ::= SEQUENCE
{
    tFPAccIngQGrpPCPOvrRowStatus     RowStatus,
    tFPAccIngQGrpPCPOvrLastChgd      TimeStamp,
    tFPAccIngQGrpPCPOvrMaxRate       THPolPIRRateOverride,
    tFPAccIngQGrpPCPOvrMinMBSSep     TPlcrBurstSizeBytesOverride
}

tFPAccIngQGrpPCPOvrRowStatus     OBJECT-TYPE
    SYNTAX      RowStatus
    MAX-ACCESS  read-create
    STATUS      current
    DESCRIPTION
        "This is the Row Status of the entry. This allows creation/deletion of
         rows in this table."
    ::= { tFPAccIngQGrpPCPOvrEntry 1 }

tFPAccIngQGrpPCPOvrLastChgd      OBJECT-TYPE
    SYNTAX      TimeStamp
    MAX-ACCESS  read-only
    STATUS      current
    DESCRIPTION
        "The value of tFPAccIngQGrpPCPOvrLastChgd indicates the timestamp of
         last change to this row in tFPAccIngQGrpPCPOvrTable."
    ::= { tFPAccIngQGrpPCPOvrEntry 2 }

tFPAccIngQGrpPCPOvrMaxRate       OBJECT-TYPE
    SYNTAX      THPolPIRRateOverride
    UNITS       "kbps"
    MAX-ACCESS  read-create
    STATUS      current
    DESCRIPTION
        "The value of tFPAccIngQGrpPCPOvrMaxRate specifies the maximum frame
         based bandwidth limit of this policer override."
    DEFVAL      { -2 }
    ::= { tFPAccIngQGrpPCPOvrEntry 3 }

tFPAccIngQGrpPCPOvrMinMBSSep     OBJECT-TYPE
    SYNTAX      TPlcrBurstSizeBytesOverride
    UNITS       "bytes"
    MAX-ACCESS  read-create
    STATUS      current
    DESCRIPTION
        "The value of tFPAccIngQGrpPCPOvrMinMBSSep specifies the minimum amount
         of seperation buffer space (in bytes) allowed by this policer
         override."
    DEFVAL      { -2 }
    ::= { tFPAccIngQGrpPCPOvrEntry 4 }

tFPAccIngQGrpPCPOvrLvlTblLstChgd OBJECT-TYPE
    SYNTAX      TimeStamp
    MAX-ACCESS  read-only
    STATUS      current
    DESCRIPTION
        "tFPAccIngQGrpPCPOvrLvlTblLstChgd indicates the timestamp of last
         change to the tFPAccIngQGrpPCPOvrLvlTable."
    ::= { tmnxCardObjs 39 }

tFPAccIngQGrpPCPOvrLvlTable      OBJECT-TYPE
    SYNTAX      SEQUENCE OF TFPAccIngQGrpPCPOvrLvlEntry
    MAX-ACCESS  not-accessible
    STATUS      current
    DESCRIPTION
        "A table that contains forwarding plane access ingress policer control
         override information for the priority level."
    ::= { tmnxCardObjs 40 }

tFPAccIngQGrpPCPOvrLvlEntry      OBJECT-TYPE
    SYNTAX      TFPAccIngQGrpPCPOvrLvlEntry
    MAX-ACCESS  not-accessible
    STATUS      current
    DESCRIPTION
        "Policer control priority level override information about a specific
         forwarding plane on the access ingress side.

         Entries are created/deleted automatically by the system when entries
         are created/delete in the tFPAccIngQGrpPCPOvrTable."
    INDEX       {
        tmnxChassisIndex,
        tmnxCardSlotNum,
        tmnxFPNum,
        tmnxFPAccIngQGrpName,
        tmnxFPAccIngQGrpInstanceId,
        tFPAccIngQGrpPCPOvrLvl
    }
    ::= { tFPAccIngQGrpPCPOvrLvlTable 1 }

TFPAccIngQGrpPCPOvrLvlEntry      ::= SEQUENCE
{
    tFPAccIngQGrpPCPOvrLvl           TLevel,
    tFPAccIngQGrpPCPOvrLvlLastChgd   TimeStamp,
    tFPAccIngQGrpPCPOvrLvlMBS        TPlcrBurstSizeBytesOverride
}

tFPAccIngQGrpPCPOvrLvl           OBJECT-TYPE
    SYNTAX      TLevel
    MAX-ACCESS  not-accessible
    STATUS      current
    DESCRIPTION
        "The value of tFPAccIngQGrpPCPOvrLvl identifies the level of the
         policer control policy defined by tQosPolicerCtrlPolName."
    ::= { tFPAccIngQGrpPCPOvrLvlEntry 1 }

tFPAccIngQGrpPCPOvrLvlLastChgd   OBJECT-TYPE
    SYNTAX      TimeStamp
    MAX-ACCESS  read-only
    STATUS      current
    DESCRIPTION
        "The value of tFPAccIngQGrpPCPOvrLvlLastChgd indicates the timestamp of
         last change to this row in tFPAccIngQGrpPCPOvrLvlTable."
    ::= { tFPAccIngQGrpPCPOvrLvlEntry 2 }

tFPAccIngQGrpPCPOvrLvlMBS        OBJECT-TYPE
    SYNTAX      TPlcrBurstSizeBytesOverride
    UNITS       "bytes"
    MAX-ACCESS  read-create
    STATUS      current
    DESCRIPTION
        "The value of tFPAccIngQGrpPCPOvrLvlMBS specifies the maximum amount of
         cumulative buffer space (in bytes) allowed for this level by the
         policer of this level."
    DEFVAL      { -2 }
    ::= { tFPAccIngQGrpPCPOvrLvlEntry 3 }

tFPNetIngQGrpPCPOvrTblLastChgd   OBJECT-TYPE
    SYNTAX      TimeStamp
    MAX-ACCESS  read-only
    STATUS      current
    DESCRIPTION
        "tFPNetIngQGrpPCPOvrTblLastChgd indicates the timestamp of last change
         to the tFPNetIngQGrpPCPOvrTable."
    ::= { tmnxCardObjs 41 }

tFPNetIngQGrpPCPOvrTable         OBJECT-TYPE
    SYNTAX      SEQUENCE OF TFPNetIngQGrpPCPOvrEntry
    MAX-ACCESS  not-accessible
    STATUS      current
    DESCRIPTION
        "A table that contains forwarding plane ingress policer control
         override information."
    ::= { tmnxCardObjs 42 }

tFPNetIngQGrpPCPOvrEntry         OBJECT-TYPE
    SYNTAX      TFPNetIngQGrpPCPOvrEntry
    MAX-ACCESS  not-accessible
    STATUS      current
    DESCRIPTION
        "Policer control override information about a specific forwarding plane
         on the access ingress side."
    INDEX       {
        tmnxChassisIndex,
        tmnxCardSlotNum,
        tmnxFPNum,
        tmnxFPNetIngQGrpName,
        tmnxFPNetIngQGrpInstanceId
    }
    ::= { tFPNetIngQGrpPCPOvrTable 1 }

TFPNetIngQGrpPCPOvrEntry         ::= SEQUENCE
{
    tFPNetIngQGrpPCPOvrRowStatus     RowStatus,
    tFPNetIngQGrpPCPOvrLastChgd      TimeStamp,
    tFPNetIngQGrpPCPOvrMaxRate       THPolPIRRateOverride,
    tFPNetIngQGrpPCPOvrMinMBSSep     TPlcrBurstSizeBytesOverride
}

tFPNetIngQGrpPCPOvrRowStatus     OBJECT-TYPE
    SYNTAX      RowStatus
    MAX-ACCESS  read-create
    STATUS      current
    DESCRIPTION
        "This is the Row Status of the entry. This allows creation/deletion of
         rows in this table."
    ::= { tFPNetIngQGrpPCPOvrEntry 1 }

tFPNetIngQGrpPCPOvrLastChgd      OBJECT-TYPE
    SYNTAX      TimeStamp
    MAX-ACCESS  read-only
    STATUS      current
    DESCRIPTION
        "The value of tFPNetIngQGrpPCPOvrLastChgd indicates the timestamp of
         last change to this row in tFPNetIngQGrpPCPOvrTable."
    ::= { tFPNetIngQGrpPCPOvrEntry 2 }

tFPNetIngQGrpPCPOvrMaxRate       OBJECT-TYPE
    SYNTAX      THPolPIRRateOverride
    UNITS       "kbps"
    MAX-ACCESS  read-create
    STATUS      current
    DESCRIPTION
        "The value of tFPNetIngQGrpPCPOvrMaxRate specifies the maximum frame
         based bandwidth limit of this policer override."
    DEFVAL      { -2 }
    ::= { tFPNetIngQGrpPCPOvrEntry 3 }

tFPNetIngQGrpPCPOvrMinMBSSep     OBJECT-TYPE
    SYNTAX      TPlcrBurstSizeBytesOverride
    UNITS       "bytes"
    MAX-ACCESS  read-create
    STATUS      current
    DESCRIPTION
        "The value of tFPNetIngQGrpPCPOvrMinMBSSep specifies the minimum amount
         of seperation buffer space (in bytes) allowed by this policer
         override."
    DEFVAL      { -2 }
    ::= { tFPNetIngQGrpPCPOvrEntry 4 }

tFPNetIngQGrpPCPOvrLvlTblLstChgd OBJECT-TYPE
    SYNTAX      TimeStamp
    MAX-ACCESS  read-only
    STATUS      current
    DESCRIPTION
        "tFPNetIngQGrpPCPOvrLvlTblLstChgd indicates the timestamp of last
         change to the tFPNetIngQGrpPCPOvrLvlTable."
    ::= { tmnxCardObjs 43 }

tFPNetIngQGrpPCPOvrLvlTable      OBJECT-TYPE
    SYNTAX      SEQUENCE OF TFPNetIngQGrpPCPOvrLvlEntry
    MAX-ACCESS  not-accessible
    STATUS      current
    DESCRIPTION
        "A table that contains forwarding plane network ingress policer control
         override information for the priority level."
    ::= { tmnxCardObjs 44 }

tFPNetIngQGrpPCPOvrLvlEntry      OBJECT-TYPE
    SYNTAX      TFPNetIngQGrpPCPOvrLvlEntry
    MAX-ACCESS  not-accessible
    STATUS      current
    DESCRIPTION
        "Policer control priority level override information about a specific
         forwarding plane on the network ingress side.

         Entries are created/deleted automatically by the system when entries
         are created/delete in the tFPNetIngQGrpPCPOvrTable."
    INDEX       {
        tmnxChassisIndex,
        tmnxCardSlotNum,
        tmnxFPNum,
        tmnxFPNetIngQGrpName,
        tmnxFPNetIngQGrpInstanceId,
        tFPNetIngQGrpPCPOvrLvl
    }
    ::= { tFPNetIngQGrpPCPOvrLvlTable 1 }

TFPNetIngQGrpPCPOvrLvlEntry      ::= SEQUENCE
{
    tFPNetIngQGrpPCPOvrLvl           TLevel,
    tFPNetIngQGrpPCPOvrLvlLastChgd   TimeStamp,
    tFPNetIngQGrpPCPOvrLvlMBS        TPlcrBurstSizeBytesOverride
}

tFPNetIngQGrpPCPOvrLvl           OBJECT-TYPE
    SYNTAX      TLevel
    MAX-ACCESS  not-accessible
    STATUS      current
    DESCRIPTION
        "The value of tFPNetIngQGrpPCPOvrLvl identifies the level of the
         policer control policy defined by tQosPolicerCtrlPolName."
    ::= { tFPNetIngQGrpPCPOvrLvlEntry 1 }

tFPNetIngQGrpPCPOvrLvlLastChgd   OBJECT-TYPE
    SYNTAX      TimeStamp
    MAX-ACCESS  read-only
    STATUS      current
    DESCRIPTION
        "The value of tFPNetIngQGrpPCPOvrLvlLastChgd indicates the timestamp of
         last change to this row in tFPNetIngQGrpPCPOvrLvlTable."
    ::= { tFPNetIngQGrpPCPOvrLvlEntry 2 }

tFPNetIngQGrpPCPOvrLvlMBS        OBJECT-TYPE
    SYNTAX      TPlcrBurstSizeBytesOverride
    UNITS       "bytes"
    MAX-ACCESS  read-create
    STATUS      current
    DESCRIPTION
        "The value of tFPNetIngQGrpPCPOvrLvlMBS specifies the maximum amount of
         cumulative buffer space (in bytes) allowed for this level by the
         policer of this level."
    DEFVAL      { -2 }
    ::= { tFPNetIngQGrpPCPOvrLvlEntry 3 }

tCardResTable                    OBJECT-TYPE
    SYNTAX      SEQUENCE OF TCardResEntry
    MAX-ACCESS  not-accessible
    STATUS      current
    DESCRIPTION
        "The value of tCardResTable represents system resource information that
         are specific to a particular card on a given chassis."
    ::= { tmnxCardObjs 45 }

tCardResEntry                    OBJECT-TYPE
    SYNTAX      TCardResEntry
    MAX-ACCESS  not-accessible
    STATUS      current
    DESCRIPTION
        "The value of tCardResEntry represents card specific system resource
         information."
    INDEX       {
        tmnxChassisIndex,
        tmnxCardSlotNum
    }
    ::= { tCardResTable 1 }

TCardResEntry                    ::= SEQUENCE
{
    tCardResQosUserSchedsTotal       Unsigned32,
    tCardResQosUserSchedsAlloc       Unsigned32,
    tCardResQosIntSchedsTotal        Unsigned32,
    tCardResQosIntSchedsAlloc        Unsigned32,
    tCardResSubSPIQosOvrTotal        Unsigned32,
    tCardResSubSPIQosOvrAlloc        Unsigned32,
    tCardResHsmdaQOvrTotal           Unsigned32,
    tCardResHsmdaQOvrAlloc           Unsigned32,
    tCardResPortAccEgrQGrpInstTotal  Unsigned32,
    tCardResPortAccEgrQGrpInstAlloc  Unsigned32,
    tCardResPortNetEgrQGrpInstTotal  Unsigned32,
    tCardResPortNetEgrQGrpInstAlloc  Unsigned32,
    tCardResPortEgrQGrpInstTotal     Unsigned32,
    tCardResPortEgrQGrpInstAlloc     Unsigned32,
    tCardResFPIngQGrpInstTotal       Unsigned32,
    tCardResFPIngQGrpInstAlloc       Unsigned32,
    tCardResPortEgrVPortTotal        Unsigned32,
    tCardResPortEgrVPortAlloc        Unsigned32,
    tCardResQosUserSchedOvrsTotal    Unsigned32,
    tCardResQosUserSchedOvrsAlloc    Unsigned32,
    tCardResCategoryEntriesTotal     Unsigned32,
    tCardResCategoryEntriesAlloc     Unsigned32
}

tCardResQosUserSchedsTotal       OBJECT-TYPE
    SYNTAX      Unsigned32
    MAX-ACCESS  read-only
    STATUS      current
    DESCRIPTION
        "The value of tCardResQosUserSchedsTotal represents the total amount of
         QoS user virtual schedulers that are supported on this card.

         When the value of tCardResQosUserSchedsTotal is zero, it indicates
         that this resource type is not supported on this card."
    ::= { tCardResEntry 1 }

tCardResQosUserSchedsAlloc       OBJECT-TYPE
    SYNTAX      Unsigned32
    MAX-ACCESS  read-only
    STATUS      current
    DESCRIPTION
        "The value of tCardResQosUserSchedsAlloc represents the total number of
         QoS user virtual schedulers that are currently allocated on this card."
    ::= { tCardResEntry 2 }

tCardResQosIntSchedsTotal        OBJECT-TYPE
    SYNTAX      Unsigned32
    MAX-ACCESS  read-only
    STATUS      obsolete
    DESCRIPTION
        "The value of tCardResQosIntSchedsTotal represents the total number of
         QoS internal virtual schedulers that are supported on this card.

         When the value of tCardResQosIntSchedsTotal is zero, it indicates that
         this resource type is not supported on this card.

         This objects is obsoleted in 13.0 release."
    ::= { tCardResEntry 3 }

tCardResQosIntSchedsAlloc        OBJECT-TYPE
    SYNTAX      Unsigned32
    MAX-ACCESS  read-only
    STATUS      obsolete
    DESCRIPTION
        "The value of tCardResQosIntSchedsAlloc represents the total number of
         QoS internal virtual schedulers that are currently allocated on this
         card.

         This objects is obsoleted in 13.0 release."
    ::= { tCardResEntry 4 }

tCardResSubSPIQosOvrTotal        OBJECT-TYPE
    SYNTAX      Unsigned32
    MAX-ACCESS  read-only
    STATUS      current
    DESCRIPTION
        "The value of tCardResSubSPIQosOvrTotal represents the total number of
         QoS subscriber sla-profile instance overrides that are supported on
         this card.

         When the value of tCardResSubSPIQosOvrTotal is zero, it indicates that
         this resource type is not supported on this card."
    ::= { tCardResEntry 5 }

tCardResSubSPIQosOvrAlloc        OBJECT-TYPE
    SYNTAX      Unsigned32
    MAX-ACCESS  read-only
    STATUS      current
    DESCRIPTION
        "The value of tCardResSubSPIQosOvrAlloc represents the total number of
         QoS subscriber sla-profile instance overrides that are currently
         allocated on this card."
    ::= { tCardResEntry 6 }

tCardResHsmdaQOvrTotal           OBJECT-TYPE
    SYNTAX      Unsigned32
    MAX-ACCESS  read-only
    STATUS      current
    DESCRIPTION
        "The value of tCardResHsmdaQOvrTotal represents the total number of
         HSMDA queue overrides that are supported on this card.

         When the value of tCardResHsmdaQOvrTotal is zero, it indicates that
         this resource type is not supported on this card."
    ::= { tCardResEntry 7 }

tCardResHsmdaQOvrAlloc           OBJECT-TYPE
    SYNTAX      Unsigned32
    MAX-ACCESS  read-only
    STATUS      current
    DESCRIPTION
        "The value of tCardResHsmdaQOvrAlloc represents the total number of
         HSMDA queue overrides that are currently allocated on this card."
    ::= { tCardResEntry 8 }

tCardResPortAccEgrQGrpInstTotal  OBJECT-TYPE
    SYNTAX      Unsigned32
    MAX-ACCESS  read-only
    STATUS      current
    DESCRIPTION
        "The value of tCardResPortAccEgrQGrpInstTotal represents the total
         number of port access egress queue-group instances across all ports on
         this card that are allowed to be provisioned.

         When the value of tCardResPortAccEgrQGrpInstTotal is zero, it
         indicates that this resource type is not supported on this card."
    ::= { tCardResEntry 9 }

tCardResPortAccEgrQGrpInstAlloc  OBJECT-TYPE
    SYNTAX      Unsigned32
    MAX-ACCESS  read-only
    STATUS      current
    DESCRIPTION
        "The value of tCardResPortAccEgrQGrpInstAlloc represents the total
         number of port access egress queue-group instances across all ports on
         this card that are currently provisioned."
    ::= { tCardResEntry 10 }

tCardResPortNetEgrQGrpInstTotal  OBJECT-TYPE
    SYNTAX      Unsigned32
    MAX-ACCESS  read-only
    STATUS      current
    DESCRIPTION
        "The value of tCardResPortNetEgrQGrpInstTotal represents the total
         number of port network egress queue-group instances across all ports
         on this card that are allowed to be provisioned.

         When the value of tCardResPortNetEgrQGrpInstTotal is zero, it
         indicates that this resource type is not supported on this card."
    ::= { tCardResEntry 11 }

tCardResPortNetEgrQGrpInstAlloc  OBJECT-TYPE
    SYNTAX      Unsigned32
    MAX-ACCESS  read-only
    STATUS      current
    DESCRIPTION
        "The value of tCardResPortNetEgrQGrpInstAlloc represents the total
         number of port network egress queue-group instances across all ports
         on this card that are currently provisioned."
    ::= { tCardResEntry 12 }

tCardResPortEgrQGrpInstTotal     OBJECT-TYPE
    SYNTAX      Unsigned32
    MAX-ACCESS  read-only
    STATUS      current
    DESCRIPTION
        "The value of tCardResPortEgrQGrpInstTotal represents the total number
         of port egress queue-group instances across all ports on this card
         including access and network instances that are allowed to be
         provisioned.

         When the value of tCardResPortEgrQGrpInstTotal is zero, it indicates
         that this resource type is not supported on this card."
    ::= { tCardResEntry 13 }

tCardResPortEgrQGrpInstAlloc     OBJECT-TYPE
    SYNTAX      Unsigned32
    MAX-ACCESS  read-only
    STATUS      current
    DESCRIPTION
        "The value of tCardResPortEgrQGrpInstAlloc represents the total number
         of port egress queue-group instances across all ports on this card
         including access and network instances that are currently provisioned."
    ::= { tCardResEntry 14 }

tCardResFPIngQGrpInstTotal       OBJECT-TYPE
    SYNTAX      Unsigned32
    MAX-ACCESS  read-only
    STATUS      current
    DESCRIPTION
        "The value of tCardResFPIngQGrpInstTotal represents the total number of
         forwarding-plane (FP) ingress queue-group instances across all FP on
         this card including access and network instances that are allowed to
         be provisioned.

         When the value of tCardResFPIngQGrpInstTotal is zero, it indicates
         that this resource type is not supported on this card."
    ::= { tCardResEntry 15 }

tCardResFPIngQGrpInstAlloc       OBJECT-TYPE
    SYNTAX      Unsigned32
    MAX-ACCESS  read-only
    STATUS      current
    DESCRIPTION
        "The value of tCardResFPIngQGrpInstAlloc represents the total number of
         forwarding-plane (FP) ingress queue-group instances across all FP on
         this card including access and network instances that are currently
         provisioned."
    ::= { tCardResEntry 16 }

tCardResPortEgrVPortTotal        OBJECT-TYPE
    SYNTAX      Unsigned32
    MAX-ACCESS  read-only
    STATUS      current
    DESCRIPTION
        "The value of tCardResPortEgrVPortTotal represents the total number of
         egress virtual ports across all ports on this card that are allowed to
         be provisioned.

         When the value of tCardResPortEgrVPortTotal is zero, it indicates that
         this resource type is not supported on this card."
    ::= { tCardResEntry 17 }

tCardResPortEgrVPortAlloc        OBJECT-TYPE
    SYNTAX      Unsigned32
    MAX-ACCESS  read-only
    STATUS      current
    DESCRIPTION
        "The value of tCardResPortEgrVPortAlloc represents the total number of
         egress virtual ports across all ports on this card that are currently
         provisioned."
    ::= { tCardResEntry 18 }

tCardResQosUserSchedOvrsTotal    OBJECT-TYPE
    SYNTAX      Unsigned32
    MAX-ACCESS  read-only
    STATUS      current
    DESCRIPTION
        "The value of tCardResQosUserSchedOvrsTotal represents the total amount
         of QoS user virtual scheduler overrides that are supported on this
         card.

         When the value of tCardResQosUserSchedOvrsTotal is zero, it indicates
         that this resource type is not supported on this card."
    ::= { tCardResEntry 19 }

tCardResQosUserSchedOvrsAlloc    OBJECT-TYPE
    SYNTAX      Unsigned32
    MAX-ACCESS  read-only
    STATUS      current
    DESCRIPTION
        "The value of tCardResQosUserSchedOvrsAlloc represents the total number
         of QoS user virtual scheduler overrides that are currently allocated
         on this card."
    ::= { tCardResEntry 20 }

tCardResCategoryEntriesTotal     OBJECT-TYPE
    SYNTAX      Unsigned32
    MAX-ACCESS  read-only
    STATUS      current
    DESCRIPTION
        "The value of tCardResCategoryEntriesTotal indicates the total number
         of subscriber category entries currently associated with this card."
    ::= { tCardResEntry 21 }

tCardResCategoryEntriesAlloc     OBJECT-TYPE
    SYNTAX      Unsigned32
    MAX-ACCESS  read-only
    STATUS      current
    DESCRIPTION
        "The value of tCardResCategoryEntriesAlloc indicates the total number
         of subscriber category entries that are currently allocated on this
         card."
    ::= { tCardResEntry 22 }

tFPResTable                      OBJECT-TYPE
    SYNTAX      SEQUENCE OF TFPResEntry
    MAX-ACCESS  not-accessible
    STATUS      current
    DESCRIPTION
        "The value of tFPResTable represents system resource information that
         are specific to forwarding plane (FP) for a particular card on a given
         chassis."
    ::= { tmnxCardObjs 46 }

tFPResEntry                      OBJECT-TYPE
    SYNTAX      TFPResEntry
    MAX-ACCESS  not-accessible
    STATUS      current
    DESCRIPTION
        "The value of tFPResEntry represents forwarding plane (FP) specific
         system resource information."
    INDEX       {
        tmnxChassisIndex,
        tmnxCardSlotNum,
        tmnxFPNum
    }
    ::= { tFPResTable 1 }

TFPResEntry                      ::= SEQUENCE
{
    tFPResSapIngQosPolTotal          Unsigned32,
    tFPResSapIngQosPolAlloc          Unsigned32,
    tFPResDynEgrClassTotal           Unsigned32,
    tFPResDynEgrClassAlloc           Unsigned32,
    tFPResDynEgrClassIUBSE           Unsigned32,
    tFPResDynEgrClassIUBNE           Unsigned32,
    tFPResIngQueueTotal              Unsigned32,
    tFPResIngQueueAlloc              Unsigned32,
    tFPResEgrQueueTotal              Unsigned32,
    tFPResEgrQueueAlloc              Unsigned32,
    tFPResIngPolicerTotal            Unsigned32,
    tFPResIngPolicerAlloc            Unsigned32,
    tFPResEgrPolicerTotal            Unsigned32,
    tFPResEgrPolicerAlloc            Unsigned32,
    tFPResIngPolicerStatTotal        Unsigned32,
    tFPResIngPolicerStatAlloc        Unsigned32,
    tFPResEgrPolicerStatTotal        Unsigned32,
    tFPResEgrPolicerStatAlloc        Unsigned32,
    tFPResIngRootArbiterTotal        Unsigned32,
    tFPResIngRootArbiterAlloc        Unsigned32,
    tFPResEgrRootArbiterTotal        Unsigned32,
    tFPResEgrRootArbiterAlloc        Unsigned32,
    tFPResIntArbiterTotal            Unsigned32,
    tFPResIntArbiterAlloc            Unsigned32,
    tFPResDynQueueTotal              Unsigned32,
    tFPResDynQueueAlloc              Unsigned32,
    tFPResDynQueueIUBI               Unsigned32,
    tFPResDynQueueIUBE               Unsigned32,
    tFPResDynPolicerTotal            Unsigned32,
    tFPResDynPolicerAlloc            Unsigned32,
    tFPResDynPolicerIUBI             Unsigned32,
    tFPResDynPolicerIUBE             Unsigned32,
    tFPResDynPolicerStatTotal        Unsigned32,
    tFPResDynPolicerStatAlloc        Unsigned32,
    tFPResDynPolicerStatIUBI         Unsigned32,
    tFPResDynPolicerStatIUBE         Unsigned32,
    tFPResIngAclEntryTotal           Unsigned32,
    tFPResIngAclEntryAlloc           Unsigned32,
    tFPResIngQosEntryTotal           Unsigned32,
    tFPResIngQosEntryAlloc           Unsigned32,
    tFPResIngAclQosEntryTotal        Unsigned32,
    tFPResIngAclQosEntryAlloc        Unsigned32,
    tFPResIngIPv6AclEntryTotal       Unsigned32,
    tFPResIngIPv6AclEntryAlloc       Unsigned32,
    tFPResIngIPv6QosEntryTotal       Unsigned32,
    tFPResIngIPv6QosEntryAlloc       Unsigned32,
    tFPResEgrAclEntryTotal           Unsigned32,
    tFPResEgrAclEntryAlloc           Unsigned32,
    tFPResEgrQosEntryTotal           Unsigned32,
    tFPResEgrQosEntryAlloc           Unsigned32,
    tFPResEgrAclQosEntryTotal        Unsigned32,
    tFPResEgrAclQosEntryAlloc        Unsigned32,
    tFPResEgrIPv6AclEntryTotal       Unsigned32,
    tFPResEgrIPv6AclEntryAlloc       Unsigned32,
    tFPResEgrIPv6QosEntryTotal       Unsigned32,
    tFPResEgrIPv6QosEntryAlloc       Unsigned32,
    tFPResIngAclFilterTotal          Unsigned32,
    tFPResIngAclFilterAlloc          Unsigned32,
    tFPResEgrAclFilterTotal          Unsigned32,
    tFPResEgrAclFilterAlloc          Unsigned32,
    tFPResDynSvcEntryTotal           Unsigned32,
    tFPResDynSvcEntryAlloc           Unsigned32,
    tFPResSubHostTotal               Unsigned32,
    tFPResSubHostAlloc               Unsigned32,
    tFPResEncapGrpMemberTotal        Unsigned32,
    tFPResEncapGrpMemberAlloc        Unsigned32,
    tFPResEgrNetQGrpMapTotal         Unsigned32,
    tFPResEgrNetQGrpMapAlloc         Unsigned32,
    tFPResMacFdbRecTotal             Unsigned32,
    tFPResMacFdbRecAlloc             Unsigned32,
    tFPResResRvplsFdbRecTotal        Unsigned32,
    tFPResResRvplsFdbRecAlloc        Unsigned32,
    tFPResDynQ2NamedPoolTotal        Unsigned32,
    tFPResDynQ2NamedPoolAlloc        Unsigned32,
    tFPResDynQ2NamedPoolIUBI         Unsigned32,
    tFPResDynQ2NamedPoolIUBE         Unsigned32,
    tFPResIngQ1NamedPoolTotal        Unsigned32,
    tFPResIngQ1NamedPoolAlloc        Unsigned32,
    tFPResEgrQ1NamedPoolTotal        Unsigned32,
    tFPResEgrQ1NamedPoolAlloc        Unsigned32,
    tFPResDynQ2WredPoolTotal         Unsigned32,
    tFPResDynQ2WredPoolAlloc         Unsigned32,
    tFPResIngIPv6AclFilterTotal      Unsigned32,
    tFPResIngIPv6AclFilterAlloc      Unsigned32,
    tFPResEgrIPv6AclFilterTotal      Unsigned32,
    tFPResEgrIPv6AclFilterAlloc      Unsigned32,
    tFPResEgrQosBypassTotal          Unsigned32,
    tFPResEgrQosBypassAlloc          Unsigned32,
    tFPResSapInstanceTotal           Unsigned32,
    tFPResSapInstanceAlloc           Unsigned32,
    tFPResEgrHsQGrpTotal             Unsigned32,
    tFPResEgrHsQGrpAlloc             Unsigned32,
    tFPResEgrHsPrimaryShapersTotal   Unsigned32,
    tFPResEgrHsPrimaryShapersAlloc   Unsigned32,
    tFPResEgrHsPrimaryShapersIUBES   Unsigned32,
    tFPResEgrHsPrimaryShapersIUBMS   Unsigned32,
    tFPResEgrHsSecondaryShapersTotal Unsigned32,
    tFPResEgrHsSecondaryShapersAlloc Unsigned32,
    tFPResEgrHsTurboQGrpTotal        Unsigned32,
    tFPResEgrHsTurboQGrpAlloc        Unsigned32,
    tFPResIngQGrpRedirTotal          Unsigned32,
    tFPResIngQGrpRedirAlloc          Unsigned32,
    tFPResSapInstEgrQGrpRedirTotal   Unsigned32,
    tFPResSapInstEgrQGrpRedirAlloc   Unsigned32
}

tFPResSapIngQosPolTotal          OBJECT-TYPE
    SYNTAX      Unsigned32
    MAX-ACCESS  read-only
    STATUS      current
    DESCRIPTION
        "The value of tFPResSapIngQosPolTotal represents the total number of
         sap-ingress QoS policies that are allowed to be in use on this FP."
    ::= { tFPResEntry 1 }

tFPResSapIngQosPolAlloc          OBJECT-TYPE
    SYNTAX      Unsigned32
    MAX-ACCESS  read-only
    STATUS      current
    DESCRIPTION
        "The value of tFPResSapIngQosPolAlloc represents the total number of
         sap-ingress QoS policies that are currently allocated on this FP."
    ::= { tFPResEntry 2 }

tFPResDynEgrClassTotal           OBJECT-TYPE
    SYNTAX      Unsigned32
    MAX-ACCESS  read-only
    STATUS      current
    DESCRIPTION
        "The value of tFPResDynEgrClassTotal represents the total number of QoS
         dynamic egress classification resources that are allowed to be in use
         on this FP."
    ::= { tFPResEntry 3 }

tFPResDynEgrClassAlloc           OBJECT-TYPE
    SYNTAX      Unsigned32
    MAX-ACCESS  read-only
    STATUS      current
    DESCRIPTION
        "The value of tFPResDynEgrClassAlloc represents the total number of QoS
         dynamic egress classification resources that are currently allocated
         on this FP."
    ::= { tFPResEntry 4 }

tFPResDynEgrClassIUBSE           OBJECT-TYPE
    SYNTAX      Unsigned32
    MAX-ACCESS  read-only
    STATUS      current
    DESCRIPTION
        "The value of tFPResDynEgrClassIUBSE represents the subset of resources
         which are currently in use by sap-egress QoS policies out of currently
         allocated QoS dynamic egress classification resources,
         tFPResDynEgrClassAlloc."
    ::= { tFPResEntry 5 }

tFPResDynEgrClassIUBNE           OBJECT-TYPE
    SYNTAX      Unsigned32
    MAX-ACCESS  read-only
    STATUS      current
    DESCRIPTION
        "The value of tFPResDynEgrClassIUBNE represents the subset of resources
         which are currently in use by network egress QoS classification out of
         currently allocated QoS dynamic egress classification resources,
         tFPResDynEgrClassAlloc.

         A network egress QoS classification resource is consumed whenever a
         network QoS policy has at least one egress DSCP or prec classification
         rule provisioned."
    ::= { tFPResEntry 6 }

tFPResIngQueueTotal              OBJECT-TYPE
    SYNTAX      Unsigned32
    MAX-ACCESS  read-only
    STATUS      current
    DESCRIPTION
        "The value of tFPResIngQueueTotal represents the total number of
         ingress queues that are supported on this FP.

         When the value of tFPResIngQueueTotal is zero, it indicates that this
         resource type is not supported on this FP."
    ::= { tFPResEntry 7 }

tFPResIngQueueAlloc              OBJECT-TYPE
    SYNTAX      Unsigned32
    MAX-ACCESS  read-only
    STATUS      current
    DESCRIPTION
        "The value of tFPResIngQueueAlloc represents the total number of
         ingress queues that are currently allocated on this FP."
    ::= { tFPResEntry 8 }

tFPResEgrQueueTotal              OBJECT-TYPE
    SYNTAX      Unsigned32
    MAX-ACCESS  read-only
    STATUS      current
    DESCRIPTION
        "The value of tFPResEgrQueueTotal represents the total number of egress
         queues that are supported on this FP.

         When the value of tFPResEgrQueueTotal is zero, it indicates that this
         resource type is not supported on this FP."
    ::= { tFPResEntry 9 }

tFPResEgrQueueAlloc              OBJECT-TYPE
    SYNTAX      Unsigned32
    MAX-ACCESS  read-only
    STATUS      current
    DESCRIPTION
        "The value of tFPResEgrQueueAlloc represents the total number of egress
         queues that are currently allocated on this FP."
    ::= { tFPResEntry 10 }

tFPResIngPolicerTotal            OBJECT-TYPE
    SYNTAX      Unsigned32
    MAX-ACCESS  read-only
    STATUS      current
    DESCRIPTION
        "The value of tFPResIngPolicerTotal represents the total number of
         ingress policers that are supported on this FP.

         When the value of tFPResIngPolicerTotal is zero, it indicates that
         this resource type is not supported on this FP."
    ::= { tFPResEntry 11 }

tFPResIngPolicerAlloc            OBJECT-TYPE
    SYNTAX      Unsigned32
    MAX-ACCESS  read-only
    STATUS      current
    DESCRIPTION
        "The value of tFPResIngPolicerAlloc represents the total number of
         ingress policers that are currently allocated on this FP."
    ::= { tFPResEntry 12 }

tFPResEgrPolicerTotal            OBJECT-TYPE
    SYNTAX      Unsigned32
    MAX-ACCESS  read-only
    STATUS      current
    DESCRIPTION
        "The value of tFPResEgrPolicerTotal represents the total number of
         egress policers that are supported on this FP.

         When the value of tFPResEgrPolicerTotal is zero, it indicates that
         this resource type is not supported on this FP."
    ::= { tFPResEntry 13 }

tFPResEgrPolicerAlloc            OBJECT-TYPE
    SYNTAX      Unsigned32
    MAX-ACCESS  read-only
    STATUS      current
    DESCRIPTION
        "The value of tFPResEgrPolicerAlloc represents the total number of
         egress policers that are currently allocated on this FP."
    ::= { tFPResEntry 14 }

tFPResIngPolicerStatTotal        OBJECT-TYPE
    SYNTAX      Unsigned32
    MAX-ACCESS  read-only
    STATUS      current
    DESCRIPTION
        "The value of tFPResIngPolicerStatTotal represents the total number of
         ingress policer stats that are supported on this FP.

         When the value of tFPResIngPolicerStatTotal is zero, it indicates that
         this resource type is not supported on this FP."
    ::= { tFPResEntry 15 }

tFPResIngPolicerStatAlloc        OBJECT-TYPE
    SYNTAX      Unsigned32
    MAX-ACCESS  read-only
    STATUS      current
    DESCRIPTION
        "The value of tFPResIngPolicerStatAlloc represents the total number of
         ingress policer stats that are currently allocated on this FP."
    ::= { tFPResEntry 16 }

tFPResEgrPolicerStatTotal        OBJECT-TYPE
    SYNTAX      Unsigned32
    MAX-ACCESS  read-only
    STATUS      current
    DESCRIPTION
        "The value of tFPResEgrPolicerStatTotal represents the total number of
         egress policer stats that are supported on this FP.

         When the value of tFPResEgrPolicerStatTotal is zero, it indicates that
         this resource type is not supported on this FP."
    ::= { tFPResEntry 17 }

tFPResEgrPolicerStatAlloc        OBJECT-TYPE
    SYNTAX      Unsigned32
    MAX-ACCESS  read-only
    STATUS      current
    DESCRIPTION
        "The value of tFPResEgrPolicerStatAlloc represents the total number of
         egress policer stats that are currently allocated on this FP."
    ::= { tFPResEntry 18 }

tFPResIngRootArbiterTotal        OBJECT-TYPE
    SYNTAX      Unsigned32
    MAX-ACCESS  read-only
    STATUS      current
    DESCRIPTION
        "The value of tFPResIngRootArbiterTotal represents the total number of
         ingress root arbiters that are supported on this FP.

         When the value of tFPResIngRootArbiterTotal is zero, it indicates that
         this resource type is not supported on this FP."
    ::= { tFPResEntry 19 }

tFPResIngRootArbiterAlloc        OBJECT-TYPE
    SYNTAX      Unsigned32
    MAX-ACCESS  read-only
    STATUS      current
    DESCRIPTION
        "The value of tFPResIngRootArbiterAlloc represents the total number of
         ingress root arbiters that are currently allocated on this FP."
    ::= { tFPResEntry 20 }

tFPResEgrRootArbiterTotal        OBJECT-TYPE
    SYNTAX      Unsigned32
    MAX-ACCESS  read-only
    STATUS      current
    DESCRIPTION
        "The value of tFPResEgrRootArbiterTotal represents the total number of
         egress root arbiters that are supported on this FP.

         When the value of tFPResEgrRootArbiterTotal is zero, it indicates that
         this resource type is not supported on this FP."
    ::= { tFPResEntry 21 }

tFPResEgrRootArbiterAlloc        OBJECT-TYPE
    SYNTAX      Unsigned32
    MAX-ACCESS  read-only
    STATUS      current
    DESCRIPTION
        "The value of tFPResEgrRootArbiterAlloc represents the total number of
         egress root arbiters that are currently allocated on this FP."
    ::= { tFPResEntry 22 }

tFPResIntArbiterTotal            OBJECT-TYPE
    SYNTAX      Unsigned32
    MAX-ACCESS  read-only
    STATUS      current
    DESCRIPTION
        "The value of tFPResIntArbiterTotal represents the total number of
         intermediate arbiters that are supported on this FP.

         When the value of tFPResIntArbiterTotal is zero, it indicates that
         this resource type is not supported on this FP."
    ::= { tFPResEntry 23 }

tFPResIntArbiterAlloc            OBJECT-TYPE
    SYNTAX      Unsigned32
    MAX-ACCESS  read-only
    STATUS      current
    DESCRIPTION
        "The value of tFPResIntArbiterAlloc represents the total number of
         intermediate arbiters that are currently allocated on this FP."
    ::= { tFPResEntry 24 }

tFPResDynQueueTotal              OBJECT-TYPE
    SYNTAX      Unsigned32
    MAX-ACCESS  read-only
    STATUS      current
    DESCRIPTION
        "The value of tFPResDynQueueTotal represents the total number of
         dynamic queues that are supported on this FP.

         When the value of tFPResEgrRootArbiterTotal is zero, it indicates that
         this resource type is not supported on this FP."
    ::= { tFPResEntry 25 }

tFPResDynQueueAlloc              OBJECT-TYPE
    SYNTAX      Unsigned32
    MAX-ACCESS  read-only
    STATUS      current
    DESCRIPTION
        "The value of tFPResDynQueueAlloc represents the total number of
         dynamic queues that are currently allocated on this FP."
    ::= { tFPResEntry 26 }

tFPResDynQueueIUBI               OBJECT-TYPE
    SYNTAX      Unsigned32
    MAX-ACCESS  read-only
    STATUS      current
    DESCRIPTION
        "The value of tFPResDynQueueIUBI represents the subset of resources
         which are currently in use by ingress queues out of currently
         allocated dynamic queue resources, tFPResDynQueueAlloc."
    ::= { tFPResEntry 27 }

tFPResDynQueueIUBE               OBJECT-TYPE
    SYNTAX      Unsigned32
    MAX-ACCESS  read-only
    STATUS      current
    DESCRIPTION
        "The value of tFPResDynQueueIUBE represents the subset of resources
         which are currently in use by egress queues out of currently allocated
         dynamic queue resources, tFPResDynQueueAlloc."
    ::= { tFPResEntry 28 }

tFPResDynPolicerTotal            OBJECT-TYPE
    SYNTAX      Unsigned32
    MAX-ACCESS  read-only
    STATUS      current
    DESCRIPTION
        "The value of tFPResDynPolicerTotal represents the total number of
         dynamic policer that are supported on this FP.

         When the value of tFPResDynPolicerTotal is zero, it indicates that
         this resource type is not supported on this FP."
    ::= { tFPResEntry 29 }

tFPResDynPolicerAlloc            OBJECT-TYPE
    SYNTAX      Unsigned32
    MAX-ACCESS  read-only
    STATUS      current
    DESCRIPTION
        "The value of tFPResDynPolicerAlloc represents the total number of
         dynamic policers that are currently allocated on this FP."
    ::= { tFPResEntry 30 }

tFPResDynPolicerIUBI             OBJECT-TYPE
    SYNTAX      Unsigned32
    MAX-ACCESS  read-only
    STATUS      current
    DESCRIPTION
        "The value of tFPResDynPolicerIUBI represents the subset of resources
         which are currently in use by ingress policer out of currently
         allocated dynamic policer resources, tFPResDynPolicerAlloc."
    ::= { tFPResEntry 31 }

tFPResDynPolicerIUBE             OBJECT-TYPE
    SYNTAX      Unsigned32
    MAX-ACCESS  read-only
    STATUS      current
    DESCRIPTION
        "The value of tFPResDynPolicerIUBE represents the subset of resources
         which are currently in use by egress policer out of currently
         allocated dynamic policer resources, tFPResDynPolicerAlloc."
    ::= { tFPResEntry 32 }

tFPResDynPolicerStatTotal        OBJECT-TYPE
    SYNTAX      Unsigned32
    MAX-ACCESS  read-only
    STATUS      current
    DESCRIPTION
        "The value of tFPResDynPolicerStatTotal represents the total number of
         dynamic policer stats that are supported on this FP.

         When the value of tFPResDynPolicerStatTotal is zero, it indicates that
         this resource type is not supported on this FP."
    ::= { tFPResEntry 33 }

tFPResDynPolicerStatAlloc        OBJECT-TYPE
    SYNTAX      Unsigned32
    MAX-ACCESS  read-only
    STATUS      current
    DESCRIPTION
        "The value of tFPResDynPolicerStatAlloc represents the total number of
         dynamic policers stats that are currently allocated on this FP."
    ::= { tFPResEntry 34 }

tFPResDynPolicerStatIUBI         OBJECT-TYPE
    SYNTAX      Unsigned32
    MAX-ACCESS  read-only
    STATUS      current
    DESCRIPTION
        "The value of tFPResDynPolicerStatIUBI represents the subset of
         resources which are currently in use by ingress policer stats out of
         currently allocated dynamic policer stats resources,
         tFPResDynPolicerStatAlloc."
    ::= { tFPResEntry 35 }

tFPResDynPolicerStatIUBE         OBJECT-TYPE
    SYNTAX      Unsigned32
    MAX-ACCESS  read-only
    STATUS      current
    DESCRIPTION
        "The value of tFPResDynPolicerStatIUBE represents the subset of
         resources which are currently in use by egress policer stats out of
         currently allocated dynamic policer stats resources,
         tFPResDynPolicerStatAlloc."
    ::= { tFPResEntry 36 }

tFPResIngAclEntryTotal           OBJECT-TYPE
    SYNTAX      Unsigned32
    MAX-ACCESS  read-only
    STATUS      current
    DESCRIPTION
        "The value of tFPResIngAclEntryTotal represents the total number of
         ingress ACL CAM entries that are supported on this FP.

         When the value of tFPResIngAclEntryTotal is zero, it indicates that
         this resource type is not supported on this FP."
    ::= { tFPResEntry 37 }

tFPResIngAclEntryAlloc           OBJECT-TYPE
    SYNTAX      Unsigned32
    MAX-ACCESS  read-only
    STATUS      current
    DESCRIPTION
        "The value of tFPResIngAclEntryAlloc represents the total number of
         ingress ACL CAM entries that are currently allocated on this FP."
    ::= { tFPResEntry 38 }

tFPResIngQosEntryTotal           OBJECT-TYPE
    SYNTAX      Unsigned32
    MAX-ACCESS  read-only
    STATUS      current
    DESCRIPTION
        "The value of tFPResIngQosEntryTotal represents the total number of
         ingress QoS CAM entries that are supported on this FP.

         When the value of tFPResIngQosEntryTotal is zero, it indicates that
         this resource type is not supported on this FP."
    ::= { tFPResEntry 39 }

tFPResIngQosEntryAlloc           OBJECT-TYPE
    SYNTAX      Unsigned32
    MAX-ACCESS  read-only
    STATUS      current
    DESCRIPTION
        "The value of tFPResIngQosEntryAlloc represents the total number of
         ingress QoS CAM entries that are currently allocated on this FP."
    ::= { tFPResEntry 40 }

tFPResIngAclQosEntryTotal        OBJECT-TYPE
    SYNTAX      Unsigned32
    MAX-ACCESS  read-only
    STATUS      current
    DESCRIPTION
        "The value of tFPResIngAclQosEntryTotal represents the total number of
         combined ingress ACL and QoS CAM entries that are supported on this
         FP.

         When the value of tFPResIngAclQosEntryTotal is zero, it indicates that
         this resource type is not supported on this FP."
    ::= { tFPResEntry 41 }

tFPResIngAclQosEntryAlloc        OBJECT-TYPE
    SYNTAX      Unsigned32
    MAX-ACCESS  read-only
    STATUS      current
    DESCRIPTION
        "The value of tFPResIngAclQosEntryAlloc represents the total number of
         combined ingress ACL and QoS CAM entries that are currently allocated
         on this FP."
    ::= { tFPResEntry 42 }

tFPResIngIPv6AclEntryTotal       OBJECT-TYPE
    SYNTAX      Unsigned32
    MAX-ACCESS  read-only
    STATUS      current
    DESCRIPTION
        "The value of tFPResIngIPv6AclEntryTotal represents the total number of
         IPv6 ingress ACL CAM entries that are supported on this FP.

         When the value of tFPResIngIPv6AclEntryTotal is zero, it indicates
         that this resource type is not supported on this FP."
    ::= { tFPResEntry 43 }

tFPResIngIPv6AclEntryAlloc       OBJECT-TYPE
    SYNTAX      Unsigned32
    MAX-ACCESS  read-only
    STATUS      current
    DESCRIPTION
        "The value of tFPResIngIPv6AclEntryAlloc represents the total number of
         IPv6 ingress ACL CAM entries that are currently allocated on this FP."
    ::= { tFPResEntry 44 }

tFPResIngIPv6QosEntryTotal       OBJECT-TYPE
    SYNTAX      Unsigned32
    MAX-ACCESS  read-only
    STATUS      current
    DESCRIPTION
        "The value of tFPResIngIPv6QosEntryTotal represents the total number of
         IPv6 ingress QoS CAM entries that are supported on this FP.

         When the value of tFPResIngIPv6QosEntryTotal is zero, it indicates
         that this resource type is not supported on this FP."
    ::= { tFPResEntry 45 }

tFPResIngIPv6QosEntryAlloc       OBJECT-TYPE
    SYNTAX      Unsigned32
    MAX-ACCESS  read-only
    STATUS      current
    DESCRIPTION
        "The value of tFPResIngIPv6QosEntryAlloc represents the total number of
         IPv6 ingress QoS CAM entries that are currently allocated on this FP."
    ::= { tFPResEntry 46 }

tFPResEgrAclEntryTotal           OBJECT-TYPE
    SYNTAX      Unsigned32
    MAX-ACCESS  read-only
    STATUS      current
    DESCRIPTION
        "The value of tFPResEgrAclEntryTotal represents the total number of
         egress ACL CAM entries that are supported on this FP.

         When the value of tFPResEgrAclEntryTotal is zero, it indicates that
         this resource type is not supported on this FP."
    ::= { tFPResEntry 47 }

tFPResEgrAclEntryAlloc           OBJECT-TYPE
    SYNTAX      Unsigned32
    MAX-ACCESS  read-only
    STATUS      current
    DESCRIPTION
        "The value of tFPResEgrAclEntryAlloc represents the total number of
         egress ACL CAM entries that are currently allocated on this FP."
    ::= { tFPResEntry 48 }

tFPResEgrQosEntryTotal           OBJECT-TYPE
    SYNTAX      Unsigned32
    MAX-ACCESS  read-only
    STATUS      current
    DESCRIPTION
        "The value of tFPResEgrQosEntryTotal represents the total number of
         egress QoS CAM entries that are supported on this FP.

         When the value of tFPResEgrQosEntryTotal is zero, it indicates that
         this resource type is not supported on this FP."
    ::= { tFPResEntry 49 }

tFPResEgrQosEntryAlloc           OBJECT-TYPE
    SYNTAX      Unsigned32
    MAX-ACCESS  read-only
    STATUS      current
    DESCRIPTION
        "The value of tFPResEgrQosEntryAlloc represents the total number of
         egress QoS CAM entries that are currently allocated on this FP."
    ::= { tFPResEntry 50 }

tFPResEgrAclQosEntryTotal        OBJECT-TYPE
    SYNTAX      Unsigned32
    MAX-ACCESS  read-only
    STATUS      current
    DESCRIPTION
        "The value of tFPResEgrAclQosEntryTotal represents the total number of
         combined egress ACL and QoS CAM entries that are supported on this FP.

         When the value of tFPResEgrAclQosEntryTotal is zero, it indicates that
         this resource type is not supported on this FP."
    ::= { tFPResEntry 51 }

tFPResEgrAclQosEntryAlloc        OBJECT-TYPE
    SYNTAX      Unsigned32
    MAX-ACCESS  read-only
    STATUS      current
    DESCRIPTION
        "The value of tFPResEgrAclQosEntryAlloc represents the total number of
         combined egress ACL and QoS CAM entries that are currently allocated
         on this FP."
    ::= { tFPResEntry 52 }

tFPResEgrIPv6AclEntryTotal       OBJECT-TYPE
    SYNTAX      Unsigned32
    MAX-ACCESS  read-only
    STATUS      current
    DESCRIPTION
        "The value of tFPResEgrIPv6AclEntryTotal represents the total number of
         IPv6 egress ACL CAM entries that are supported on this FP.

         When the value of tFPResEgrIPv6AclEntryTotal is zero, it indicates
         that this resource type is not supported on this FP."
    ::= { tFPResEntry 53 }

tFPResEgrIPv6AclEntryAlloc       OBJECT-TYPE
    SYNTAX      Unsigned32
    MAX-ACCESS  read-only
    STATUS      current
    DESCRIPTION
        "The value of tFPResEgrIPv6AclEntryAlloc represents the total number of
         IPv6 egress ACL CAM entries that are currently allocated on this FP."
    ::= { tFPResEntry 54 }

tFPResEgrIPv6QosEntryTotal       OBJECT-TYPE
    SYNTAX      Unsigned32
    MAX-ACCESS  read-only
    STATUS      current
    DESCRIPTION
        "The value of tFPResEgrIPv6QosEntryTotal represents the total number of
         IPv6 egress QoS CAM entries that are supported on this FP.

         When the value of tFPResEgrIPv6QosEntryTotal is zero, it indicates
         that this resource type is not supported on this FP."
    ::= { tFPResEntry 55 }

tFPResEgrIPv6QosEntryAlloc       OBJECT-TYPE
    SYNTAX      Unsigned32
    MAX-ACCESS  read-only
    STATUS      current
    DESCRIPTION
        "The value of tFPResEgrIPv6QosEntryAlloc represents the total number of
         IPv6 egress QoS CAM entries that are currently allocated on this FP."
    ::= { tFPResEntry 56 }

tFPResIngAclFilterTotal          OBJECT-TYPE
    SYNTAX      Unsigned32
    MAX-ACCESS  read-only
    STATUS      current
    DESCRIPTION
        "The value of tFPResIngAclFilterTotal represents the total number of
         ingress MAC + IP ACL filter policies that are supported on this FP.

         Note that on 7750 SR-c4/c12 the CPM enforced limit for the total
         number of ACL filter policies is lower than the value of this object."
    ::= { tFPResEntry 57 }

tFPResIngAclFilterAlloc          OBJECT-TYPE
    SYNTAX      Unsigned32
    MAX-ACCESS  read-only
    STATUS      current
    DESCRIPTION
        "The value of tFPResIngAclFilterAlloc represents the total number of
         ingress MAC + IP ACL filter policies that are currently allocated on
         this FP."
    ::= { tFPResEntry 58 }

tFPResEgrAclFilterTotal          OBJECT-TYPE
    SYNTAX      Unsigned32
    MAX-ACCESS  read-only
    STATUS      current
    DESCRIPTION
        "The value of tFPResEgrAclFilterTotal represents the total number of
         egress MAC + IP ACL filter policies that are supported on this FP.

         Note that on 7750 SR-c4/c12 the CPM enforced limit for the total
         number of ACL filter policies is lower than the value of this object."
    ::= { tFPResEntry 59 }

tFPResEgrAclFilterAlloc          OBJECT-TYPE
    SYNTAX      Unsigned32
    MAX-ACCESS  read-only
    STATUS      current
    DESCRIPTION
        "The value of tFPResEgrAclFilterAlloc represents the total number of
         egress MAC + IP ACL filter policies that are currently allocated on
         this FP."
    ::= { tFPResEntry 60 }

tFPResDynSvcEntryTotal           OBJECT-TYPE
    SYNTAX      Unsigned32
    MAX-ACCESS  read-only
    STATUS      current
    DESCRIPTION
        "The value of tFPResDynSvcEntryTotal represents the total number of
         dynamic services that are supported on this FP.

         When the value of tFPResDynSvcEntryTotal is zero, it indicates that
         this resource type is not supported on this FP.

         The value of tFPResDynSvcEntryTotal will always equal to the sum of
         tFPResSubHostTotal, tFPResEncapGrpMemberTotal and
         tFPResEgrNetQGrpMapTotal since subscriber host resources, encap-group
         members resources and egress network queue-group mappings resources
         are subsets of dynamic service entry resources."
    ::= { tFPResEntry 61 }

tFPResDynSvcEntryAlloc           OBJECT-TYPE
    SYNTAX      Unsigned32
    MAX-ACCESS  read-only
    STATUS      current
    DESCRIPTION
        "The value of tFPResDynSvcEntryAlloc represents the total number of
         dynamic services that are currently allocated on this FP.

         The value of tFPResDynSvcEntryAlloc will always equal to the sum of
         tFPResSubHostAlloc, tFPResEncapGrpMemberAlloc and
         tFPResEgrNetQGrpMapAlloc since subscriber host resources, encap-group
         members resources and egress network queue-group mappings resources
         are subsets of dynamic service entry resources."
    ::= { tFPResEntry 62 }

tFPResSubHostTotal               OBJECT-TYPE
    SYNTAX      Unsigned32
    MAX-ACCESS  read-only
    STATUS      current
    DESCRIPTION
        "The value of tFPResSubHostTotal represents the total number of
         subscriber hosts that are supported on this FP.

         When the value of tFPResSubHostTotal is zero, it indicates that this
         resource type is not supported on this FP.

         The value of tFPResSubHostTotal will always be less than or equal to
         tFPResDynSvcEntryTotal since subscriber host resources are subset of
         dynamic service entry resources."
    ::= { tFPResEntry 63 }

tFPResSubHostAlloc               OBJECT-TYPE
    SYNTAX      Unsigned32
    MAX-ACCESS  read-only
    STATUS      current
    DESCRIPTION
        "The value of tFPResSubHostAlloc represents the total number of
         subscriber hosts that are currently allocated on this FP.

         The value of tFPResSubHostAlloc will always be less than or equal to
         tFPResDynSvcEntryAlloc since subscriber host resources are subset of
         dynamic service entry resources."
    ::= { tFPResEntry 64 }

tFPResEncapGrpMemberTotal        OBJECT-TYPE
    SYNTAX      Unsigned32
    MAX-ACCESS  read-only
    STATUS      current
    DESCRIPTION
        "The value of tFPResEncapGrpMemberTotal represents the total number of
         encap group members that are supported on this FP.

         When the value of tFPResEncapGrpMemberTotal is zero, it indicates that
         this resource type is not supported on this FP.

         The value of tFPResEncapGrpMemberTotal will always be less than or
         equal to tFPResDynSvcEntryTotal since encap group members are subset
         of dynamic service entry resources."
    ::= { tFPResEntry 65 }

tFPResEncapGrpMemberAlloc        OBJECT-TYPE
    SYNTAX      Unsigned32
    MAX-ACCESS  read-only
    STATUS      current
    DESCRIPTION
        "The value of tFPResEncapGrpMemberAlloc represents the total number of
         encap group members that are currently allocated on this FP.

         The value of tFPResEncapGrpMemberAlloc will always be less than or
         equal to tFPResDynSvcEntryAlloc since encap group members are subset
         of dynamic service entry resources."
    ::= { tFPResEntry 66 }

tFPResEgrNetQGrpMapTotal         OBJECT-TYPE
    SYNTAX      Unsigned32
    MAX-ACCESS  read-only
    STATUS      current
    DESCRIPTION
        "The value of tFPResEgrNetQGrpMapTotal represents the total number of
         egress network queue-group mappings that are supported on this FP.

         When the value of tFPResEgrNetQGrpMapTotal is zero, it indicates that
         this resource type is not supported on this FP.

         The value of tFPResEgrNetQGrpMapTotal will always be less than or
         equal to tFPResDynSvcEntryTotal since egress network queue-group
         mappings are subset of dynamic service entry resources."
    ::= { tFPResEntry 67 }

tFPResEgrNetQGrpMapAlloc         OBJECT-TYPE
    SYNTAX      Unsigned32
    MAX-ACCESS  read-only
    STATUS      current
    DESCRIPTION
        "The value of tFPResEgrNetQGrpMapAlloc represents the total number of
         egress network queue-group mappings that are currently allocated on
         this FP.

         The value of tFPResEgrNetQGrpMapAlloc will always be less than or
         equal to tFPResDynSvcEntryAlloc since egress network queue-group
         mappings are subset of dynamic service entry resources."
    ::= { tFPResEntry 68 }

tFPResMacFdbRecTotal             OBJECT-TYPE
    SYNTAX      Unsigned32
    MAX-ACCESS  read-only
    STATUS      current
    DESCRIPTION
        "The value of tFPResMacFdbRecTotal represents the total number of MAC
         Forwarding Data-Base (FDB) records that are supported on this FP.

         When the value of tFPResMacFdbRecTotal is zero, it indicates that this
         resource type is not supported on this FP."
    ::= { tFPResEntry 69 }

tFPResMacFdbRecAlloc             OBJECT-TYPE
    SYNTAX      Unsigned32
    MAX-ACCESS  read-only
    STATUS      current
    DESCRIPTION
        "The value of tFPResMacFdbRecAlloc represents the total number of MAC
         Forwarding Data-Base (FDB) records that are currently allocated on
         this FP."
    ::= { tFPResEntry 70 }

tFPResResRvplsFdbRecTotal        OBJECT-TYPE
    SYNTAX      Unsigned32
    MAX-ACCESS  read-only
    STATUS      obsolete
    DESCRIPTION
        "The value of tFPResResRvplsFdbRecTotal represents the total number of
         reserved R-VPLS Forwarding Data-Base (FDB) records that are supported
         on this FP.

         When the value of tFPResResRvplsFdbRecTotal is zero, it indicates that
         this resource type is not supported on this FP."
    ::= { tFPResEntry 71 }

tFPResResRvplsFdbRecAlloc        OBJECT-TYPE
    SYNTAX      Unsigned32
    MAX-ACCESS  read-only
    STATUS      obsolete
    DESCRIPTION
        "The value of tFPResResRvplsFdbRecAlloc represents the total number of
         reserved R-VPLS Forwarding Data-Base (FDB) records that are currently
         allocated on this FP."
    ::= { tFPResEntry 72 }

tFPResDynQ2NamedPoolTotal        OBJECT-TYPE
    SYNTAX      Unsigned32
    MAX-ACCESS  read-only
    STATUS      current
    DESCRIPTION
        "The value of tFPResDynQ2NamedPoolTotal represents the total number of
         dynamic Q2 named pools that are supported on this FP.

         When the value of tFPResDynQ2NamedPoolTotal is zero, it indicates that
         this resource type is not supported on this FP."
    ::= { tFPResEntry 73 }

tFPResDynQ2NamedPoolAlloc        OBJECT-TYPE
    SYNTAX      Unsigned32
    MAX-ACCESS  read-only
    STATUS      current
    DESCRIPTION
        "The value of tFPResDynQ2NamedPoolAlloc represents the total number of
         dynamic Q2 named pools that are currently allocated on this FP."
    ::= { tFPResEntry 74 }

tFPResDynQ2NamedPoolIUBI         OBJECT-TYPE
    SYNTAX      Unsigned32
    MAX-ACCESS  read-only
    STATUS      current
    DESCRIPTION
        "The value of tFPResDynQ2NamedPoolIUBI represents the subset of
         resources which are currently in use by ingress Q2 named pools out of
         currently allocated dynamic Q2 named pools resources,
         tFPResDynQ2NamedPoolAlloc."
    ::= { tFPResEntry 75 }

tFPResDynQ2NamedPoolIUBE         OBJECT-TYPE
    SYNTAX      Unsigned32
    MAX-ACCESS  read-only
    STATUS      current
    DESCRIPTION
        "The value of tFPResDynQ2NamedPoolIUBE represents the subset of
         resources which are currently in use by egress Q2 named pools out of
         currently allocated dynamic Q2 named pools resources,
         tFPResDynQ2NamedPoolAlloc."
    ::= { tFPResEntry 76 }

tFPResIngQ1NamedPoolTotal        OBJECT-TYPE
    SYNTAX      Unsigned32
    MAX-ACCESS  read-only
    STATUS      current
    DESCRIPTION
        "The value of tFPResIngQ1NamedPoolTotal represents the total number of
         ingress Q1 named pools that are supported on this FP.

         When the value of tFPResIngQ1NamedPoolTotal is zero, it indicates that
         this resource type is not supported on this FP."
    ::= { tFPResEntry 77 }

tFPResIngQ1NamedPoolAlloc        OBJECT-TYPE
    SYNTAX      Unsigned32
    MAX-ACCESS  read-only
    STATUS      current
    DESCRIPTION
        "The value of tFPResIngQ1NamedPoolAlloc represents the total number of
         ingress Q1 named pools that are currently allocated on this FP."
    ::= { tFPResEntry 78 }

tFPResEgrQ1NamedPoolTotal        OBJECT-TYPE
    SYNTAX      Unsigned32
    MAX-ACCESS  read-only
    STATUS      current
    DESCRIPTION
        "The value of tFPResEgrQ1NamedPoolTotal represents the total number of
         egress Q1 named pools that are supported on this FP.

         When the value of tFPResEgrQ1NamedPoolTotal is zero, it indicates that
         this resource type is not supported on this FP."
    ::= { tFPResEntry 79 }

tFPResEgrQ1NamedPoolAlloc        OBJECT-TYPE
    SYNTAX      Unsigned32
    MAX-ACCESS  read-only
    STATUS      current
    DESCRIPTION
        "The value of tFPResEgrQ1NamedPoolAlloc represents the total number of
         egress Q1 named pools that are currently allocated on this FP."
    ::= { tFPResEntry 80 }

tFPResDynQ2WredPoolTotal         OBJECT-TYPE
    SYNTAX      Unsigned32
    MAX-ACCESS  read-only
    STATUS      current
    DESCRIPTION
        "The value of tFPResDynQ2WredPoolTotal represents the total number of
         dynamic Q2 wred pools that are supported on this FP.

         When the value of tFPResDynQ2WredPoolTotal is zero, it indicates that
         this resource type is not supported on this FP."
    ::= { tFPResEntry 81 }

tFPResDynQ2WredPoolAlloc         OBJECT-TYPE
    SYNTAX      Unsigned32
    MAX-ACCESS  read-only
    STATUS      current
    DESCRIPTION
        "The value of tFPResDynQ2WredPoolAlloc represents the total number of
         dynamic Q2 wred pools that are currently allocated on this FP."
    ::= { tFPResEntry 82 }

tFPResIngIPv6AclFilterTotal      OBJECT-TYPE
    SYNTAX      Unsigned32
    MAX-ACCESS  read-only
    STATUS      current
    DESCRIPTION
        "The value of tFPResIngIPv6AclFilterTotal represents the total number
         of ingress IPv6 ACL filter policies that are supported on this FP.

         Note that on 7750 SR-c4/c12 the CPM enforced limit for the total
         number of ACL filter policies is lower than the value of this object."
    ::= { tFPResEntry 83 }

tFPResIngIPv6AclFilterAlloc      OBJECT-TYPE
    SYNTAX      Unsigned32
    MAX-ACCESS  read-only
    STATUS      current
    DESCRIPTION
        "The value of tFPResIngIPv6AclFilterAlloc represents the total number
         of ingress IPv6 ACL filter policies that are currently allocated on
         this FP."
    ::= { tFPResEntry 84 }

tFPResEgrIPv6AclFilterTotal      OBJECT-TYPE
    SYNTAX      Unsigned32
    MAX-ACCESS  read-only
    STATUS      current
    DESCRIPTION
        "The value of tFPResEgrIPv6AclFilterTotal represents the total number
         of egress IPv6 ACL filter policies that are supported on this FP.

         Note that on 7750 SR-c4/c12 the CPM enforced limit for the total
         number of ACL filter policies is lower than the value of this object."
    ::= { tFPResEntry 85 }

tFPResEgrIPv6AclFilterAlloc      OBJECT-TYPE
    SYNTAX      Unsigned32
    MAX-ACCESS  read-only
    STATUS      current
    DESCRIPTION
        "The value of tFPResEgrIPv6AclFilterAlloc represents the total number
         of egress IPv6 ACL filter policies that are currently allocated on
         this FP."
    ::= { tFPResEntry 86 }

tFPResEgrQosBypassTotal          OBJECT-TYPE
    SYNTAX      Unsigned32
    MAX-ACCESS  read-only
    STATUS      current
    DESCRIPTION
        "The value of tFPResEgrQosBypassTotal represents the total number of
         egress qos bypass entries that are supported on this FP.

         When the value of tFPResEgrQosBypassTotal is zero, it indicates that
         this resource type is not supported on this FP."
    ::= { tFPResEntry 87 }

tFPResEgrQosBypassAlloc          OBJECT-TYPE
    SYNTAX      Unsigned32
    MAX-ACCESS  read-only
    STATUS      current
    DESCRIPTION
        "The value of tFPResEgrQosBypassAlloc represents the total number of
         egress qos bypass entries that are currently allocated on this FP."
    ::= { tFPResEntry 88 }

tFPResSapInstanceTotal           OBJECT-TYPE
    SYNTAX      Unsigned32
    MAX-ACCESS  read-only
    STATUS      current
    DESCRIPTION
        "The value of tFPResSapInstanceTotal represents the total number of SAP
         instances that are supported on this FP.

         When the value of tFPResSapInstanceTotal is zero, it indicates that
         this resource type is not supported on this FP."
    ::= { tFPResEntry 89 }

tFPResSapInstanceAlloc           OBJECT-TYPE
    SYNTAX      Unsigned32
    MAX-ACCESS  read-only
    STATUS      current
    DESCRIPTION
        "The value of tFPResSapInstanceAlloc represents the total number of SAP
         instances that are currently allocated on this FP."
    ::= { tFPResEntry 90 }

tFPResEgrHsQGrpTotal             OBJECT-TYPE
    SYNTAX      Unsigned32
    MAX-ACCESS  read-only
    STATUS      current
    DESCRIPTION
        "The value of tFPResEgrHsQGrpTotal represents the total number of HS
         egress queue-group resources that are supported on this FP.

         When the value of tFPResEgrHsQGrpTotal is zero, it indicates that this
         resource type is not supported on this FP."
    ::= { tFPResEntry 91 }

tFPResEgrHsQGrpAlloc             OBJECT-TYPE
    SYNTAX      Unsigned32
    MAX-ACCESS  read-only
    STATUS      current
    DESCRIPTION
        "The value of tFPResEgrHsQGrpAlloc represents the total number of HS
         egress queue-group resources that are allocated on this FP."
    ::= { tFPResEntry 92 }

tFPResEgrHsPrimaryShapersTotal   OBJECT-TYPE
    SYNTAX      Unsigned32
    MAX-ACCESS  read-only
    STATUS      current
    DESCRIPTION
        "The value of tFPResEgrHsPrimaryShapersTotal represents the total
         number of HS Primary Shapers that are supported on this FP.

         When the value of tFPResEgrHsPrimaryShapersTotal is zero, it indicates
         that this resource type is not supported on this FP."
    ::= { tFPResEntry 93 }

tFPResEgrHsPrimaryShapersAlloc   OBJECT-TYPE
    SYNTAX      Unsigned32
    MAX-ACCESS  read-only
    STATUS      current
    DESCRIPTION
        "The value of tFPResEgrHsPrimaryShapersAlloc represents the total
         number of HS Primary Shapers that are allocatted on this FP."
    ::= { tFPResEntry 94 }

tFPResEgrHsPrimaryShapersIUBES   OBJECT-TYPE
    SYNTAX      Unsigned32
    MAX-ACCESS  read-only
    STATUS      current
    DESCRIPTION
        "The value of tFPResEgrHsPrimaryShapersIUBES represents the subset of
         resources which are currently in use by HS Explicit Shapers out of
         currently allocated Primary Shapers."
    ::= { tFPResEntry 95 }

tFPResEgrHsPrimaryShapersIUBMS   OBJECT-TYPE
    SYNTAX      Unsigned32
    MAX-ACCESS  read-only
    STATUS      current
    DESCRIPTION
        "The value of tFPResEgrHsPrimaryShapersIUBMS represents the subset of
         resources which are currently in use by HS Managed Shapers out of
         currently allocated Primary Shapers."
    ::= { tFPResEntry 96 }

tFPResEgrHsSecondaryShapersTotal OBJECT-TYPE
    SYNTAX      Unsigned32
    MAX-ACCESS  read-only
    STATUS      current
    DESCRIPTION
        "The value of tFPResEgrHsSecondaryShapersTotal represents the total
         number of HS Secondary Shapers that are supported on this FP.

         When the value of tFPResEgrHsSecondaryShapersTotal is zero, it
         indicates that this resource type is not supported on this FP."
    ::= { tFPResEntry 97 }

tFPResEgrHsSecondaryShapersAlloc OBJECT-TYPE
    SYNTAX      Unsigned32
    MAX-ACCESS  read-only
    STATUS      current
    DESCRIPTION
        "The value of tFPResEgrHsSecondaryShapersAlloc represents the total
         number of HS Secondary Shapers that are allocated on this FP."
    ::= { tFPResEntry 98 }

tFPResEgrHsTurboQGrpTotal        OBJECT-TYPE
    SYNTAX      Unsigned32
    MAX-ACCESS  read-only
    STATUS      current
    DESCRIPTION
        "The value of tFPResEgrHsTurboQGrpTotal represents the total number of
         HS egress turbo queue-group resources that are supported on this FP.

         When the value of tFPResEgrHsTurboQGrpTotal is zero, it indicates that
         this resource type is not supported on this FP."
    ::= { tFPResEntry 99 }

tFPResEgrHsTurboQGrpAlloc        OBJECT-TYPE
    SYNTAX      Unsigned32
    MAX-ACCESS  read-only
    STATUS      current
    DESCRIPTION
        "The value of tFPResEgrHsTurboQGrpAlloc represents the total number of
         HS egress turbo queue-group resources that are allocated on this FP."
    ::= { tFPResEntry 100 }

tFPResIngQGrpRedirTotal          OBJECT-TYPE
    SYNTAX      Unsigned32
    MAX-ACCESS  read-only
    STATUS      current
    DESCRIPTION
        "The value of tFPResIngQGrpRedirTotal represents the total number of
         Ingress Queue Group Redirect List Entries that are supported on this
         FP.

         When the value of tFPResIngQGrpRedirTotal is zero, it indicates that
         this resource type is not supported on this FP."
    ::= { tFPResEntry 101 }

tFPResIngQGrpRedirAlloc          OBJECT-TYPE
    SYNTAX      Unsigned32
    MAX-ACCESS  read-only
    STATUS      current
    DESCRIPTION
        "The value of tFPResIngQGrpRedirAlloc represents the total number of
         Ingress Queue Group Redirect List Entries that are currently allocated
         on this FP."
    ::= { tFPResEntry 102 }

tFPResSapInstEgrQGrpRedirTotal   OBJECT-TYPE
    SYNTAX      Unsigned32
    MAX-ACCESS  read-only
    STATUS      current
    DESCRIPTION
        "The value of tFPResIngQGrpRedirTotal represents the total number of
         per-SAP instance Egress Queue Group Redirect List Entries that are
         supported on this FP.

         When the value of tFPResSapInstEgrQGrpRedirTotal is zero, it indicates
         that this resource type is not supported on this FP."
    ::= { tFPResEntry 103 }

tFPResSapInstEgrQGrpRedirAlloc   OBJECT-TYPE
    SYNTAX      Unsigned32
    MAX-ACCESS  read-only
    STATUS      current
    DESCRIPTION
        "The value of tFPResSapInstEgrQGrpRedirAlloc represents the total
         number of per-SAP instance Egress Queue Group Redirect List Entries
         that are currently allocated on this FP."
    ::= { tFPResEntry 104 }

tMDAResTable                     OBJECT-TYPE
    SYNTAX      SEQUENCE OF TMDAResEntry
    MAX-ACCESS  not-accessible
    STATUS      current
    DESCRIPTION
        "The value of tMDAResTable represents system resource information that
         are specific to MDA for a particular card on a given chassis."
    ::= { tmnxCardObjs 47 }

tMDAResEntry                     OBJECT-TYPE
    SYNTAX      TMDAResEntry
    MAX-ACCESS  not-accessible
    STATUS      current
    DESCRIPTION
        "The value of tMDAResEntry represents MDA specific system resource
         information."
    INDEX       {
        tmnxChassisIndex,
        tmnxCardSlotNum,
        tmnxMDASlotNum
    }
    ::= { tMDAResTable 1 }

TMDAResEntry                     ::= SEQUENCE
{
    tMDAResEgrHsmdaQGrpTotal         Unsigned32,
    tMDAResEgrHsmdaQGrpAlloc         Unsigned32,
    tMDAResEgrHsmdaSecShaperTotal    Unsigned32,
    tMDAResEgrHsmdaSecShaperAlloc    Unsigned32,
    tMDAResSapInstanceTotal          Unsigned32,
    tMDAResSapInstanceAlloc          Unsigned32
}

tMDAResEgrHsmdaQGrpTotal         OBJECT-TYPE
    SYNTAX      Unsigned32
    MAX-ACCESS  read-only
    STATUS      current
    DESCRIPTION
        "The value of tMDAResEgrHsmdaQGrpTotal represents the total number of
         egress HSMDA queue-groups that are supported on this MDA.

         When the value of tMDAResEgrHsmdaQGrpTotal is zero, it indicates that
         this resource type is not supported on this MDA."
    ::= { tMDAResEntry 1 }

tMDAResEgrHsmdaQGrpAlloc         OBJECT-TYPE
    SYNTAX      Unsigned32
    MAX-ACCESS  read-only
    STATUS      current
    DESCRIPTION
        "The value of tMDAResEgrHsmdaQGrpAlloc represents the total number of
         egress HSMDA queue-groups that are currently allocated on this MDA."
    ::= { tMDAResEntry 2 }

tMDAResEgrHsmdaSecShaperTotal    OBJECT-TYPE
    SYNTAX      Unsigned32
    MAX-ACCESS  read-only
    STATUS      current
    DESCRIPTION
        "The value of tMDAResEgrHsmdaSecShaperTotal represents the total number
         of egress HSMDA secondary-shapers that are supported on this MDA.

         When the value of tMDAResEgrHsmdaSecShaperTotal is zero, it indicates
         that this resource type is not supported on this MDA."
    ::= { tMDAResEntry 3 }

tMDAResEgrHsmdaSecShaperAlloc    OBJECT-TYPE
    SYNTAX      Unsigned32
    MAX-ACCESS  read-only
    STATUS      current
    DESCRIPTION
        "The value of tMDAResEgrHsmdaSecShaperAlloc represents the total number
         of egress HSMDA secondary-shapers that are currently allocated on this
         MDA."
    ::= { tMDAResEntry 4 }

tMDAResSapInstanceTotal          OBJECT-TYPE
    SYNTAX      Unsigned32
    MAX-ACCESS  read-only
    STATUS      current
    DESCRIPTION
        "The value of tMDAResSapInstanceTotal represents the total number of
         SAP instances that are supported on this MDA.

         When the value of tMDAResSapInstanceTotal is zero, it indicates that
         this resource type is not supported on this MDA."
    ::= { tMDAResEntry 5 }

tMDAResSapInstanceAlloc          OBJECT-TYPE
    SYNTAX      Unsigned32
    MAX-ACCESS  read-only
    STATUS      current
    DESCRIPTION
        "The value of tMDAResSapInstanceAlloc represents the total number of
         SAP instances that are currently allocated on this MDA."
    ::= { tMDAResEntry 6 }

tFPEgressFwdEngDRStatsTable      OBJECT-TYPE
    SYNTAX      SEQUENCE OF TFPEgressFwdEngDRStatsEntry
    MAX-ACCESS  not-accessible
    STATUS      current
    DESCRIPTION
        "The value of tFPEgressFwdEngDRStatsTable specifies per-reason drop
         statistics for the packets dropped by the forwarding engine."
    ::= { tmnxCardObjs 52 }

tFPEgressFwdEngDRStatsEntry      OBJECT-TYPE
    SYNTAX      TFPEgressFwdEngDRStatsEntry
    MAX-ACCESS  not-accessible
    STATUS      current
    DESCRIPTION
        "The value of tFPEgressFwdEngDRStatsEntry specifies per-reason drop
         statistics for the packets dropped by the forwarding engine."
    INDEX       {
        tmnxChassisIndex,
        tmnxCardSlotNum,
        tmnxFPNum
    }
    ::= { tFPEgressFwdEngDRStatsTable 1 }

TFPEgressFwdEngDRStatsEntry      ::= SEQUENCE
{
    tFwdEngDREgrEncapExceeded        Counter64,
    tFwdEngDREgrMtuExceeded          Counter64
}

tFwdEngDREgrEncapExceeded        OBJECT-TYPE
    SYNTAX      Counter64
    MAX-ACCESS  read-only
    STATUS      current
    DESCRIPTION
        "The value of tFwdEngDREgrEncapExceeded indicates the total number of
         packets dropped by the forwarding engine due to the packet header size
         exceeding the egress encapsulation limit."
    ::= { tFPEgressFwdEngDRStatsEntry 1 }

tFwdEngDREgrMtuExceeded          OBJECT-TYPE
    SYNTAX      Counter64
    MAX-ACCESS  read-only
    STATUS      current
    DESCRIPTION
        "The value of tFwdEngDREgrMtuExceeded indicates the total number of
         exceptions at egress that need an ICMP cannot fragment response."
    ::= { tFPEgressFwdEngDRStatsEntry 2 }

tmnxCardVFpStatsTable            OBJECT-TYPE
    SYNTAX      SEQUENCE OF TmnxCardVFpStatsEntry
    MAX-ACCESS  not-accessible
    STATUS      current
    DESCRIPTION
        "The value of tmnxCardVFpStatsTable contains CPU statistics for the
         virtual forwarding plane (vFP) of a given card."
    ::= { tmnxCardObjs 53 }

tmnxCardVFpStatsEntry            OBJECT-TYPE
    SYNTAX      TmnxCardVFpStatsEntry
    MAX-ACCESS  not-accessible
    STATUS      current
    DESCRIPTION
        "The value of tmnxCardVFpStatsEntry consists of CPU statistics for a
         virtual forwarding plane (vFP) task on a card."
    INDEX       {
        tmnxChassisIndex,
        tmnxCardSlotNum,
        tmnxCardVFpTaskType
    }
    ::= { tmnxCardVFpStatsTable 1 }

TmnxCardVFpStatsEntry            ::= SEQUENCE
{
    tmnxCardVFpTaskType              INTEGER,
    tmnxCardVFpCpuCount              Unsigned32,
    tmnxCardVFpAvgUtilization        Unsigned32,
    tmnxCardVFpMaxUtilization        Unsigned32
}

tmnxCardVFpTaskType              OBJECT-TYPE
    SYNTAX      INTEGER {
        nic       (1),
        worker    (2),
        scheduler (3),
        collapsed (4),
        combined  (5)
    }
    MAX-ACCESS  not-accessible
    STATUS      current
    DESCRIPTION
        "The value of tmnxCardVFpTaskType specifies the virtual forwarding
         plane (vFP) task type.

         Values:
            nic       - task includes only network interface card work
            worker    - task includes only worker work
            scheduler - task includes only scheduler work
            collapsed - task includes NIC and scheduler work
            combined  - task includes NIC, scheduler and worker work"
    ::= { tmnxCardVFpStatsEntry 1 }

tmnxCardVFpCpuCount              OBJECT-TYPE
    SYNTAX      Unsigned32
    MAX-ACCESS  read-only
    STATUS      current
    DESCRIPTION
        "The value of tmnxCardVFpCpuCount indicates the number of virtual CPUs
         that the vFP task is running on for the card."
    ::= { tmnxCardVFpStatsEntry 2 }

tmnxCardVFpAvgUtilization        OBJECT-TYPE
    SYNTAX      Unsigned32
    UNITS       "hundredths of a percent"
    MAX-ACCESS  read-only
    STATUS      current
    DESCRIPTION
        "The value of tmnxCardVFpAvgUtilization indicates the average CPU
         utilization of the vFP task on the card."
    ::= { tmnxCardVFpStatsEntry 3 }

tmnxCardVFpMaxUtilization        OBJECT-TYPE
    SYNTAX      Unsigned32
    UNITS       "hundredths of a percent"
    MAX-ACCESS  read-only
    STATUS      current
    DESCRIPTION
        "The value of tmnxCardVFpMaxUtilization indicates the maximum CPU
         utilization of the vFP task on the card."
    ::= { tmnxCardVFpStatsEntry 4 }

tmnxCardVCpuSchedStatsTable      OBJECT-TYPE
    SYNTAX      SEQUENCE OF TmnxCardVCpuSchedStatsEntry
    MAX-ACCESS  not-accessible
    STATUS      current
    DESCRIPTION
        "The value of tmnxCardVCpuSchedStatsTable contains virtual CPU
         scheduling statistics for a given card."
    ::= { tmnxCardObjs 54 }

tmnxCardVCpuSchedStatsEntry      OBJECT-TYPE
    SYNTAX      TmnxCardVCpuSchedStatsEntry
    MAX-ACCESS  not-accessible
    STATUS      current
    DESCRIPTION
        "The value of tmnxCardVCpuSchedStatsEntry consists of virtual CPU
         scheduling statistics for a card."
    INDEX       {
        tmnxChassisIndex,
        tmnxCardSlotNum
    }
    ::= { tmnxCardVCpuSchedStatsTable 1 }

TmnxCardVCpuSchedStatsEntry      ::= SEQUENCE
{
    tmnxCardVCpuSchedHealth          Unsigned32,
    tmnxCardVCpuSchedLastClearedTime TimeStamp
}

tmnxCardVCpuSchedHealth          OBJECT-TYPE
    SYNTAX      Unsigned32
    UNITS       "hundredths of a percent"
    MAX-ACCESS  read-only
    STATUS      current
    DESCRIPTION
        "The value of tmnxCardVCpuSchedHealth indicates the scheduling health
         of the virtual CPU on the card."
    ::= { tmnxCardVCpuSchedStatsEntry 1 }

tmnxCardVCpuSchedLastClearedTime OBJECT-TYPE
    SYNTAX      TimeStamp
    MAX-ACCESS  read-only
    STATUS      current
    DESCRIPTION
        "The value of tmnxCardVCpuSchedLastClearedTime indicates the time,
         since system startup, when tmnxCardVCpuSchedStatsEntry was last
         cleared."
    ::= { tmnxCardVCpuSchedStatsEntry 2 }

tmnxChassisNotificationObjects   OBJECT IDENTIFIER ::= { tmnxHwObjs 6 }

tmnxEqNotificationRow            OBJECT-TYPE
    SYNTAX      RowPointer
    MAX-ACCESS  accessible-for-notify
    STATUS      current
    DESCRIPTION
        "used by tmnx chassis Notifications, the OID indicates the table and
         entry."
    ::= { tmnxChassisNotificationObjects 1 }

tmnxEqTypeNotificationRow        OBJECT-TYPE
    SYNTAX      RowPointer
    MAX-ACCESS  accessible-for-notify
    STATUS      current
    DESCRIPTION
        "used by tmnx chassis notifications, the OID indicates the table and
         entry with the equipment model type information."
    ::= { tmnxChassisNotificationObjects 2 }

tmnxChassisNotifyChassisId       OBJECT-TYPE
    SYNTAX      TmnxChassisIndex
    MAX-ACCESS  accessible-for-notify
    STATUS      current
    DESCRIPTION
        "Used by tmnx chassis and port Notifications, indicates the chassis
         associated with the alarm."
    ::= { tmnxChassisNotificationObjects 3 }

tmnxChassisNotifyHwIndex         OBJECT-TYPE
    SYNTAX      TmnxHwIndex
    MAX-ACCESS  accessible-for-notify
    STATUS      current
    DESCRIPTION
        "Used by tmnx chassis and port Notifications, indicates the entry in
         the tmnxHwTable for the hardware component associated with an alarm."
    ::= { tmnxChassisNotificationObjects 4 }

tmnxRedSecondaryCPMStatus        OBJECT-TYPE
    SYNTAX      INTEGER {
        online  (1),
        offline (2),
        fail    (3)
    }
    MAX-ACCESS  accessible-for-notify
    STATUS      current
    DESCRIPTION
        "Used by the tmnxRedSecondaryCPMStatusChange Notification, indicates
         the status of the secondary CPM."
    ::= { tmnxChassisNotificationObjects 5 }

tmnxChassisNotifyOID             OBJECT-TYPE
    SYNTAX      OBJECT IDENTIFIER
    MAX-ACCESS  accessible-for-notify
    STATUS      current
    DESCRIPTION
        "Used by the tmnxChassisNotificationClear trap, the OID identifies the
         trap which is getting cleared."
    ::= { tmnxChassisNotificationObjects 6 }

tmnxSyncIfTimingNotifyAlarm      OBJECT-TYPE
    SYNTAX      INTEGER {
        notUsed (0),
        los     (1),
        oof     (2),
        oopir   (3)
    }
    MAX-ACCESS  accessible-for-notify
    STATUS      current
    DESCRIPTION
        "Used by synchronous interface timing notifications, the value of
         tmnxSyncIfTimingNotifyAlarm indicates the reason a timing reference
         alarm has been raised."
    ::= { tmnxChassisNotificationObjects 7 }

tmnxChassisNotifyMismatchedVer   OBJECT-TYPE
    SYNTAX      DisplayString
    MAX-ACCESS  accessible-for-notify
    STATUS      current
    DESCRIPTION
        "Used by tmnxPeSoftwareVersionMismatch, the value of
         tmnxChassisNotifyMismatchedVer indicates the software version of the
         mismatched CPM/IOM card."
    ::= { tmnxChassisNotificationObjects 8 }

tmnxChassisNotifySoftwareLocation OBJECT-TYPE
    SYNTAX      DisplayString
    MAX-ACCESS  accessible-for-notify
    STATUS      current
    DESCRIPTION
        "Used by tmnxPeSoftwareLoadFailed, the value of
         tmnxChassisNotifySoftwareLocation contains the location of the
         software."
    ::= { tmnxChassisNotificationObjects 9 }

tmnxChassisNotifyCardFailureReason OBJECT-TYPE
    SYNTAX      DisplayString
    MAX-ACCESS  accessible-for-notify
    STATUS      current
    DESCRIPTION
        "Used by tmnxEqCardFailure, the value of
         tmnxChassisNotifyCardFailureReason contains the reason for card
         failure."
    ::= { tmnxChassisNotificationObjects 10 }

tmnxChassisNotifyCardName        OBJECT-TYPE
    SYNTAX      DisplayString (SIZE (1..32))
    MAX-ACCESS  accessible-for-notify
    STATUS      current
    DESCRIPTION
        "Used by tmnxEqCardInserted and tmnxEqCardRemoved, the value of
         tmnxChassisNotifyCardName specifies the name of the affected card."
    ::= { tmnxChassisNotificationObjects 11 }

tmnxChassisNotifyCardSyncFile    OBJECT-TYPE
    SYNTAX      DisplayString
    MAX-ACCESS  accessible-for-notify
    STATUS      current
    DESCRIPTION
        "Used by tmnxCpmCardSyncFileNotPresent, the value of
         tmnxChassisNotifyCardSyncFile specifies the name of the affected file."
    ::= { tmnxChassisNotificationObjects 12 }

tmnxCardComplexNumber            OBJECT-TYPE
    SYNTAX      Unsigned32
    MAX-ACCESS  accessible-for-notify
    STATUS      current
    DESCRIPTION
        "Used by tmnxEqCardPChipError, the value of tmnxCardComplexNumber
         specifies the number of the affected Complex."
    ::= { tmnxChassisNotificationObjects 13 }

tmnxCardFwdDirection             OBJECT-TYPE
    SYNTAX      INTEGER {
        ingress (1),
        egress  (2)
    }
    MAX-ACCESS  accessible-for-notify
    STATUS      current
    DESCRIPTION
        "Used by tmnxEqCardPChipError, the value of tmnxCardFwdDirection
         specifies the direction of the affected Complex."
    ::= { tmnxChassisNotificationObjects 14 }

tmnxCardSoftResetState           OBJECT-TYPE
    SYNTAX      INTEGER {
        initiated (1),
        aborted   (2),
        complete  (3)
    }
    MAX-ACCESS  accessible-for-notify
    STATUS      current
    DESCRIPTION
        "Used by tmnxEqCardSoftResetAlarm, the value of tmnxCardSoftResetState
         specifies the reset state of the IOM card."
    ::= { tmnxChassisNotificationObjects 15 }

tmnxMdaNotifyType                OBJECT-TYPE
    SYNTAX      TmnxMdaType
    MAX-ACCESS  accessible-for-notify
    STATUS      current
    DESCRIPTION
        "Used by equipment alarms where the type of MDA isn't supported with
         the current configuration."
    ::= { tmnxChassisNotificationObjects 16 }

tmnxCardSrcSlotBitmap            OBJECT-TYPE
    SYNTAX      TmnxCardSlotBitMap
    MAX-ACCESS  accessible-for-notify
    STATUS      current
    DESCRIPTION
        "Used by tmnxEqCardPChipError, the value of tmnxCardSrcSlotBitmap
         specifies the source slots of the affected Complex."
    ::= { tmnxChassisNotificationObjects 17 }

tmnxDcpTimeEventOccured          OBJECT-TYPE
    SYNTAX      TimeStamp
    MAX-ACCESS  accessible-for-notify
    STATUS      current
    DESCRIPTION
        "The value of tmnxDcpTimeEventOccured indicates the actual time the
         event was detected in the system which may differ from the time that
         event was collected by the logging infrastructure."
    ::= { tmnxChassisNotificationObjects 18 }

tmnxDcpMissingNotificationCount  OBJECT-TYPE
    SYNTAX      Unsigned32
    MAX-ACCESS  accessible-for-notify
    STATUS      current
    DESCRIPTION
        "The value of tmnxDcpMissingNotificationCount indicates the number of
         events dropped because of event throttling during the last throttle
         interval for distributed CPU protection events."
    ::= { tmnxChassisNotificationObjects 19 }

tmnxChassisNotifyCardSlotNum     OBJECT-TYPE
    SYNTAX      TmnxSlotNum
    MAX-ACCESS  accessible-for-notify
    STATUS      current
    DESCRIPTION
        "The unique value of tmnxChassisNotifyCardSlotNum identifies the IOM
         slot within a chassis in the system."
    ::= { tmnxChassisNotificationObjects 20 }

tmnxChassisNotifyPowerZone       OBJECT-TYPE
    SYNTAX      Unsigned32
    MAX-ACCESS  accessible-for-notify
    STATUS      current
    DESCRIPTION
        "The value of tmnxChassisNotifyPowerZone indicates, along with the
         value of tmnxChassisNotifyChassisId, the row in the
         tmnxChassisPowerMgmtTable that is affected by the notification."
    ::= { tmnxChassisNotificationObjects 21 }

tmnxChassisNotifyPowerCapacity   OBJECT-TYPE
    SYNTAX      Unsigned32
    MAX-ACCESS  accessible-for-notify
    STATUS      current
    DESCRIPTION
        "The value of tmnxChassisNotifyPowerCapacity indicates the overall
         power capacity available to the system at the time of the
         notification."
    ::= { tmnxChassisNotificationObjects 22 }

tmnxPlcyAcctTimeEventOccured     OBJECT-TYPE
    SYNTAX      TimeStamp
    MAX-ACCESS  accessible-for-notify
    STATUS      current
    DESCRIPTION
        "The value of tmnxPlcyAcctTimeEventOccured indicates the actual time
         the event was detected in the system which may differ from the time
         that event was collected by the logging infrastructure."
    ::= { tmnxChassisNotificationObjects 23 }

tmnxPlcyAcctMissingNotifCount    OBJECT-TYPE
    SYNTAX      Unsigned32
    MAX-ACCESS  accessible-for-notify
    STATUS      current
    DESCRIPTION
        "The value of tmnxPlcyAcctMissingNotifCount indicates the number of
         events dropped because of event throttling during the last throttle
         interval for distributed policy accounting events."
    ::= { tmnxChassisNotificationObjects 24 }

tmnxChassisNotifyCpmCardSlotNum  OBJECT-TYPE
    SYNTAX      TmnxSlotNum
    MAX-ACCESS  accessible-for-notify
    STATUS      current
    DESCRIPTION
        "The unique value of tmnxChassisNotifyCpmCardSlotNum identifies the CPM
         slot within a chassis in the system."
    ::= { tmnxChassisNotificationObjects 25 }

tmnxChassisNotifyFabricSlotNum   OBJECT-TYPE
    SYNTAX      Unsigned32
    MAX-ACCESS  accessible-for-notify
    STATUS      current
    DESCRIPTION
        "The unique value of tmnxChassisNotifyFabricSlotNum identifies the
         fabric slot within a chassis in the system."
    ::= { tmnxChassisNotificationObjects 26 }

tmnxIomResourceType              OBJECT-TYPE
    SYNTAX      INTEGER {
        nextHop       (1),
        tunnelNextHop (2),
        stickyHash    (3),
        arpEntry      (4),
        ecmp          (5),
        ecmpNextHop   (6),
        ecmpTunnel    (7)
    }
    MAX-ACCESS  accessible-for-notify
    STATUS      current
    DESCRIPTION
        "Used by tmnxIomResHighLimitReached, tmnxIomResExhausted and
         tmnxIomResStateClr, the value of tmnxIomResourceType specifies the
         type of IOM resource."
    ::= { tmnxChassisNotificationObjects 27 }

tmnxIomResourceLimitPct          OBJECT-TYPE
    SYNTAX      Unsigned32
    MAX-ACCESS  accessible-for-notify
    STATUS      current
    DESCRIPTION
        "Used by tmnxIomResHighLimitReached, tmnxIomResExhausted and
         tmnxIomResStateClr, the value of tmnxIomResourceLimitPct specifies the
         percentage of IOM Resource being utilized."
    ::= { tmnxChassisNotificationObjects 28 }

tmnxIomResLimitTimeEventOccured  OBJECT-TYPE
    SYNTAX      TimeStamp
    MAX-ACCESS  accessible-for-notify
    STATUS      current
    DESCRIPTION
        "The value of tmnxIomResLimitTimeEventOccured indicates the actual time
         the event was detected in the system which may differ from the time
         that event was collected by the logging infrastructure."
    ::= { tmnxChassisNotificationObjects 29 }

tmnxIomResLimMissingNotifCount   OBJECT-TYPE
    SYNTAX      Unsigned32
    MAX-ACCESS  accessible-for-notify
    STATUS      current
    DESCRIPTION
        "The value of tmnxIomResLimMissingNotifCount indicates the number of
         events dropped because of event throttling during the last throttle
         interval for next hop resource events."
    ::= { tmnxChassisNotificationObjects 30 }

tmnxChassisNotifyFpNum           OBJECT-TYPE
    SYNTAX      Unsigned32
    MAX-ACCESS  accessible-for-notify
    STATUS      current
    DESCRIPTION
        "The value of tmnxChassisNotifyFpNum indicates the Forwarding Plane."
    ::= { tmnxChassisNotificationObjects 31 }

tmnxChassisNotifyDiskFullReason  OBJECT-TYPE
    SYNTAX      DisplayString
    MAX-ACCESS  accessible-for-notify
    STATUS      current
    DESCRIPTION
        "The value of tmnxChassisNotifyDiskFullReason indicates the reason for
         the disk full condition."
    ::= { tmnxChassisNotificationObjects 32 }

tmnxChassisNotifyMgmtEthRedPort  OBJECT-TYPE
    SYNTAX      TmnxPortID
    MAX-ACCESS  accessible-for-notify
    STATUS      current
    DESCRIPTION
        "The value of tmnxChassisNotifyMgmtEthRedPort indicates the CPM port
         operating as the system's management interface."
    ::= { tmnxChassisNotificationObjects 33 }

tmnxMacScaleCardSlotNum          OBJECT-TYPE
    SYNTAX      TmnxSlotNum
    MAX-ACCESS  accessible-for-notify
    STATUS      current
    DESCRIPTION
        "The unique value of tmnxMacScaleCardSlotNum identifies the card slot
         within a chassis in the system. It is used by the FDB MAC scale
         notifications."
    ::= { tmnxChassisNotificationObjects 38 }

tmnxChassisAdminObjects          OBJECT IDENTIFIER ::= { tmnxHwObjs 8 }

tmnxChassisAdminCtrlObjs         OBJECT IDENTIFIER ::= { tmnxChassisAdminObjects 1 }

tmnxChassisAdminOwner            OBJECT-TYPE
    SYNTAX      SnmpAdminString
    MAX-ACCESS  read-write
    STATUS      current
    DESCRIPTION
        "Who has last initialized the chassis administrative table, who is
         making all the changes, and who is expected to either commit or
         re-initialize (ABORT-TRANSACTION).

         tmnxChassisAdminOwner is advisory only. Before beginning a transaction,
         read tmnxChassisAdminOwner.  if it is empty then proceed with the
         configuration.

         Set tmnxChassisAdminOwner after setting tmnxChassisAdminControlApply
         so that other users will be advised to not make changes to the Admin
         tables.

         Agent sets tmnxChassisAdminOwner to empty string after
         tmnxChassisAdminControlApply is set - either by user initializing or
         committing, or by agent timing out the uncommitted transactions."
    ::= { tmnxChassisAdminCtrlObjs 1 }

tmnxChassisAdminControlApply     OBJECT-TYPE
    SYNTAX      INTEGER {
        none       (1),
        initialize (2),
        commit     (3)
    }
    MAX-ACCESS  read-write
    STATUS      current
    DESCRIPTION
        "The value of tmnxChassisAdminControlApply specifies how
         tmnxChassisAdminTable object is used in order to update
         tmnxChassisTable table objects.

         When set to initialize(2) (BEGIN-TRANSACTION), the objects in
         tmnxChassisAdminTable are set to the current Operational values, from
         the tmnxChassisTable.

         When set to commit(3) (END-TRANSACTION), all of the objects from
         tmnxChassisAdminTable are copied to the corresponding tmnxChassisTable
         table objects.

         When set to none(1) (ABORT-TRANSACTION) any uncommitted changes will
         be lost.

         If changes are not committed within a predefined timeout, they will be
         lost."
    ::= { tmnxChassisAdminCtrlObjs 2 }

tmnxChassisAdminLastSetTimer     OBJECT-TYPE
    SYNTAX      TimeInterval
    UNITS       "seconds"
    MAX-ACCESS  read-only
    STATUS      obsolete
    DESCRIPTION
        "The time remaining until the agent re-initializes the administrative
         tables.

         If tmnxChassisAdminControlApply is not set to commit(3) within
         tmnxChassisAdminLastSetTimeout seconds, the agent will set it to
         initialize(2) and all uncommitted changes will be lost.

         This way, uncommitted changes from failed (uncompleted) change sets
         will eventually be removed, and another transaction can safely begin.

         this object is reset to tmnxChassisAdminLastSetTimeout after SNMP SET
         operation to any of the tmnxChassisAdminValue tables."
    ::= { tmnxChassisAdminCtrlObjs 3 }

tmnxChassisAdminLastSetTimeout   OBJECT-TYPE
    SYNTAX      TimeInterval
    UNITS       "seconds"
    MAX-ACCESS  read-write
    STATUS      obsolete
    DESCRIPTION
        "Timeout for tmnxChassisAdminLastSetTimer. The value zero is not
         allowed."
    DEFVAL      { 1800 }
    ::= { tmnxChassisAdminCtrlObjs 4 }

tmnxChassisAdminValueObjs        OBJECT IDENTIFIER ::= { tmnxChassisAdminObjects 2 }

tSyncIfTimingAdmTable            OBJECT-TYPE
    SYNTAX      SEQUENCE OF TSyncIfTimingAdmEntry
    MAX-ACCESS  not-accessible
    STATUS      current
    DESCRIPTION
        "Values for the synchronous interface timing for the chassis.

         The VSR system does not support synchronous interface timing."
    ::= { tmnxChassisAdminValueObjs 1 }

tSyncIfTimingAdmEntry            OBJECT-TYPE
    SYNTAX      TSyncIfTimingAdmEntry
    MAX-ACCESS  not-accessible
    STATUS      current
    DESCRIPTION
        "Information about the synchronous interface timing. Entries are
         created by user. Entries are deleted by user. Note that the first
         Nokia SROS series product release does not support configuration of
         synchronous timing equipment on the secondary CPM. All SNMP operations
         with tmnxCpmCardSlotNum of the secondary CPM will be denied.

         In an XRS-40 system, the configuration of synchronous timing equipment
         on the extension chassis is not supported.

         The 7x50 systems supports 3 timing references (reference1, reference2
         and bits).

         The 7710 system only supports 2 timing references (reference1 and
         reference2).  On 7710 system, references can be a source port
         or a BITS input on a CES CMA.  If the value of the reference source
         port is a valid Port ID then the reference is a source port.  If the
         value of the source hardware is a valid HWIndex of a CES CMA then the
         source is a BITS on the CES CMA.

         The VSR system does not support synchronous interface timing."
    INDEX       {
        tmnxChassisIndex,
        tmnxCpmCardSlotNum,
        tmnxCpmCardNum
    }
    ::= { tSyncIfTimingAdmTable 1 }

TSyncIfTimingAdmEntry            ::= SEQUENCE
{
    tSyncIfTimingAdmRevert           TruthValue,
    tSyncIfTimingAdmRefOrder1        TmnxSETSRefSource,
    tSyncIfTimingAdmRefOrder2        TmnxSETSRefSource,
    tSyncIfTimingAdmRef1SrcPort      TmnxPortID,
    tSyncIfTimingAdmRef1AdminStatus  TmnxPortAdminStatus,
    tSyncIfTimingAdmRef2SrcPort      TmnxPortID,
    tSyncIfTimingAdmRef2AdminStatus  TmnxPortAdminStatus,
    tSyncIfTimingAdmChanged          Unsigned32,
    tSyncIfTimingAdmRefOrder3        TmnxSETSRefSource,
    tSyncIfTimingAdmBITSIfType       TmnxBITSIfType,
    tSyncIfTimingAdmBITSAdminStatus  TmnxPortAdminStatus,
    tSyncIfTimingAdmRef1SrcHw        TmnxHwIndexOrZero,
    tSyncIfTimingAdmRef1BITSIfType   TmnxBITSIfType,
    tSyncIfTimingAdmRef2SrcHw        TmnxHwIndexOrZero,
    tSyncIfTimingAdmRef2BITSIfType   TmnxBITSIfType,
    tSyncIfTimingAdmBITSOutAdmStatus TmnxPortAdminStatus,
    tSyncIfTimingAdmBITSOutLineLen   INTEGER,
    tSyncIfTimingAdmRef1CfgQltyLevel TmnxSSMQualityLevel,
    tSyncIfTimingAdmRef2CfgQltyLevel TmnxSSMQualityLevel,
    tSyncIfTimingAdmBITSCfgQltyLevel TmnxSSMQualityLevel,
    tSyncIfTimingAdmRef1NationalUse  Unsigned32,
    tSyncIfTimingAdmRef2NationalUse  Unsigned32,
    tSyncIfTimingAdmBITSNationalUse  Unsigned32,
    tSyncIfTimingAdmQLSelection      TmnxEnabledDisabled,
    tSyncIfTimingAdmRefOrder4        TmnxSETSRefSource,
    tSyncIfTimingAdmPTPAdminStatus   TmnxPortAdminStatus,
    tSyncIfTimingAdmPTPCfgQltyLevel  TmnxSSMQualityLevel,
    tSyncIfTimingAdmBITSOutSource    TmnxBITSOutSource,
    tSyncIfTimingAdmBITSOutQlMin     TmnxSSMQualityLevel,
    tSyncIfTimingAdmBITSOutSquelch   TruthValue,
    tSyncIfTimingAdmQlMin            TmnxSSMQualityLevel,
    tSyncIfTimingAdmWaitToRestorTime Unsigned32,
    tSyncIfTimingAdmChangedMask      BITS
}

tSyncIfTimingAdmRevert           OBJECT-TYPE
    SYNTAX      TruthValue
    MAX-ACCESS  read-create
    STATUS      current
    DESCRIPTION
        "The value of tSyncIfTimingAdmRevert specifies whether the reference
         source will revert to a higher priority source that has been
         re-validated or newly validated.

         The synchronous interface timing subsystem is by default non-revertive
         ('false')."
    DEFVAL      { false }
    ::= { tSyncIfTimingAdmEntry 1 }

tSyncIfTimingAdmRefOrder1        OBJECT-TYPE
    SYNTAX      TmnxSETSRefSource
    MAX-ACCESS  read-create
    STATUS      current
    DESCRIPTION
        "The value of tSyncIfTimingAdmRefOrder1 specifies the most preferred
         timing reference source.

         The synchronous equipment timing subsystem chooses a timing reference
         based on priority.

         The user can configure the priority order of the following timing
         reference inputs ('bits', 'reference1', 'reference2', and 'ptp').

         If the platform does not support that timing reference input, it
         cannot be configured in the reference priority order.  For example,
         the 'bits' timing reference cannot be configured on a 7750 SR-c12
         system.

         Other values of TmnxSETSRefSource (e.g. 'bits2') cannot be configured
         in the reference order."
    DEFVAL      { bits }
    ::= { tSyncIfTimingAdmEntry 2 }

tSyncIfTimingAdmRefOrder2        OBJECT-TYPE
    SYNTAX      TmnxSETSRefSource
    MAX-ACCESS  read-create
    STATUS      current
    DESCRIPTION
        "The value of tSyncIfTimingAdmRefOrder2 specifies the second most
         preferred timing reference for the synchronous equipment timing
         subsystem."
    DEFVAL      { reference1 }
    ::= { tSyncIfTimingAdmEntry 3 }

tSyncIfTimingAdmRef1SrcPort      OBJECT-TYPE
    SYNTAX      TmnxPortID
    MAX-ACCESS  read-create
    STATUS      current
    DESCRIPTION
        "The value of tSyncIfTimingAdmRef1SrcPort specifies the source port of
         the first timing reference.

         This can only be set to a valid TmnxPortID if the value of
         tSyncIfTimingAdmRef1SrcHw is 0."
    DEFVAL      { '1e000000'H }
    ::= { tSyncIfTimingAdmEntry 4 }

tSyncIfTimingAdmRef1AdminStatus  OBJECT-TYPE
    SYNTAX      TmnxPortAdminStatus
    MAX-ACCESS  read-create
    STATUS      current
    DESCRIPTION
        "The value of tSyncIfTimingAdmRef1AdminStatus specifies the desired
         administrative status of the first timing reference."
    DEFVAL      { outOfService }
    ::= { tSyncIfTimingAdmEntry 5 }

tSyncIfTimingAdmRef2SrcPort      OBJECT-TYPE
    SYNTAX      TmnxPortID
    MAX-ACCESS  read-create
    STATUS      current
    DESCRIPTION
        "The value of tSyncIfTimingAdmRef2SrcPort specifies the source port of
         the second timing reference.

         This can only be set to a valid TmnxPortID if the value of
         tSyncIfTimingAdmRef2SrcHw is 0."
    DEFVAL      { '1e000000'H }
    ::= { tSyncIfTimingAdmEntry 6 }

tSyncIfTimingAdmRef2AdminStatus  OBJECT-TYPE
    SYNTAX      TmnxPortAdminStatus
    MAX-ACCESS  read-create
    STATUS      current
    DESCRIPTION
        "The value of tSyncIfTimingAdmRef2AdminStatus specifies the desired
         administrative status of the second timing reference."
    DEFVAL      { outOfService }
    ::= { tSyncIfTimingAdmEntry 7 }

tSyncIfTimingAdmChanged          OBJECT-TYPE
    SYNTAX      Unsigned32
    MAX-ACCESS  read-create
    STATUS      current
    DESCRIPTION
        "The value of tSyncIfTimingAdmChanged is a bitmask that indicates which
         objects have been set, but not committed.  bit values used here are:

         0x0001:    tSyncIfTimingAdmRevert
         0x0002:    tSyncIfTimingAdmRefOrder1
         0x0004:    tSyncIfTimingAdmRefOrder2
         0x0008:    tSyncIfTimingAdmRef1SrcPort
         0x0010:    tSyncIfTimingAdmRef1AdminStatus
         0x0020:    tSyncIfTimingAdmRef2SrcPort
         0x0040:    tSyncIfTimingAdmRef2AdminStatus
         0x0080:    tSyncIfTimingAdmRefOrder3
         0x0100:    tSyncIfTimingAdmBITSIfType
         0x0200:    tSyncIfTimingAdmBITSAdminStatus
         0x0400:    tSyncIfTimingAdmRef1SrcHw
         0x0800:    tSyncIfTimingAdmRef1BITSIfType
         0x1000:    tSyncIfTimingAdmRef2SrcHw
         0x2000:    tSyncIfTimingAdmRef2BITSIfType

         The agent sets these bits when an object in the row
         is set.  This object is cleared to zero by setting
         tmnxChassisAdminControlApply to initialize(2) or commit(3)."
    ::= { tSyncIfTimingAdmEntry 8 }

tSyncIfTimingAdmRefOrder3        OBJECT-TYPE
    SYNTAX      TmnxSETSRefSource
    MAX-ACCESS  read-create
    STATUS      current
    DESCRIPTION
        "The value of tSyncIfTimingAdmRefOrder3 specifies the third most
         preferred timing reference for the synchronous equipment timing
         subsystem."
    DEFVAL      { reference2 }
    ::= { tSyncIfTimingAdmEntry 9 }

tSyncIfTimingAdmBITSIfType       OBJECT-TYPE
    SYNTAX      TmnxBITSIfType
    MAX-ACCESS  read-create
    STATUS      current
    DESCRIPTION
        "The value of tSyncIfTimingAdmBITSIfType specifies the interface type
         of the BITS (Building Integrated Timing Supply) timing reference."
    DEFVAL      { t1-esf }
    ::= { tSyncIfTimingAdmEntry 10 }

tSyncIfTimingAdmBITSAdminStatus  OBJECT-TYPE
    SYNTAX      TmnxPortAdminStatus
    MAX-ACCESS  read-create
    STATUS      current
    DESCRIPTION
        "The value of tSyncIfTimingAdmBITSAdminStatus specifies the desired
         administrative status of the BITS (Building Integrated Timing Supply)
         input timing reference."
    DEFVAL      { outOfService }
    ::= { tSyncIfTimingAdmEntry 11 }

tSyncIfTimingAdmRef1SrcHw        OBJECT-TYPE
    SYNTAX      TmnxHwIndexOrZero
    MAX-ACCESS  read-create
    STATUS      current
    DESCRIPTION
        "The value of tSyncIfTimingAdmRef1SrcHw specifies the source HW Index
         of the first timing reference if the source is not a port.

         This can only be set to a valid HW Index if the value of
         tSyncIfTimingAdmRef1SrcPort is '1e000000'H.

         Setting the value of tSyncIfTimingAdmRef1SrcHw from non-zero to zero
         will cause the value of tSyncIfTimingAdmRef1BITSIfType to be reset to
         its default value of 't1-esf'."
    DEFVAL      { 0 }
    ::= { tSyncIfTimingAdmEntry 12 }

tSyncIfTimingAdmRef1BITSIfType   OBJECT-TYPE
    SYNTAX      TmnxBITSIfType
    MAX-ACCESS  read-create
    STATUS      current
    DESCRIPTION
        "The value of tSyncIfTimingAdmRef1BITSIfType specifies the interface
         type of the first timing reference if the source is BITS.

         This can only be changed if the value of tSyncIfTimingAdmRef1SrcHw is
         not 0."
    DEFVAL      { t1-esf }
    ::= { tSyncIfTimingAdmEntry 13 }

tSyncIfTimingAdmRef2SrcHw        OBJECT-TYPE
    SYNTAX      TmnxHwIndexOrZero
    MAX-ACCESS  read-create
    STATUS      current
    DESCRIPTION
        "The value of tSyncIfTimingAdmRef2SrcHw specifies the source HW Index
         of the second timing reference if the source is not a port.

         This can only be set to a valid HW Index if the value of
         tSyncIfTimingAdmRef2SrcPort is '1e000000'H.

         Setting the value of tSyncIfTimingAdmRef2SrcHw from non-zero to zero
         will cause the value of tSyncIfTimingAdmRef2BITSIfType to be reset to
         its default value of 't1-esf'."
    DEFVAL      { 0 }
    ::= { tSyncIfTimingAdmEntry 14 }

tSyncIfTimingAdmRef2BITSIfType   OBJECT-TYPE
    SYNTAX      TmnxBITSIfType
    MAX-ACCESS  read-create
    STATUS      current
    DESCRIPTION
        "The value of tSyncIfTimingAdmRef2BITSIfType specifies the interface
         type of the second timing reference if the source is BITS.

         This can only be changed if the value of tSyncIfTimingAdmRef2SrcHw is
         not 0."
    DEFVAL      { t1-esf }
    ::= { tSyncIfTimingAdmEntry 15 }

tSyncIfTimingAdmBITSOutAdmStatus OBJECT-TYPE
    SYNTAX      TmnxPortAdminStatus
    MAX-ACCESS  read-create
    STATUS      current
    DESCRIPTION
        "The value of tSyncIfTimingAdmBITSOutAdmStatus specifies administrative
         status of the BITS (Building Integrated Timing Supply) output timing
         reference.

         In an XRS-40 system, tSyncIfTimingAdmBITSOutAdmStatus is always
         'inService(2)', and cannot be changed.  In an XRS-40 system, the
         extension chassis is synchronized with the master chassis via the BITS
         ports.  See the description of tSyncIfTimingAdmBITSOutSource for
         details on how the BITS ports are used to synchronize the master and
         extension chassis of the XRS-40 system."
    DEFVAL      { outOfService }
    ::= { tSyncIfTimingAdmEntry 16 }

tSyncIfTimingAdmBITSOutLineLen   OBJECT-TYPE
    SYNTAX      INTEGER {
        lengthNotApplicable (0),
        length0To110        (1),
        length110To220      (2),
        length220To330      (3),
        length330To440      (4),
        length440To550      (5),
        length550To660      (6)
    }
    MAX-ACCESS  read-create
    STATUS      current
    DESCRIPTION
        "tSyncIfTimingAdmBITSOutLineLen specifies the length of the line
         (in feet) for the BITS (Building Integrated Timing Supply) output.
         The following values are valid:
             lengthNotApplicable (0) - When BITS output is not supported
             length0To110        (1) - For line length from 0 to 110 feet
             length110To220      (2) - For line length from 110 to 220 feet
             length220To330      (3) - For line length from 230 to 330 feet
             length330To440      (4) - For line length from 330 to 440 feet
             length440To550      (5) - For line length from 440 to 550 feet
             length550To660      (6) - For line length from 550 to 660 feet
         The default is 'lengthNotApplicable' on CPM cards which do not
         support line length.  Otherwise, the default is 'length0To110'."
    DEFVAL      { lengthNotApplicable }
    ::= { tSyncIfTimingAdmEntry 17 }

tSyncIfTimingAdmRef1CfgQltyLevel OBJECT-TYPE
    SYNTAX      TmnxSSMQualityLevel
    MAX-ACCESS  read-create
    STATUS      current
    DESCRIPTION
        "The value of tSyncIfTimingAdmRef1CfgQltyLevel specifies the configured
         Quality Level of Reference 1. A value of 'unknown (0)' indicates
         Reference 1 is not forced to a specific quality level."
    DEFVAL      { unknown }
    ::= { tSyncIfTimingAdmEntry 18 }

tSyncIfTimingAdmRef2CfgQltyLevel OBJECT-TYPE
    SYNTAX      TmnxSSMQualityLevel
    MAX-ACCESS  read-create
    STATUS      current
    DESCRIPTION
        "The value of tSyncIfTimingAdmRef2CfgQltyLevel specifies the configured
         Quality Level of Reference 2. A value of 'unknown (0)' indicates
         Reference 2 is not forced to a specific quality level."
    DEFVAL      { unknown }
    ::= { tSyncIfTimingAdmEntry 19 }

tSyncIfTimingAdmBITSCfgQltyLevel OBJECT-TYPE
    SYNTAX      TmnxSSMQualityLevel
    MAX-ACCESS  read-create
    STATUS      current
    DESCRIPTION
        "The value of tSyncIfTimingAdmBITSCfgQltyLevel specifies the configured
         Quality Level of the BITS interface. A value of 'unknown (0)'
         indicates the BITS interface is not forced to a specific quality
         level."
    DEFVAL      { unknown }
    ::= { tSyncIfTimingAdmEntry 20 }

tSyncIfTimingAdmRef1NationalUse  OBJECT-TYPE
    SYNTAX      Unsigned32 (4..8)
    MAX-ACCESS  read-create
    STATUS      current
    DESCRIPTION
        "The value of tSyncIfTimingAdmRef1NationalUse specifies the national
         use bit to carry SSM Messages. This applies only to E1 BITS
         interfaces."
    DEFVAL      { 8 }
    ::= { tSyncIfTimingAdmEntry 21 }

tSyncIfTimingAdmRef2NationalUse  OBJECT-TYPE
    SYNTAX      Unsigned32 (4..8)
    MAX-ACCESS  read-create
    STATUS      current
    DESCRIPTION
        "The value of tSyncIfTimingAdmRef2NationalUse specifies the national
         use bit to carry SSM Messages. This applies only to E1 BITS
         interfaces."
    DEFVAL      { 8 }
    ::= { tSyncIfTimingAdmEntry 22 }

tSyncIfTimingAdmBITSNationalUse  OBJECT-TYPE
    SYNTAX      Unsigned32 (4..8)
    MAX-ACCESS  read-create
    STATUS      current
    DESCRIPTION
        "The value of tSyncIfTimingAdmBITSNationalUse specifies the national
         use bit to carry SSM Messages. This applies only to E1 BITS
         interfaces."
    DEFVAL      { 8 }
    ::= { tSyncIfTimingAdmEntry 23 }

tSyncIfTimingAdmQLSelection      OBJECT-TYPE
    SYNTAX      TmnxEnabledDisabled
    MAX-ACCESS  read-create
    STATUS      current
    DESCRIPTION
        "The value of tSyncIfTimingAdmQLSelection specifies whether or not the
         timing reference selection process uses the quality level of each
         timing reference when making the decision on which reference should
         provide system timing."
    REFERENCE
        "ITU-T Recommendation G.781, June 1999, Section 5.12"
    DEFVAL      { disabled }
    ::= { tSyncIfTimingAdmEntry 24 }

tSyncIfTimingAdmRefOrder4        OBJECT-TYPE
    SYNTAX      TmnxSETSRefSource
    MAX-ACCESS  read-create
    STATUS      current
    DESCRIPTION
        "The value of tSyncIfTimingAdmRefOrder4 specifies the fourth most
         preferred timing reference for the synchronous equipment timing
         subsystem."
    DEFVAL      { ptp }
    ::= { tSyncIfTimingAdmEntry 25 }

tSyncIfTimingAdmPTPAdminStatus   OBJECT-TYPE
    SYNTAX      TmnxPortAdminStatus
    MAX-ACCESS  read-create
    STATUS      current
    DESCRIPTION
        "The value of tSyncIfTimingAdmPTPAdminStatus specifies the desired
         administrative status of the Precision Timing Protocol (PTP) timing
         reference."
    DEFVAL      { outOfService }
    ::= { tSyncIfTimingAdmEntry 26 }

tSyncIfTimingAdmPTPCfgQltyLevel  OBJECT-TYPE
    SYNTAX      TmnxSSMQualityLevel
    MAX-ACCESS  read-create
    STATUS      current
    DESCRIPTION
        "The value of tSyncIfTimingAdmPTPCfgQltyLevel specifies the configured
         Quality Level of the Precision Timing Protocol (PTP). A value of
         'unknown (0)' specifies PTP is not forced to a specific quality level."
    DEFVAL      { unknown }
    ::= { tSyncIfTimingAdmEntry 27 }

tSyncIfTimingAdmBITSOutSource    OBJECT-TYPE
    SYNTAX      TmnxBITSOutSource
    MAX-ACCESS  read-create
    STATUS      current
    DESCRIPTION
        "The value of tSyncIfTimingAdmBITSOutSource specifies the source of the
         BITS (Building Integrated Timing Supply) output.

         In an XRS-40 system, the extension chassis is synchronized with the
         master chassis via the BITS ports.  Two modes of operation are
         permitted:
         1)  The BITS output ports of the master chassis CPMs are connected to
             the BITS input ports of the extension chassis CPMs.  In this mode,
             tSyncIfTimingAdmBITSOutSource should be set to 'internalClock(2)',
             to ensure that a valid clock signal is transmitted on the master
             chassis's CPMs' BITS output ports.
         2)  The BITS input ports of all 4 CPMs are connected to external BITS
             equipment.  In this mode, the customer may connect the master
             chassis's BITS output ports to the external BITS equipment's input
             ports.  This allows for recovered line references to be provided as
             a frequency source into the external BITS equipment following the
             inter-site synchronization mode of SDH/SONET.  In this case,
             tSyncIfTimingAdmBITSOutSource should be set to 'lineRef(1)'."
    DEFVAL      { lineRef }
    ::= { tSyncIfTimingAdmEntry 28 }

tSyncIfTimingAdmBITSOutQlMin     OBJECT-TYPE
    SYNTAX      TmnxSSMQualityLevel
    MAX-ACCESS  read-create
    STATUS      current
    DESCRIPTION
        "The value of tSyncIfTimingAdmBITSOutQlMin specifies the minimum
         quality level that a signal must have for it to be selected for BITS
         output. This can be used to ensure that the signal has traceability to
         a source with at least a specific quality level so that the attached
         equipment can function properly.

         A value of 'unknown (0)' indicates that there is no minimum quality
         level.

         Values: 'smc (7)', st4 (8)', 'dus (9)', 'dnu (14)', 'inv (15)', 'pno
         (16)', and 'failed (19)' are not supported for this object."
    DEFVAL      { unknown }
    ::= { tSyncIfTimingAdmEntry 29 }

tSyncIfTimingAdmBITSOutSquelch   OBJECT-TYPE
    SYNTAX      TruthValue
    MAX-ACCESS  read-create
    STATUS      current
    DESCRIPTION
        "The value of tSyncIfTimingAdmBITSOutSquelch specifies whether or not
         to squelch the output signal. This object is only valid when there is
         no valid reference selected.

         If the value is 'true (1)' and there is no valid reference, then no
         signal is sent out the port.

         If the value is 'false (2)' and there is no valid reference, then the
         AIS signal is presented along with the QL-DNU/QL-DUS SSM if the signal
         format supports SSM."
    DEFVAL      { false }
    ::= { tSyncIfTimingAdmEntry 30 }

tSyncIfTimingAdmQlMin            OBJECT-TYPE
    SYNTAX      TmnxSSMQualityLevel
    MAX-ACCESS  read-create
    STATUS      current
    DESCRIPTION
        "The value of tSyncIfTimingAdmQlMin specifies the minimum acceptable
         quality level that a signal must have for it to be considered for
         selection by the system timing module.

         A value of 'unknown (0)' indicates that there is no minimum quality
         level.

         Values: 'st4 (8)', 'dus (9)', 'prc (10)', 'dnu (14)', 'inv (15)', 'pno
         (16)', and 'failed (19)' are not supported for this object."
    DEFVAL      { unknown }
    ::= { tSyncIfTimingAdmEntry 32 }

tSyncIfTimingAdmWaitToRestorTime OBJECT-TYPE
    SYNTAX      Unsigned32 (0..12)
    UNITS       "minutes"
    MAX-ACCESS  read-create
    STATUS      current
    DESCRIPTION
        "The value of tSyncIfTimingAdmWaitToRestorTime specifies the time, in
         minutes, that a previously failed input reference must be valid before
         it will be used for either the BITS output or the central clock input
         reference.

         A value of '0' indicates that the wait-to-restore timer is disabled."
    DEFVAL      { 0 }
    ::= { tSyncIfTimingAdmEntry 33 }

tSyncIfTimingAdmChangedMask      OBJECT-TYPE
    SYNTAX      BITS {
        tSyncIfTimingAdmRevert           (0),
        tSyncIfTimingAdmRefOrder1        (1),
        tSyncIfTimingAdmRefOrder2        (2),
        tSyncIfTimingAdmRef1SrcPort      (3),
        tSyncIfTimingAdmRef1AdminStatus  (4),
        tSyncIfTimingAdmRef2SrcPort      (5),
        tSyncIfTimingAdmRef2AdminStatus  (6),
        tSyncIfTimingAdmChanged          (7),
        tSyncIfTimingAdmRefOrder3        (8),
        tSyncIfTimingAdmBITSIfType       (9),
        tSyncIfTimingAdmBITSAdminStatus  (10),
        tSyncIfTimingAdmRef1SrcHw        (11),
        tSyncIfTimingAdmRef1BITSIfType   (12),
        tSyncIfTimingAdmRef2SrcHw        (13),
        tSyncIfTimingAdmRef2BITSIfType   (14),
        tSyncIfTimingAdmBITSOutAdmStatus (15),
        tSyncIfTimingAdmBITSOutLineLen   (16),
        tSyncIfTimingAdmRef1CfgQltyLevel (17),
        tSyncIfTimingAdmRef2CfgQltyLevel (18),
        tSyncIfTimingAdmBITSCfgQltyLevel (19),
        tSyncIfTimingAdmRef1NationalUse  (20),
        tSyncIfTimingAdmRef2NationalUse  (21),
        tSyncIfTimingAdmBITSNationalUse  (22),
        tSyncIfTimingAdmQLSelection      (23),
        tSyncIfTimingAdmRefOrder4        (24),
        tSyncIfTimingAdmPTPAdminStatus   (25),
        tSyncIfTimingAdmPTPCfgQltyLevel  (26),
        tSyncIfTimingAdmBITSOutSource    (27),
        tSyncIfTimingAdmBITSOutQlMin     (28),
        tSyncIfTimingAdmBITSOutSquelch   (29),
        tSyncIfTimingAdmHoldOffTime      (30),
        tSyncIfTimingAdmQlMin            (31),
        tSyncIfTimingAdmWaitToRestorTime (32),
        tSyncIfTimingAdmChangedMask      (33)
    }
    MAX-ACCESS  read-only
    STATUS      current
    DESCRIPTION
        "The value of tSyncIfTimingAdmChangedMask indicates a bitmask of which
         synchronous interface timing objects have been set, but not committed.

         The agent sets these bits when an object in tSyncIfTimingAdmEntry is
         set. All bits are cleared when tmnxChassisAdminControlApply is set to
         'initialize (2)' or 'commit (3)'.

         Bits 'tSyncIfTimingAdmChanged (7)' and 'tSyncIfTimingAdmChangedMask
         (33)' are not valid. This object replaces the functionality of
         tSyncIfTimingAdmChanged."
    ::= { tSyncIfTimingAdmEntry 34 }

tmnxHwConformance                OBJECT IDENTIFIER ::= { tmnxSRConfs 2 }

tmnxChassisConformance           OBJECT IDENTIFIER ::= { tmnxHwConformance 1 }

tmnxChassisCompliances           OBJECT IDENTIFIER ::= { tmnxChassisConformance 1 }

tmnxChassisV4v0Compliance        MODULE-COMPLIANCE
    STATUS      obsolete
    DESCRIPTION
        "The compliance statement for management of chassis features in the
         TIMETRA-CHASSIS-MIB."
    MODULE
        MANDATORY-GROUPS {
            tmnxChassisV3v0Group,
            tmnxCardV3v0Group,
            tmnxMDAV4v0Group,
            tmnxChassisNotificationV4v0Group
        }
    ::= { tmnxChassisCompliances 4 }

tmnxChassisComp7710              OBJECT IDENTIFIER ::= { tmnxChassisCompliances 5 }

tmnxChassisComp7710V3v0          MODULE-COMPLIANCE
    STATUS      obsolete
    DESCRIPTION
        "The compliance statement for management of chassis features for the
         7710 in the TIMETRA-CHASSIS-MIB."
    MODULE
        MANDATORY-GROUPS {
            tmnxChassisV3v0Group,
            tmnxCardV3v0Group,
            tmnxMDAV3v0Group,
            tmnxChassisNotificationV3v0Group,
            tmnx7710HwV3v0Group
        }
    ::= { tmnxChassisComp7710 1 }

tmnxChassisComp7710V5v0          MODULE-COMPLIANCE
    STATUS      obsolete
    DESCRIPTION
        "The compliance statement for management of chassis features for the
         7710 in the TIMETRA-CHASSIS-MIB."
    MODULE
        MANDATORY-GROUPS {
            tmnxChassisV5v0Group,
            tmnxCardV3v0Group,
            tmnxMDAV4v0Group,
            tmnxChassisNotificationV4v0Group,
            tmnx7710HwV3v0Group
        }
    ::= { tmnxChassisComp7710 2 }

tmnxChassisComp7710V6v0          MODULE-COMPLIANCE
    STATUS      obsolete
    DESCRIPTION
        "The compliance statement for management of chassis features for the
         7710 in the TIMETRA-CHASSIS-MIB."
    MODULE
        MANDATORY-GROUPS {
            tmnxChassisV5v0Group,
            tmnxCardV3v0Group,
            tmnxMDAV4v0Group,
            tmnxChassisNotificationV6v0Group,
            tmnx7710HwV3v0Group,
            tmnx77x0CESMDAV6v0Group,
            tmnxIPsecIsaGrpV6v0Group,
            tmnx7710SETSRefSrcHwV6v0Group,
            tmnxCardV6v0NamedPoolPlcyGroup,
            tmnxSyncV6v0Group,
            tmnxChassisV6v0Group
        }
    ::= { tmnxChassisComp7710 3 }

tmnxChassisComp7710V6v1          MODULE-COMPLIANCE
    STATUS      obsolete
    DESCRIPTION
        "The compliance statement for management of chassis features for the
         7710 in the TIMETRA-CHASSIS-MIB."
    MODULE
        MANDATORY-GROUPS {
            tmnxChassisV5v0Group,
            tmnxCardV3v0Group,
            tmnxMDAV6v1Group,
            tmnxChassisNotificationV6v1Group,
            tmnx7710HwV3v0Group,
            tmnx77x0CESMDAV6v0Group,
            tmnxIPsecIsaGrpV6v0Group,
            tmnx7710SETSRefSrcHwV6v0Group,
            tmnxCardV6v0NamedPoolPlcyGroup,
            tmnxChassisV6v1Group,
            tmnxMdaXplV5v0Group,
            tmnxCardPchipV5v0Group,
            tmnxCardCamErrorV6v1Group,
            tmnxSyncV6v0Group,
            tmnxChassisHwV6v1Group
        }
    ::= { tmnxChassisComp7710 4 }

tmnxChassisComp7710V7v0          MODULE-COMPLIANCE
    STATUS      obsolete
    DESCRIPTION
        "The compliance statement for management of chassis features for the
         7710 in the TIMETRA-CHASSIS-MIB."
    MODULE
        MANDATORY-GROUPS {
            tmnxChassisV5v0Group,
            tmnxCardV3v0Group,
            tmnxMDAV6v1Group,
            tmnxChassisNotificationV7v0Group,
            tmnx7710HwV3v0Group,
            tmnx77x0CESMDAV6v0Group,
            tmnxIPsecIsaGrpV6v0Group,
            tmnx7710SETSRefSrcHwV6v0Group,
            tmnxCardV6v0NamedPoolPlcyGroup,
            tmnxChassisV6v1Group,
            tmnxChassisV7v0Group,
            tmnxMdaXplV5v0Group,
            tmnxChassisUserModV7v0Group,
            tmnxCardPchipV5v0Group,
            tmnxCardCamErrorV6v1Group,
            tmnxCardV7v0Group,
            tmnxFPWredV7v0Group,
            tmnxIPsecV7v0Group,
            tmnxIPsecNotifV7v0Group,
            tmnxSyncV6v0Group,
            tmnxChassisHwV6v1Group
        }
    ::= { tmnxChassisComp7710 5 }

tmnxChassisComp7710V8v0          MODULE-COMPLIANCE
    STATUS      obsolete
    DESCRIPTION
        "The compliance statement for management of chassis features for the
         7710 in the TIMETRA-CHASSIS-MIB.

         This MODULE-COMPLIANCE has been replaced by tmnxChassisV9v0Compliance."
    MODULE
        MANDATORY-GROUPS {
            tmnxChassisV5v0Group,
            tmnxChassisV8v0Group,
            tmnxCardV3v0Group,
            tmnxMDAV6v1Group,
            tmnxChassisNotificationV7v0Group,
            tmnx7710HwV3v0Group,
            tmnx77x0CESMDAV6v0Group,
            tmnxIPsecIsaGrpV6v0Group,
            tmnx7710SETSRefSrcHwV6v0Group,
            tmnxCardV6v0NamedPoolPlcyGroup,
            tmnxChassisV6v1Group,
            tmnxChassisV7v0Group,
            tmnxMdaXplV5v0Group,
            tmnxChassisUserModV7v0Group,
            tmnxCardPchipV5v0Group,
            tmnxCardPchipV8v0Group,
            tmnxCardCamErrorV6v1Group,
            tmnxCardV7v0Group,
            tmnxFPWredV7v0Group,
            tmnxIPsecV7v0Group,
            tmnxIPsecNotifV7v0Group,
            tmnxSyncIfTimingV8v0Group,
            tmnxSyncV6v0Group,
            tmnxSyncIfTimingNotifV8v0Group,
            tmnxChassisHwV6v1Group
        }
    ::= { tmnxChassisComp7710 6 }

tmnxChassisV5v0Compliance        MODULE-COMPLIANCE
    STATUS      obsolete
    DESCRIPTION
        "The compliance statement for management of chassis features in the
         TIMETRA-CHASSIS-MIB."
    MODULE
        MANDATORY-GROUPS {
            tmnxChassisV5v0Group,
            tmnxCardV3v0Group,
            tmnxMDAV4v0Group,
            tmnxChassisNotificationV4v0Group,
            tmnxChassisNotificationV5v0Group,
            tmnxMdaXplV5v0Group,
            tmnxCardPchipV5v0Group
        }
    ::= { tmnxChassisCompliances 6 }

tmnxChassis7750V6v0Compliance    MODULE-COMPLIANCE
    STATUS      obsolete
    DESCRIPTION
        "The compliance statement for management of chassis features on the
         7750 in the TIMETRA-CHASSIS-MIB."
    MODULE
        MANDATORY-GROUPS {
            tmnxChassisV5v0Group,
            tmnxCardV3v0Group,
            tmnxMDAV4v0Group,
            tmnxChassisNotificationV6v0Group,
            tmnx77x0CESMDAV6v0Group,
            tmnxCardV6v0NamedPoolPlcyGroup,
            tmnxIPsecIsaGrpV6v0Group,
            tmnxChassisHsmdaV6v0Group,
            tmnxMDAMcPathMgmtV6v0Group,
            tmnxMdaXplV5v0Group,
            tmnxCardPchipV5v0Group,
            tmnxSyncV6v0Group,
            tmnxChassisV6v0Group
        }
    ::= { tmnxChassisCompliances 7 }

tmnxChassis7450V6v0Compliance    MODULE-COMPLIANCE
    STATUS      obsolete
    DESCRIPTION
        "The compliance statement for management of chassis features on the
         7450 in the TIMETRA-CHASSIS-MIB."
    MODULE
        MANDATORY-GROUPS {
            tmnxChassisV5v0Group,
            tmnxCardV3v0Group,
            tmnxMDAV4v0Group,
            tmnxCardV6v0NamedPoolPlcyGroup,
            tmnxChassisNotificationV6v0Group,
            tmnxChassisHsmdaV6v0Group,
            tmnxMDAMcPathMgmtV6v0Group,
            tmnxMdaXplV5v0Group,
            tmnxCardPchipV5v0Group,
            tmnxSyncV6v0Group,
            tmnxChassisV6v0Group
        }
    ::= { tmnxChassisCompliances 8 }

tmnxChassis7750V6v1Compliance    MODULE-COMPLIANCE
    STATUS      obsolete
    DESCRIPTION
        "The compliance statement for management of chassis features on the
         7750 in the TIMETRA-CHASSIS-MIB."
    MODULE
        MANDATORY-GROUPS {
            tmnxChassisV5v0Group,
            tmnxCardV3v0Group,
            tmnxMDAV6v1Group,
            tmnxChassisNotificationV6v0Group,
            tmnx77x0CESMDAV6v0Group,
            tmnxCardV6v0NamedPoolPlcyGroup,
            tmnxIPsecIsaGrpV6v0Group,
            tmnxChassisHsmdaV6v0Group,
            tmnxMDAMcPathMgmtV6v0Group,
            tmnxChassisV6v1Group,
            tmnxFPMcPathMgmtV6v1Group,
            tmnxMDACcagV6v1Group,
            tmnxMdaXplV5v0Group,
            tmnxCardPchipV5v0Group,
            tmnxCardCamErrorV6v1Group,
            tmnxSyncV6v0Group,
            tmnxChassisHwV6v1Group
        }
    ::= { tmnxChassisCompliances 9 }

tmnxChassis7450V6v1Compliance    MODULE-COMPLIANCE
    STATUS      obsolete
    DESCRIPTION
        "The compliance statement for management of chassis features on the
         7450 in the TIMETRA-CHASSIS-MIB."
    MODULE
        MANDATORY-GROUPS {
            tmnxChassisV5v0Group,
            tmnxCardV3v0Group,
            tmnxMDAV6v1Group,
            tmnxCardV6v0NamedPoolPlcyGroup,
            tmnxChassisNotificationV6v0Group,
            tmnxChassisHsmdaV6v0Group,
            tmnxMDAMcPathMgmtV6v0Group,
            tmnxChassisV6v1Group,
            tmnxFPMcPathMgmtV6v1Group,
            tmnxMDACcagV6v1Group,
            tmnxMdaXplV5v0Group,
            tmnxCardPchipV5v0Group,
            tmnxCardCamErrorV6v1Group,
            tmnxSyncV6v0Group,
            tmnxChassisHwV6v1Group
        }
    ::= { tmnxChassisCompliances 10 }

tmnxChassis7750V7v0Compliance    MODULE-COMPLIANCE
    STATUS      obsolete
    DESCRIPTION
        "The compliance statement for management of chassis features on the
         7750 in the TIMETRA-CHASSIS-MIB."
    MODULE
        MANDATORY-GROUPS {
            tmnxChassisV5v0Group,
            tmnxCardV3v0Group,
            tmnxMDAV6v1Group,
            tmnxChassisNotificationV7v0Group,
            tmnx77x0CESMDAV6v0Group,
            tmnxCardV6v0NamedPoolPlcyGroup,
            tmnxIPsecIsaGrpV6v0Group,
            tmnxChassisHsmdaV6v0Group,
            tmnxMDAMcPathMgmtV6v0Group,
            tmnxChassisV6v1Group,
            tmnxFPMcPathMgmtV6v1Group,
            tmnxMDACcagV6v1Group,
            tmnxChassisUserModV7v0Group,
            tmnxCardV7v0Group,
            tmnxFPWredV7v0Group,
            tmnxIPsecV7v0Group,
            tmnxIPsecNotifV7v0Group,
            tmnxMdaXplV5v0Group,
            tmnxCardPchipV5v0Group,
            tmnxCardCamErrorV6v1Group,
            tmnxSyncV6v0Group,
            tmnxChassisHwV6v1Group
        }
    ::= { tmnxChassisCompliances 11 }

tmnxChassis7450V7v0Compliance    MODULE-COMPLIANCE
    STATUS      obsolete
    DESCRIPTION
        "The compliance statement for management of chassis features on the
         7450 in the TIMETRA-CHASSIS-MIB."
    MODULE
        MANDATORY-GROUPS {
            tmnxChassisV5v0Group,
            tmnxCardV3v0Group,
            tmnxMDAV6v1Group,
            tmnxCardV6v0NamedPoolPlcyGroup,
            tmnxChassisNotificationV7v0Group,
            tmnxChassisHsmdaV6v0Group,
            tmnxMDAMcPathMgmtV6v0Group,
            tmnxChassisV6v1Group,
            tmnxFPMcPathMgmtV6v1Group,
            tmnxMDACcagV6v1Group,
            tmnxChassisUserModV7v0Group,
            tmnxCardV7v0Group,
            tmnxFPWredV7v0Group,
            tmnxMdaXplV5v0Group,
            tmnxCardPchipV5v0Group,
            tmnxCardCamErrorV6v1Group,
            tmnxSyncV6v0Group,
            tmnxChassisHwV6v1Group
        }
    ::= { tmnxChassisCompliances 12 }

tmnxChassis7x50V8v0Compliance    MODULE-COMPLIANCE
    STATUS      obsolete
    DESCRIPTION
        "The compliance statement for management of chassis features on the
         7x50 in the TIMETRA-CHASSIS-MIB."
    MODULE
        MANDATORY-GROUPS {
            tmnxChassisV5v0Group,
            tmnxChassisV8v0Group,
            tmnxCardV3v0Group,
            tmnxMDAV6v1Group,
            tmnxChassisNotificationV7v0Group,
            tmnx77x0CESMDAV6v0Group,
            tmnxCardV6v0NamedPoolPlcyGroup,
            tmnxIPsecIsaGrpV6v0Group,
            tmnx7710HwV3v0Group,
            tmnx7710SETSRefSrcHwV6v0Group,
            tmnxChassisHsmdaV6v0Group,
            tmnxMDAMcPathMgmtV6v0Group,
            tmnxChassisV6v1Group,
            tmnxChassisV7v0Group,
            tmnxFPMcPathMgmtV6v1Group,
            tmnxMDACcagV6v1Group,
            tmnxChassisUserModV7v0Group,
            tmnxCardV7v0Group,
            tmnxFPWredV7v0Group,
            tmnxIPsecV7v0Group,
            tmnxIPsecNotifV7v0Group,
            tmnxSyncIfTimingV8v0Group,
            tmnxChassisMixedModeIomV8v0Group,
            tmnxMdaXplV5v0Group,
            tmnxCardPchipV5v0Group,
            tmnxCardPchipV8v0Group,
            tmnxCardCamErrorV6v1Group,
            tmnxSyncV6v0Group,
            tmnxSyncIfTimingNotifV8v0Group,
            tmnxChassisHwV6v1Group
        }
    ::= { tmnxChassisCompliances 13 }

tmnxChassisV9v0Compliance        MODULE-COMPLIANCE
    STATUS      obsolete
    DESCRIPTION
        "The compliance statement for management of chassis features on SROS
         series systems in the TIMETRA-CHASSIS-MIB."
    MODULE
        MANDATORY-GROUPS {
            tmnx7710HwV3v0Group,
            tmnx7710SETSRefSrcHwV6v0Group,
            tmnx77x0CESMDAV6v0Group,
            tmnxAtmGroup,
            tmnxCardCamErrorV6v1Group,
            tmnxCardPchipV5v0Group,
            tmnxCardPchipV8v0Group,
            tmnxCardV3v0Group,
            tmnxCardV6v0NamedPoolPlcyGroup,
            tmnxCardV7v0Group,
            tmnxChassisHsmdaV6v0Group,
            tmnxChassisHwEventGroup,
            tmnxChassisHwEventNotifyGroup,
            tmnxChassisHwV6v1Group,
            tmnxChassisHwV9v0Group,
            tmnxChassisMixedModeIomV8v0Group,
            tmnxChassisNotificationV7v0Group,
            tmnxChassisNotificationV9v0Group,
            tmnxChassisUserModV7v0Group,
            tmnxChassisV5v0Group,
            tmnxChassisV6v1Group,
            tmnxChassisV7v0Group,
            tmnxChassisV8v0Group,
            tmnxFPMcPathMgmtV6v1Group,
            tmnxFPWredV7v0Group,
            tmnxIPsecIsaGrpV6v0Group,
            tmnxIPsecNotifV7v0Group,
            tmnxIPsecV7v0Group,
            tmnxMDACcagV6v1Group,
            tmnxMDAMcPathMgmtV6v0Group,
            tmnxMDAV6v1Group,
            tmnxMDAV9v0Group,
            tmnxMdaXplV5v0Group,
            tmnxSyncIfTimingNotifV8v0Group,
            tmnxSyncIfTimingNotifyV9v0Group,
            tmnxSyncIfTimingV8v0Group,
            tmnxSyncIfTimingV9v0Group,
            tmnxSyncV6v0Group
        }
    ::= { tmnxChassisCompliances 14 }

tmnxChassisV10v0Compliance       MODULE-COMPLIANCE
    STATUS      obsolete
    DESCRIPTION
        "The compliance statement for management of chassis features on SROS
         series systems in the TIMETRA-CHASSIS-MIB."
    MODULE
        MANDATORY-GROUPS {
            tmnx7710HwV3v0Group,
            tmnx7710SETSRefSrcHwV6v0Group,
            tmnx77x0CESMDAV6v0Group,
            tmnxAtmGroup,
            tmnxCardCamErrorV6v1Group,
            tmnxCardPchipV5v0Group,
            tmnxCardPchipV8v0Group,
            tmnxCardV3v0Group,
            tmnxCardV6v0NamedPoolPlcyGroup,
            tmnxCardV7v0Group,
            tmnxChassisHwEventGroup,
            tmnxChassisHwEventNotifyGroup,
            tmnxChassisHwV6v1Group,
            tmnxChassisHwV9v0Group,
            tmnxChassisMixedModeIomV8v0Group,
            tmnxChassisNotificationV7v0Group,
            tmnxChassisNotificationV9v0Group,
            tmnxChassisUserModV7v0Group,
            tmnxChassisV5v0Group,
            tmnxChassisV6v1Group,
            tmnxChassisV7v0Group,
            tmnxChassisV8v0Group,
            tmnxChassisV10v0Group,
            tmnxFPMcPathMgmtV6v1Group,
            tmnxFPWredV7v0Group,
            tmnxIPsecIsaGrpV6v0Group,
            tmnxIPsecNotifV7v0Group,
            tmnxIPsecV7v0Group,
            tmnxMDACcagV6v1Group,
            tmnxMDAMcPathMgmtV6v0Group,
            tmnxMDAV6v1Group,
            tmnxMDAV9v0Group,
            tmnxMdaXplV5v0Group,
            tmnxSyncIfTimingNotifV8v0Group,
            tmnxSyncIfTimingNotifyV9v0Group,
            tmnxSyncIfTimingV8v0Group,
            tmnxSyncIfTimingV9v0Group,
            tmnxSyncV6v0Group,
            tmnxCardV10v0Group,
            tmnxIpsecV10v0Group,
            tmnxFPQGrpGroup,
            tmnxFPQGrpV10v0R4Group,
            tmnxMdaV10v0Group,
            tmnxChassisNotifyV10v0Group,
            tmnxMdaHsmdaPoolV10v0Group,
            tmnxChassisHwEventGroupV10v0,
            tmnxChassisHwEventNotifyGrpV10v0
        }
    ::= { tmnxChassisCompliances 15 }

tmnxChassisV11v0Compliance       MODULE-COMPLIANCE
    STATUS      obsolete
    DESCRIPTION
        "The compliance statement for management of chassis features on SROS
         series systems in the TIMETRA-CHASSIS-MIB release 11.0."
    MODULE
        MANDATORY-GROUPS {
            tmnx7710HwV3v0Group,
            tmnx7710SETSRefSrcHwV6v0Group,
            tmnx77x0CESMDAV6v0Group,
            tmnxAtmGroup,
            tmnxCardCamErrorV6v1Group,
            tmnxCardPchipV5v0Group,
            tmnxCardPchipV8v0Group,
            tmnxCardV10v0Group,
            tmnxCardV3v0Group,
            tmnxCardV6v0NamedPoolPlcyGroup,
            tmnxCardV7v0Group,
            tmnxChassisFanV11v0Group,
            tmnxChassisHwEventGroup,
            tmnxChassisHwEventNotifyGroup,
            tmnxChassisHwV11v0Group,
            tmnxChassisHwV6v1Group,
            tmnxChassisHwV9v0Group,
            tmnxChassisMixedModeIomV8v0Group,
            tmnxChassisNotificationV7v0Group,
            tmnxChassisNotificationV9v0Group,
            tmnxChassisNotifyV10v0Group,
            tmnxChassisPowerMgmtGroup,
            tmnxChassisPowerMgmtNotifyGroup,
            tmnxChassisPowerV11v0Group,
            tmnxChassisQGrpOvrGroup,
            tmnxChassisSwitchFabNtfyV11v0Grp,
            tmnxChassisUserModV7v0Group,
            tmnxChassisV10v0Group,
            tmnxChassisV11v0Group,
            tmnxChassisV6v1Group,
            tmnxChassisV7v0Group,
            tmnxChassisV8v0Group,
            tmnxFPDCpuProtV11v0R0Group,
            tmnxFPDcpNotifyObjsV11v0Group,
            tmnxFPDcpNotifyV11v0Group,
            tmnxFPMcPathMgmtV6v1Group,
            tmnxFPQGrpGroup,
            tmnxFPQGrpV10v0R4Group,
            tmnxFPWredV7v0Group,
            tmnxIPsecIsaGrpV6v0Group,
            tmnxIPsecNotifV7v0Group,
            tmnxIPsecV7v0Group,
            tmnxIpsecV10v0Group,
            tmnxMDACcagV6v1Group,
            tmnxMDAMcPathMgmtV6v0Group,
            tmnxMDAV6v1Group,
            tmnxMDAV9v0Group,
            tmnxMdaHsmdaPoolV10v0Group,
            tmnxMdaV10v0Group,
            tmnxMdaXplV5v0Group,
            tmnxSyncIfTimingNotifV8v0Group,
            tmnxSyncIfTimingNotifyV9v0Group,
            tmnxSyncIfTimingV8v0Group,
            tmnxSyncIfTimingV9v0Group,
            tmnxSyncV6v0Group,
            tmnxFPPoolSizingV11v0Group,
            tmnxCpmCardCmplxMemErrV9v0Group,
            tmnxCardCmplQChipMemErrV9v0Group,
            tmnxCardCmplChipIfErrV9v0Group,
            tmnxChassisSmartPeqV11v0Group,
            tmnxChassisSmartPeqNtfyV11v0Grp,
            tmnxChassisHwEventGroupV10v0,
            tmnxChassisHwEventNotifyGrpV10v0,
            tmnxCpmCardRebootHoldV11v0Group
        }
    ::= { tmnxChassisCompliances 16 }

tmnxChassisV12v0Compliance       MODULE-COMPLIANCE
    STATUS      obsolete
    DESCRIPTION
        "The compliance statement for management of chassis features on SROS
         series systems in the TIMETRA-CHASSIS-MIB release 12.0."
    MODULE
        MANDATORY-GROUPS {
            tmnx7710HwV3v0Group,
            tmnx7710SETSRefSrcHwV6v0Group,
            tmnx77x0CESMDAV6v0Group,
            tmnxAtmGroup,
            tmnxCardCamErrorV6v1Group,
            tmnxCardPchipV5v0Group,
            tmnxCardPchipV8v0Group,
            tmnxCardV10v0Group,
            tmnxCardV3v0Group,
            tmnxCardV6v0NamedPoolPlcyGroup,
            tmnxCardV7v0Group,
            tmnxChassisFabricV11v0Group,
            tmnxChassisFanV11v0Group,
            tmnxChassisHwEventGroup,
            tmnxChassisHwEventNotifyGroup,
            tmnxChassisHwV11v0Group,
            tmnxChassisHwV6v1Group,
            tmnxChassisHwV9v0Group,
            tmnxChassisMixedModeIomV8v0Group,
            tmnxChassisNotificationV7v0Group,
            tmnxChassisNotificationV9v0Group,
            tmnxChassisNotifyObjsV12v0Group,
            tmnxChassisNotifyV10v0Group,
            tmnxChassisNotifV12v0Group,
            tmnxChassisPowerMgmtGroup,
            tmnxChassisPowerMgmtNotifyGroup,
            tmnxChassisPowerV11v0Group,
            tmnxChassisPowerV12v0Group,
            tmnxChassisPowerNotifV12v0Group,
            tmnxChassisQGrpOvrGroup,
            tmnxChassisSwitchFabNtfyV11v0Grp,
            tmnxChassisUserModV7v0Group,
            tmnxChassisV10v0Group,
            tmnxChassisV11v0Group,
            tmnxChassisV6v1Group,
            tmnxChassisV7v0Group,
            tmnxChassisV8v0Group,
            tmnxCpmCardRebootHoldV11v0Group,
            tmnxFPDCpuProtV11v0R0Group,
            tmnxFPDcpNotifyObjsV11v0Group,
            tmnxFPDcpNotifyV11v0Group,
            tmnxFPMcPathMgmtV6v1Group,
            tmnxFPQGrpGroup,
            tmnxFPQGrpV10v0R4Group,
            tmnxFPWredV7v0Group,
            tmnxIPsecIsaGrpV6v0Group,
            tmnxIPsecNotifV7v0Group,
            tmnxIPsecV7v0Group,
            tmnxIpsecV10v0Group,
            tmnxMDACcagV6v1Group,
            tmnxMDAMcPathMgmtV6v0Group,
            tmnxMDAV6v1Group,
            tmnxMDAV9v0Group,
            tmnxMdaHsmdaPoolV10v0Group,
            tmnxMdaV10v0Group,
            tmnxMdaXplV5v0Group,
            tmnxSyncIfTimingNotifV8v0Group,
            tmnxSyncIfTimingNotifyV9v0Group,
            tmnxSyncIfTimingV8v0Group,
            tmnxSyncIfTimingV9v0Group,
            tmnxSyncV6v0Group,
            tmnxPhysChassisGroup,
            tmnxFPPoolSizingV11v0Group,
            tmnxCpmCardCmplxMemErrV9v0Group,
            tmnxChassisResourceV12v0Group,
            tmnxFPBufAllocV12v0Group,
            tmnxCardCmplQChipMemErrV9v0Group,
            tmnxCardCmplChipIfErrV9v0Group,
            tmnxFPPlcyAcctV12v0Group,
            tmnxChassisPowerSupplyV9v0Grp,
            tmnxChassisSmartPeqV11v0Group,
            tmnxChassisSmartPeqNtfyV11v0Grp,
            tmnxChassPANotifyObjsV12v0Grp,
            tmnxChassisPlcyAcctNtfyV12v0Grp,
            tmnxChassisV12v0Group,
            tmnxIomResrcNotifyObjsV12v0Grp,
            tmnxIomResrcNotifyV12v0Group,
            tmnxChassisHwEventGroupV10v0,
            tmnxChassisHwEventNotifyGrpV10v0,
            tmnxCardResetOnRecoverErGrp,
            tmnxMDAResetOnRecoverErGrp,
            tmnxCpmMemSizeNotifGroupV12v0,
            tmnxCpmPChipFcsObjGroupV12v0
        }
    ::= { tmnxChassisCompliances 17 }

tmnxChassisV13v0Compliance       MODULE-COMPLIANCE
    STATUS      obsolete
    DESCRIPTION
        "The compliance statement for management of chassis features on SROS
         series systems in the TIMETRA-CHASSIS-MIB release 13.0."
    MODULE
        MANDATORY-GROUPS {
            tmnx7710HwV3v0Group,
            tmnx7710SETSRefSrcHwV6v0Group,
            tmnx77x0CESMDAV6v0Group,
            tmnxAtmGroup,
            tmnxCardCamErrorV6v1Group,
            tmnxCardPchipV5v0Group,
            tmnxCardPchipV8v0Group,
            tmnxCardV10v0Group,
            tmnxCardV3v0Group,
            tmnxCardV6v0NamedPoolPlcyGroup,
            tmnxCardV7v0Group,
            tmnxChassisFabricV11v0Group,
            tmnxChassisFanV11v0Group,
            tmnxChassisHwEventGroup,
            tmnxChassisHwEventNotifyGroup,
            tmnxChassisHwV11v0Group,
            tmnxChassisHwV6v1Group,
            tmnxChassisHwV9v0Group,
            tmnxChassisMixedModeIomV8v0Group,
            tmnxChassisNotificationV7v0Group,
            tmnxChassisNotificationV9v0Group,
            tmnxChassisNotifyObjsV12v0Group,
            tmnxChassisNotifyV10v0Group,
            tmnxChassisNotifV12v0Group,
            tmnxChassisPowerMgmtGroup,
            tmnxChassisPowerMgmtNotifyGroup,
            tmnxChassisPowerV11v0Group,
            tmnxChassisPowerV12v0Group,
            tmnxChassisPowerNotifV12v0Group,
            tmnxChassisQGrpOvrGroup,
            tmnxChassisSwitchFabNtfyV11v0Grp,
            tmnxChassisUserModV7v0Group,
            tmnxChassisV10v0Group,
            tmnxChassisV11v0Group,
            tmnxChassisV13v0Group,
            tmnxChassisV6v1Group,
            tmnxChassisV7v0Group,
            tmnxChassisV8v0Group,
            tmnxCpmCardV13v0Group,
            tmnxCpmCardRebootHoldV11v0Group,
            tmnxFPDCpuProtV11v0R0Group,
            tmnxFPDcpNotifyObjsV11v0Group,
            tmnxFPDcpNotifyV11v0Group,
            tmnxFPMcPathMgmtV6v1Group,
            tmnxFPQGrpGroup,
            tmnxFPQGrpV10v0R4Group,
            tmnxFPWredV7v0Group,
            tmnxIPsecIsaGrpV6v0Group,
            tmnxIPsecNotifV7v0Group,
            tmnxIPsecV7v0Group,
            tmnxIpsecV10v0Group,
            tmnxMDACcagV6v1Group,
            tmnxMDAMcPathMgmtV6v0Group,
            tmnxMDAV6v1Group,
            tmnxMDAV9v0Group,
            tmnxMdaHsmdaPoolV10v0Group,
            tmnxMdaV10v0Group,
            tmnxMdaXplV5v0Group,
            tmnxSyncIfTimingNotifV8v0Group,
            tmnxSyncIfTimingNotifyV9v0Group,
            tmnxSyncIfTimingV8v0Group,
            tmnxSyncIfTimingV9v0Group,
            tmnxSyncV6v0Group,
            tmnxPhysChassisGroup,
            tmnxFPPoolSizingV11v0Group,
            tmnxCpmCardCmplxMemErrV9v0Group,
            tmnxFPBufAllocV12v0Group,
            tmnxCardCmplQChipMemErrV9v0Group,
            tmnxCardCmplChipIfErrV9v0Group,
            tmnxFPPlcyAcctV12v0Group,
            tmnxChassisPowerSupplyV9v0Grp,
            tmnxChassisSmartPeqV11v0Group,
            tmnxChassisSmartPeqNtfyV11v0Grp,
            tmnxChassPANotifyObjsV12v0Grp,
            tmnxChassisPlcyAcctNtfyV12v0Grp,
            tmnxChassisV12v0Group,
            tmnxIomResrcNotifyObjsV12v0Grp,
            tmnxIomResrcNotifyV12v0Group,
            tmnxChassisHwEventGroupV10v0,
            tmnxChassisHwEventNotifyGrpV10v0,
            tmnxChassisResourceV13v0Group,
            tmnxCardVirtualSchAdjV13v0Group,
            tmnxPhysChassisV13v0Group,
            tmnxChassisMgmtEthRedNtfV13v0Grp,
            tmnxChassisMgmtEthRedV13v0Grp,
            tmnxChassisPowerMgmtGroupV13v0,
            tmnxChassisNotifV13v0Group,
            tmnxChassisNotifyObjsV13v0Grp,
            tmnxChassisFpResourceV13v0Group,
            tmnxFPV13v0Group,
            tmnxCardResetOnRecoverErGrp,
            tmnxMDAResetOnRecoverErGrp,
            tmnxCpmMemSizeNotifGroupV12v0,
            tmnxCpmPChipFcsObjGroupV12v0
        }
    ::= { tmnxChassisCompliances 18 }

tmnxChassisV14v0Compliance       MODULE-COMPLIANCE
    STATUS      obsolete
    DESCRIPTION
        "The compliance statement for management of chassis features on SROS
         series systems in the TIMETRA-CHASSIS-MIB release 14.0."
    MODULE
        MANDATORY-GROUPS {
            tmnxChassisResourceV14v0Group,
            tmnxCpmFlashV14v0Group,
            tmnxPhysChassisGroupV14v0,
            tmnxPhysChassisNotifGroupV14v0,
            tmnxSyncIfTimingV14v0Group,
            tFPFwdEngStatsGroup,
            tmnxIsaMemWMarkNotifGroupV14v0,
            tmnxCpmMemSizeNotifGroupV12v0,
            tmnxIsaGrpIsaScaleModeGroupV14v0,
            tmnxCardVirtualGroupV14v0
        }
    ::= { tmnxChassisCompliances 19 }

tmnxChassisV15v0Compliance       MODULE-COMPLIANCE
    STATUS      current
    DESCRIPTION
        "The compliance statement for management of chassis features on SROS
         series systems in the TIMETRA-CHASSIS-MIB release 15.0."
    MODULE
        MANDATORY-GROUPS {
            tmnx7710HwV3v0Group,
            tmnx7710SETSRefSrcHwV6v0Group,
            tmnx77x0CESMDAV6v0Group,
            tmnxAtmGroup,
            tmnxCardCamErrorV6v1Group,
            tmnxCardPchipV5v0Group,
            tmnxCardPchipV8v0Group,
            tmnxCardV10v0Group,
            tmnxCardV3v0Group,
            tmnxCardV6v0NamedPoolPlcyGroup,
            tmnxCardV7v0Group,
            tmnxChassisFabricV11v0Group,
            tmnxChassisFanV11v0Group,
            tmnxChassisHwEventGroup,
            tmnxChassisHwEventNotifyGroup,
            tmnxChassisHwV11v0Group,
            tmnxChassisHwV6v1Group,
            tmnxChassisHwV9v0Group,
            tmnxChassisMixedModeIomV8v0Group,
            tmnxChassisNotificationV7v0Group,
            tmnxChassisNotificationV9v0Group,
            tmnxChassisNotifyObjsV12v0Group,
            tmnxChassisNotifyV10v0Group,
            tmnxChassisNotifV12v0Group,
            tmnxChassisPowerMgmtGroup,
            tmnxChassisPowerMgmtNotifyGroup,
            tmnxChassisPowerV11v0Group,
            tmnxChassisPowerV12v0Group,
            tmnxChassisQGrpOvrGroup,
            tmnxChassisSwitchFabNtfyV11v0Grp,
            tmnxChassisUserModV7v0Group,
            tmnxChassisV10v0Group,
            tmnxChassisV11v0Group,
            tmnxChassisV13v0Group,
            tmnxChassisV6v1Group,
            tmnxChassisV7v0Group,
            tmnxChassisV8v0Group,
            tmnxCpmCardV13v0Group,
            tmnxCpmCardRebootHoldV11v0Group,
            tmnxFPDCpuProtV11v0R0Group,
            tmnxFPDcpNotifyObjsV11v0Group,
            tmnxFPDcpNotifyV11v0Group,
            tmnxFPMcPathMgmtV6v1Group,
            tmnxFPMcPathMgmtV15v0Group,
            tmnxFPQGrpGroup,
            tmnxFPQGrpV10v0R4Group,
            tmnxFPWredV7v0Group,
            tmnxIPsecIsaGrpV6v0Group,
            tmnxIPsecNotifV7v0Group,
            tmnxIPsecV7v0Group,
            tmnxIpsecV10v0Group,
            tmnxMDACcagV6v1Group,
            tmnxMdaHsmdaPoolV10v0Group,
            tmnxMDAV15v0Group,
            tmnxMdaXplV5v0Group,
            tmnxSyncIfTimingNotifV8v0Group,
            tmnxSyncIfTimingNotifyV9v0Group,
            tmnxSyncIfTimingV8v0Group,
            tmnxSyncIfTimingV9v0Group,
            tmnxSyncV6v0Group,
            tmnxPhysChassisGroup,
            tmnxFPPoolSizingV11v0Group,
            tmnxCpmCardCmplxMemErrV9v0Group,
            tmnxFPBufAllocV12v0Group,
            tmnxCardCmplQChipMemErrV9v0Group,
            tmnxCardCmplChipIfErrV9v0Group,
            tmnxFPPlcyAcctV12v0Group,
            tmnxChassisPowerSupplyV9v0Grp,
            tmnxChassisSmartPeqV11v0Group,
            tmnxChassPANotifyObjsV12v0Grp,
            tmnxChassisPlcyAcctNtfyV12v0Grp,
            tmnxChassisV12v0Group,
            tmnxIomResrcNotifyObjsV12v0Grp,
            tmnxIomResrcNotifyV12v0Group,
            tmnxChassisHwEventGroupV10v0,
            tmnxChassisHwEventNotifyGrpV10v0,
            tmnxCardVirtualSchAdjV13v0Group,
            tmnxPhysChassisV13v0Group,
            tmnxChassisMgmtEthRedNtfV13v0Grp,
            tmnxChassisMgmtEthRedV13v0Grp,
            tmnxChassisPowerMgmtGroupV13v0,
            tmnxChassisNotifV13v0Group,
            tmnxChassisNotifyObjsV13v0Grp,
            tmnxChassisFpResourceV13v0Group,
            tmnxFPV13v0Group,
            tmnxCardResetOnRecoverErGrp,
            tmnxMDAResetOnRecoverErGrp,
            tmnxCpmMemSizeNotifGroupV12v0,
            tmnxCpmPChipFcsObjGroupV12v0,
            tmnxChassisResourceV14v0Group,
            tmnxCpmFlashV14v0Group,
            tmnxPhysChassisGroupV14v0,
            tmnxPhysChassisNotifGroupV14v0,
            tmnxSyncIfTimingV14v0Group,
            tFPFwdEngStatsGroup,
            tmnxIsaMemWMarkNotifGroupV14v0,
            tmnxCpmMemSizeNotifGroupV12v0,
            tmnxIsaGrpIsaScaleModeGroupV14v0,
            tmnxCardVirtualGroupV14v0,
            tmnxChassisFanV15v0Group,
            tmnxCardFPEgrHsGroup,
            tmnxPhysChassisGroupV15v0,
            tmnxPhysChassisNotifGroupV15v0,
            tmnxIcmpMtuExceededStatGroup,
            tmnxChassisGroupV15v0,
            tmnxCardResMacFdbUsgNotifGroup,
            tmnxMacScaleNotifyObjsV15v0Grp,
            tmnxChassisResourceV15v0Group,
            tmnxCardFPResIngV15v0QGroup,
            tmnxCardFPResEgrV15v0QGroup,
            tmnxMinFpGenerationGroupV15v0
        }
    ::= { tmnxChassisCompliances 20 }

tmnxChassisGroups                OBJECT IDENTIFIER ::= { tmnxChassisConformance 2 }

tmnxChassisNotifyObjsGroup       OBJECT-GROUP
    OBJECTS     {
        tmnxEqNotificationRow,
        tmnxEqTypeNotificationRow,
        tmnxChassisNotifyChassisId,
        tmnxChassisNotifyHwIndex,
        tmnxRedSecondaryCPMStatus,
        tmnxChassisNotifyOID,
        tmnxSyncIfTimingNotifyAlarm,
        tmnxChassisNotifyMismatchedVer,
        tmnxChassisNotifySoftwareLocation,
        tmnxChassisNotifyCardFailureReason
    }
    STATUS      current
    DESCRIPTION
        "The group of objects supporting chassis hardware notifications on
         Nokia SROS series systems."
    ::= { tmnxChassisGroups 4 }

tmnxChassisNotifyObsoleteGroup   NOTIFICATION-GROUP
    NOTIFICATIONS {
        tmnxHwConfigChange,
        tmnxEqCpuFailure,
        tmnxEqMemoryFailure,
        tmnxEqBackdoorBusFailure,
        tmnxPeSoftwareError,
        tmnxPeSoftwareAbnormalHalt,
        tmnxPeOutOfMemory,
        tmnxPeConfigurationError,
        tmnxPeStorageProblem,
        tmnxPeCpuCyclesExceeded,
        tmnxRedSecondaryCPMStatusChange,
        tmnxRedRestoreSuccess,
        tmnxRedRestoreFail
    }
    STATUS      current
    DESCRIPTION
        "The group of notifications supporting the management of chassis
         hardware made obsolete for revision 2.1 on Nokia SROS series systems."
    ::= { tmnxChassisGroups 7 }

tmnxChassisV3v0Group             OBJECT-GROUP
    OBJECTS     {
        tmnxChassisTotalNumber,
        tmnxChassisLastChange,
        tmnxChassisRowStatus,
        tmnxChassisName,
        tmnxChassisType,
        tmnxChassisLocation,
        tmnxChassisCoordinates,
        tmnxChassisNumSlots,
        tmnxChassisNumPorts,
        tmnxChassisNumPwrSupplies,
        tmnxChassisNumFanTrays,
        tmnxChassisNumFans,
        tmnxChassisCriticalLEDState,
        tmnxChassisMajorLEDState,
        tmnxChassisMinorLEDState,
        tmnxChassisBaseMacAddress,
        tmnxChassisCLLICode,
        tmnxChassisReboot,
        tmnxChassisUpgrade,
        tmnxChassisAdminMode,
        tmnxChassisOperMode,
        tmnxChassisModeForce,
        tmnxChassisUpdateWaitTime,
        tmnxChassisUpdateTimeLeft,
        tmnxChassisFanOperStatus,
        tmnxChassisFanSpeed,
        tmnxChassisPowerSupplyACStatus,
        tmnxChassisPowerSupplyDCStatus,
        tmnxChassisPowerSupplyTempStatus,
        tmnxChassisPowerSupplyTempThreshold,
        tmnxChassisPowerSupply1Status,
        tmnxChassisPowerSupply2Status,
        tmnxChassisPowerSupplyAssignedType,
        tmnxChassisTypeName,
        tmnxChassisTypeDescription,
        tmnxChassisTypeStatus,
        tmnxHwLastChange,
        tmnxHwID,
        tmnxHwMfgString,
        tmnxHwMfgBoardNumber,
        tmnxHwSerialNumber,
        tmnxHwManufactureDate,
        tmnxHwClass,
        tmnxHwName,
        tmnxHwAlias,
        tmnxHwAssetID,
        tmnxHwCLEI,
        tmnxHwIsFRU,
        tmnxHwContainedIn,
        tmnxHwParentRelPos,
        tmnxHwAdminState,
        tmnxHwOperState,
        tmnxHwTempSensor,
        tmnxHwTemperature,
        tmnxHwTempThreshold,
        tmnxHwBootCodeVersion,
        tmnxHwSoftwareCodeVersion,
        tmnxHwSwLastBoot,
        tmnxHwAlarmState,
        tmnxHwLastAlarmEvent,
        tmnxHwClearAlarms,
        tmnxHwSwImageSource,
        tmnxHwMfgDeviations,
        tmnxHwBaseMacAddress,
        tmnxHwFailureReason,
        tmnxHwContainedIndex
    }
    STATUS      obsolete
    DESCRIPTION
        "The group of objects supporting management of chassis hardware
         capabilities on release 3.0 of  Nokia SROS series systems."
    ::= { tmnxChassisGroups 9 }

tmnxMDAV3v0Group                 OBJECT-GROUP
    OBJECTS     {
        tmnxMDASupportedTypes,
        tmnxMDAAssignedType,
        tmnxMDAEquippedType,
        tmnxMDAHwIndex,
        tmnxMDAMaxPorts,
        tmnxMDAEquippedPorts,
        tmnxMDATxTimingSelected,
        tmnxMDASyncIfTimingStatus,
        tmnxMDANetworkIngQueues,
        tmnxMDACapabilities,
        tmnxMDAMinChannelization,
        tmnxMDAMaxChannelization,
        tmnxMDAMaxChannels,
        tmnxMDAChannelsInUse,
        tmnxMDACcagId,
        tmnxMdaTypeName,
        tmnxMdaTypeDescription,
        tmnxMdaTypeStatus,
        tmnxCcagRowStatus,
        tmnxCcagDescription,
        tmnxCcagAdminStatus,
        tmnxCcagOperStatus,
        tmnxCcagCcaRate,
        tmnxCcagLastChanged,
        tmnxCcagAccessAdaptQos,
        tmnxCcagPathLastChanged,
        tmnxCcagPathRate,
        tmnxCcagPathRateOption,
        tmnxCcagPathWeight,
        tmnxCcagPathCcLastChanged,
        tmnxCcagPathCcEgrPoolResvCbs,
        tmnxCcagPathCcEgrPoolSlpPlcy,
        tmnxCcagPathCcIngPoolResvCbs,
        tmnxCcagPathCcIngPoolSlpPlcy,
        tmnxCcagPathCcAcctPolicyId,
        tmnxCcagPathCcCollectStats,
        tmnxCcagPathCcQueuePlcy,
        tmnxCcagPathCcMac,
        tmnxCcagPathCcMtu,
        tmnxCcagPathCcHwMac,
        tmnxCcagPathCcUserAssignedMac
    }
    STATUS      obsolete
    DESCRIPTION
        "The group of objects supporting management of MDAs on Nokia SROS
         series systems."
    ::= { tmnxChassisGroups 10 }

tmnxChassisObsoleteGroup         OBJECT-GROUP
    OBJECTS     {
        tmnxHwSwState,
        tmnxCardAllowedTypes,
        tmnxCpmCardAllowedTypes,
        tmnxMDAAllowedTypes
    }
    STATUS      current
    DESCRIPTION
        "The group of objects supporting the allowed types of CPM cards, IOM
         cards and MDA made obsolete for revision 3.0 on Nokia SROS series
         systems."
    ::= { tmnxChassisGroups 11 }

tmnxCardV3v0Group                OBJECT-GROUP
    OBJECTS     {
        tmnxCardLastChange,
        tmnxCardTypeName,
        tmnxCardTypeDescription,
        tmnxCardTypeStatus,
        tmnxCardSupportedTypes,
        tmnxCardAssignedType,
        tmnxCardEquippedType,
        tmnxCardHwIndex,
        tmnxCardClockSource,
        tmnxCardNumMdaSlots,
        tmnxCardNumMdas,
        tmnxCardReboot,
        tmnxCardMemorySize,
        tmnxCpmCardLastChange,
        tmnxCpmCardSupportedTypes,
        tmnxCpmCardAssignedType,
        tmnxCpmCardEquippedType,
        tmnxCpmCardHwIndex,
        tmnxCpmCardBootOptionVersion,
        tmnxCpmCardBootOptionLastModified,
        tmnxCpmCardConfigBootedVersion,
        tmnxCpmCardIndexBootedVersion,
        tmnxCpmCardConfigLastModified,
        tmnxCpmCardConfigLastSaved,
        tmnxCpmCardRedundant,
        tmnxCpmCardClockSource,
        tmnxCpmCardNumCpus,
        tmnxCpmCardCpuType,
        tmnxCpmCardMemorySize,
        tmnxCpmCardSwitchToRedundantCard,
        tmnxCpmCardReboot,
        tmnxCpmCardRereadBootOptions,
        tmnxCpmCardConfigFileLastBooted,
        tmnxCpmCardConfigFileLastSaved,
        tmnxCpmCardConfigFileLastBootedHeader,
        tmnxCpmCardIndexFileLastBootedHeader,
        tmnxCpmCardBootOptionSource,
        tmnxCpmCardConfigSource,
        tmnxCpmCardBootOptionLastSaved,
        tmnxFabricLastChange,
        tmnxFabricAssignedType,
        tmnxFabricEquippedType,
        tmnxFabricHwIndex,
        tmnxCpmFlashOperStatus,
        tmnxCpmFlashSerialNumber,
        tmnxCpmFlashFirmwareRevision,
        tmnxCpmFlashModelNumber,
        tmnxCpmFlashCapacity,
        tmnxCpmFlashUsed,
        tmnxCpmFlashHwIndex,
        tmnxSyncIfTimingRevert,
        tmnxSyncIfTimingRefOrder1,
        tmnxSyncIfTimingRefOrder2,
        tmnxSyncIfTimingRef1SrcPort,
        tmnxSyncIfTimingRef1AdminStatus,
        tmnxSyncIfTimingRef1InUse,
        tmnxSyncIfTimingRef1Qualified,
        tmnxSyncIfTimingRef1Alarm,
        tmnxSyncIfTimingRef2SrcPort,
        tmnxSyncIfTimingRef2AdminStatus,
        tmnxSyncIfTimingRef2InUse,
        tmnxSyncIfTimingRef2Qualified,
        tmnxSyncIfTimingRef2Alarm,
        tmnxSyncIfTimingFreqOffset,
        tmnxSyncIfTimingStatus,
        tmnxSyncIfTimingRefOrder3,
        tmnxSyncIfTimingBITSIfType,
        tmnxSyncIfTimingBITSAdminStatus,
        tmnxSyncIfTimingBITSInUse,
        tmnxSyncIfTimingBITSQualified,
        tmnxSyncIfTimingBITSAlarm,
        tSyncIfTimingAdmRevert,
        tSyncIfTimingAdmRefOrder1,
        tSyncIfTimingAdmRefOrder2,
        tSyncIfTimingAdmRef1SrcPort,
        tSyncIfTimingAdmRef1AdminStatus,
        tSyncIfTimingAdmRef2SrcPort,
        tSyncIfTimingAdmRef2AdminStatus,
        tSyncIfTimingAdmChanged,
        tSyncIfTimingAdmRefOrder3,
        tSyncIfTimingAdmBITSIfType,
        tSyncIfTimingAdmBITSAdminStatus,
        tmnxChassisAdminOwner,
        tmnxChassisAdminControlApply
    }
    STATUS      current
    DESCRIPTION
        "The group of objects supporting management of hardware cards on Nokia
         SROS series systems."
    ::= { tmnxChassisGroups 12 }

tmnxMDAV4v0Group                 OBJECT-GROUP
    OBJECTS     {
        tmnxMDASupportedTypes,
        tmnxMDAAssignedType,
        tmnxMDAEquippedType,
        tmnxMDAHwIndex,
        tmnxMDAMaxPorts,
        tmnxMDAEquippedPorts,
        tmnxMDATxTimingSelected,
        tmnxMDASyncIfTimingStatus,
        tmnxMDANetworkIngQueues,
        tmnxMDACapabilities,
        tmnxMDAMinChannelization,
        tmnxMDAMaxChannelization,
        tmnxMDAMaxChannels,
        tmnxMDAChannelsInUse,
        tmnxMDACcagId,
        tmnxMdaTypeName,
        tmnxMdaTypeDescription,
        tmnxMdaTypeStatus,
        tmnxMDAReboot,
        tmnxCcagRowStatus,
        tmnxCcagDescription,
        tmnxCcagAdminStatus,
        tmnxCcagOperStatus,
        tmnxCcagCcaRate,
        tmnxCcagLastChanged,
        tmnxCcagAccessAdaptQos,
        tmnxCcagPathLastChanged,
        tmnxCcagPathRate,
        tmnxCcagPathRateOption,
        tmnxCcagPathWeight,
        tmnxCcagPathCcLastChanged,
        tmnxCcagPathCcEgrPoolResvCbs,
        tmnxCcagPathCcEgrPoolSlpPlcy,
        tmnxCcagPathCcIngPoolResvCbs,
        tmnxCcagPathCcIngPoolSlpPlcy,
        tmnxCcagPathCcAcctPolicyId,
        tmnxCcagPathCcCollectStats,
        tmnxCcagPathCcQueuePlcy,
        tmnxCcagPathCcMac,
        tmnxCcagPathCcMtu,
        tmnxCcagPathCcHwMac,
        tmnxCcagPathCcUserAssignedMac,
        tmnxMDAHiBwMcastSource,
        tmnxMDAHiBwMcastAlarm,
        tmnxMDAHiBwMcastTapCount,
        tmnxMDAHiBwMcastGroup
    }
    STATUS      obsolete
    DESCRIPTION
        "The group of objects supporting management of MDAs for release 4.0 on
         Nokia SROS series systems."
    ::= { tmnxChassisGroups 13 }

tmnxChassisNotificationV4v0Group NOTIFICATION-GROUP
    NOTIFICATIONS {
        tmnxEnvTempTooHigh,
        tmnxEqPowerSupplyFailure,
        tmnxEqPowerSupplyInserted,
        tmnxEqPowerSupplyRemoved,
        tmnxEqFanFailure,
        tmnxEqCardFailure,
        tmnxEqCardInserted,
        tmnxEqCardRemoved,
        tmnxEqWrongCard,
        tmnxPeSoftwareVersionMismatch,
        tmnxRedPrimaryCPMFail,
        tmnxChassisNotificationClear,
        tmnxEqSyncIfTimingHoldover,
        tmnxEqSyncIfTimingHoldoverClear,
        tmnxEqSyncIfTimingRef1Alarm,
        tmnxEqSyncIfTimingRef1AlarmClear,
        tmnxEqSyncIfTimingRef2Alarm,
        tmnxEqSyncIfTimingRef2AlarmClear,
        tmnxEqFlashDataLoss,
        tmnxEqFlashDiskFull,
        tmnxPeSoftwareLoadFailed,
        tmnxPeBootloaderVersionMismatch,
        tmnxPeBootromVersionMismatch,
        tmnxPeFPGAVersionMismatch,
        tmnxEqSyncIfTimingBITSAlarm,
        tmnxEqSyncIfTimingBITSAlarmClear,
        tmnxEqCardFirmwareUpgraded,
        tmnxChassisUpgradeInProgress,
        tmnxChassisUpgradeComplete,
        tmnxChassisHiBwMcastAlarm,
        tmnxEqMdaCfgNotCompatible
    }
    STATUS      obsolete
    DESCRIPTION
        "The group of notifications supporting the management of chassis
         hardware for release 4.0 on Nokia SROS series systems."
    ::= { tmnxChassisGroups 14 }

tmnx7710HwV3v0Group              OBJECT-GROUP
    OBJECTS     {
        tmnxChassisOverTempState,
        tmnxCpmCardMasterSlaveRefState,
        tmnxCcmOperStatus,
        tmnxCcmHwIndex,
        tmnxCcmEquippedType,
        tmnxCcmTypeName,
        tmnxCcmTypeDescription,
        tmnxCcmTypeStatus,
        tmnxMcmSupportedTypes,
        tmnxMcmAssignedType,
        tmnxMcmEquippedType,
        tmnxMcmHwIndex,
        tmnxMcmTypeName,
        tmnxMcmTypeDescription,
        tmnxMcmTypeStatus,
        tmnxChassisPowerSupplyInputStatus,
        tmnxChassisPowerSupplyOutputStatus,
        tmnxMDAReboot
    }
    STATUS      current
    DESCRIPTION
        "The group of objects supporting management of hardware specific to the
         Nokia 7710 SR series systems."
    ::= { tmnxChassisGroups 15 }

tmnxChassisV5v0Group             OBJECT-GROUP
    OBJECTS     {
        tmnxChassisTotalNumber,
        tmnxChassisLastChange,
        tmnxChassisRowStatus,
        tmnxChassisName,
        tmnxChassisType,
        tmnxChassisLocation,
        tmnxChassisCoordinates,
        tmnxChassisNumSlots,
        tmnxChassisNumPorts,
        tmnxChassisNumPwrSupplies,
        tmnxChassisNumFanTrays,
        tmnxChassisNumFans,
        tmnxChassisCriticalLEDState,
        tmnxChassisMajorLEDState,
        tmnxChassisMinorLEDState,
        tmnxChassisBaseMacAddress,
        tmnxChassisCLLICode,
        tmnxChassisReboot,
        tmnxChassisUpgrade,
        tmnxChassisAdminMode,
        tmnxChassisOperMode,
        tmnxChassisModeForce,
        tmnxChassisUpdateTimeLeft,
        tmnxChassisFanOperStatus,
        tmnxChassisFanSpeed,
        tmnxChassisPowerSupplyACStatus,
        tmnxChassisPowerSupplyDCStatus,
        tmnxChassisPowerSupplyTempStatus,
        tmnxChassisPowerSupplyTempThreshold,
        tmnxChassisPowerSupply1Status,
        tmnxChassisPowerSupply2Status,
        tmnxChassisPowerSupplyAssignedType,
        tmnxChassisTypeName,
        tmnxChassisTypeDescription,
        tmnxChassisTypeStatus,
        tmnxHwLastChange,
        tmnxHwID,
        tmnxHwMfgString,
        tmnxHwMfgBoardNumber,
        tmnxHwSerialNumber,
        tmnxHwManufactureDate,
        tmnxHwClass,
        tmnxHwName,
        tmnxHwAlias,
        tmnxHwAssetID,
        tmnxHwCLEI,
        tmnxHwIsFRU,
        tmnxHwContainedIn,
        tmnxHwParentRelPos,
        tmnxHwAdminState,
        tmnxHwOperState,
        tmnxHwTempSensor,
        tmnxHwTemperature,
        tmnxHwTempThreshold,
        tmnxHwBootCodeVersion,
        tmnxHwSoftwareCodeVersion,
        tmnxHwSwLastBoot,
        tmnxHwAlarmState,
        tmnxHwLastAlarmEvent,
        tmnxHwClearAlarms,
        tmnxHwSwImageSource,
        tmnxHwMfgDeviations,
        tmnxHwBaseMacAddress,
        tmnxHwFailureReason,
        tmnxHwContainedIndex
    }
    STATUS      obsolete
    DESCRIPTION
        "The group of objects supporting management of chassis hardware
         capabilities on release 5.0 of Nokia SROS series systems."
    ::= { tmnxChassisGroups 16 }

tmnxChassisV5v0ObsoleteGroup     OBJECT-GROUP
    OBJECTS     {
        tmnxChassisUpdateWaitTime
    }
    STATUS      current
    DESCRIPTION
        "The group of obsolete objects for managing the chassis hardware
         capabilities on release 5.0 of Nokia SROS series systems."
    ::= { tmnxChassisGroups 17 }

tmnx77x0CESMDAV6v0Group          OBJECT-GROUP
    OBJECTS     {
        tmnxMDAClockMode,
        tmnxMDADiffTimestampFreq,
        tmnxMDAIngNamedPoolPolicy,
        tmnxMDAEgrNamedPoolPolicy
    }
    STATUS      current
    DESCRIPTION
        "The group of objects supporting management of CES MDAs for release 6.0
         on Nokia 77x0 SR series systems."
    ::= { tmnxChassisGroups 18 }

tmnxIPsecIsaGrpV6v0Group         OBJECT-GROUP
    OBJECTS     {
        tmnxIPsecIsaGrpTableLastChanged,
        tmnxIPsecIsaGrpRowStatus,
        tmnxIPsecIsaGrpLastChanged,
        tmnxIPsecIsaGrpDescription,
        tmnxIPsecIsaGrpAdminState,
        tmnxIPsecIsaGrpOperState,
        tmnxIPsecIsaGrpIsaChassis,
        tmnxIPsecIsaGrpPrimaryIsa,
        tmnxIPsecIsaGrpBackupIsa,
        tmnxIPsecIsaGrpActiveIsa
    }
    STATUS      current
    DESCRIPTION
        "The group of objects supporting management of IPsec MDAs for release
         6.0 on Nokia 7750 and 7710 SR series systems."
    ::= { tmnxChassisGroups 19 }

tmnxChassisNotificationV3v0Group NOTIFICATION-GROUP
    NOTIFICATIONS {
        tmnxEnvTempTooHigh,
        tmnxEqPowerSupplyFailure,
        tmnxEqPowerSupplyInserted,
        tmnxEqPowerSupplyRemoved,
        tmnxEqFanFailure,
        tmnxEqCardFailure,
        tmnxEqCardInserted,
        tmnxEqCardRemoved,
        tmnxEqWrongCard,
        tmnxPeSoftwareVersionMismatch,
        tmnxRedPrimaryCPMFail,
        tmnxChassisNotificationClear,
        tmnxEqSyncIfTimingHoldover,
        tmnxEqSyncIfTimingHoldoverClear,
        tmnxEqSyncIfTimingRef1Alarm,
        tmnxEqSyncIfTimingRef1AlarmClear,
        tmnxEqSyncIfTimingRef2Alarm,
        tmnxEqSyncIfTimingRef2AlarmClear,
        tmnxEqFlashDataLoss,
        tmnxEqFlashDiskFull,
        tmnxPeSoftwareLoadFailed,
        tmnxPeBootloaderVersionMismatch,
        tmnxPeBootromVersionMismatch,
        tmnxPeFPGAVersionMismatch,
        tmnxEqSyncIfTimingBITSAlarm,
        tmnxEqSyncIfTimingBITSAlarmClear,
        tmnxEqCardFirmwareUpgraded,
        tmnxEqMdaCfgNotCompatible
    }
    STATUS      obsolete
    DESCRIPTION
        "The group of notifications supporting the management of chassis
         hardware for release 3.0 on Nokia SROS series systems."
    ::= { tmnxChassisGroups 20 }

tmnxChassisNotificationV6v0Group NOTIFICATION-GROUP
    NOTIFICATIONS {
        tmnxEnvTempTooHigh,
        tmnxEqPowerSupplyFailure,
        tmnxEqPowerSupplyInserted,
        tmnxEqPowerSupplyRemoved,
        tmnxEqFanFailure,
        tmnxEqCardFailure,
        tmnxEqCardInserted,
        tmnxEqCardRemoved,
        tmnxEqWrongCard,
        tmnxPeSoftwareVersionMismatch,
        tmnxRedPrimaryCPMFail,
        tmnxChassisNotificationClear,
        tmnxEqSyncIfTimingHoldover,
        tmnxEqSyncIfTimingHoldoverClear,
        tmnxEqSyncIfTimingRef1Alarm,
        tmnxEqSyncIfTimingRef1AlarmClear,
        tmnxEqSyncIfTimingRef2Alarm,
        tmnxEqSyncIfTimingRef2AlarmClear,
        tmnxEqFlashDataLoss,
        tmnxEqFlashDiskFull,
        tmnxPeSoftwareLoadFailed,
        tmnxPeBootloaderVersionMismatch,
        tmnxPeBootromVersionMismatch,
        tmnxPeFPGAVersionMismatch,
        tmnxEqSyncIfTimingBITSAlarm,
        tmnxEqSyncIfTimingBITSAlarmClear,
        tmnxEqCardFirmwareUpgraded,
        tmnxChassisUpgradeInProgress,
        tmnxChassisUpgradeComplete,
        tmnxChassisHiBwMcastAlarm,
        tmnxEqMdaCfgNotCompatible,
        tmnxCpmCardSyncFileNotPresent,
        tmnxEqMdaXplError,
        tmnxEqCardPChipError,
        tmnxEqCardPChipMemoryEvent
    }
    STATUS      obsolete
    DESCRIPTION
        "The group of notifications supporting the management of chassis
         hardware for release 6.0 on Nokia SROS series systems."
    ::= { tmnxChassisGroups 21 }

tmnx7710SETSRefSrcHwV6v0Group    OBJECT-GROUP
    OBJECTS     {
        tmnxSyncIfTimingRef1SrcHw,
        tmnxSyncIfTimingRef1BITSIfType,
        tmnxSyncIfTimingRef2SrcHw,
        tmnxSyncIfTimingRef2BITSIfType,
        tSyncIfTimingAdmRef1SrcHw,
        tSyncIfTimingAdmRef1BITSIfType,
        tSyncIfTimingAdmRef2SrcHw,
        tSyncIfTimingAdmRef2BITSIfType
    }
    STATUS      current
    DESCRIPTION
        "The group of objects supporting management of 'Synchronous Equipment
         Timing' (SETS) when the references are of type 'Building Integrated
         Timing Supply' (BITS) for release 6.0 on Nokia 7710 SR series systems."
    ::= { tmnxChassisGroups 22 }

tmnxChassisHsmdaV6v0Group        OBJECT-GROUP
    OBJECTS     {
        tmnxMDAIngHsmdaSchedPolicy,
        tmnxHsmdaMdaSchOvrTblLastChangd,
        tmnxHsmdaMdaSchOvrRowStatus,
        tmnxHsmdaMdaSchOvrLastChanged,
        tmnxHsmdaMdaSchOvrMaxRate,
        tmnxHsmdaMdaSchOvrGrp1Rate,
        tmnxHsmdaMdaSchOvrGrp2Rate,
        tmnxHsmdaMdaSchOvrClass1Rate,
        tmnxHsmdaMdaSchOvrClass1WtInGrp,
        tmnxHsmdaMdaSchOvrClass2Rate,
        tmnxHsmdaMdaSchOvrClass2WtInGrp,
        tmnxHsmdaMdaSchOvrClass3Rate,
        tmnxHsmdaMdaSchOvrClass3WtInGrp,
        tmnxHsmdaMdaSchOvrClass4Rate,
        tmnxHsmdaMdaSchOvrClass4WtInGrp,
        tmnxHsmdaMdaSchOvrClass5Rate,
        tmnxHsmdaMdaSchOvrClass5WtInGrp,
        tmnxHsmdaMdaSchOvrClass6Rate,
        tmnxHsmdaMdaSchOvrClass6WtInGrp,
        tmnxHsmdaMdaSchOvrClass7Rate,
        tmnxHsmdaMdaSchOvrClass7WtInGrp,
        tmnxHsmdaMdaSchOvrClass8Rate,
        tmnxHsmdaMdaSchOvrClass8WtInGrp,
        tmnxMDAIngHsmdaPoolPolicy,
        tmnxMDAEgrHsmdaPoolPolicy
    }
    STATUS      obsolete
    DESCRIPTION
        "The group of objects supporting management of the 'Queueing MDA'
         (HSMDA) for release 6.0 on Nokia SROS series systems."
    ::= { tmnxChassisGroups 23 }

tmnxMDAMcPathMgmtV6v0Group       OBJECT-GROUP
    OBJECTS     {
        tmnxMDAMcPathMgmtBwPlcyName,
        tmnxMDAMcPathMgmtPriPathLimit,
        tmnxMDAMcPathMgmtSecPathLimit,
        tmnxMDAMcPathMgmtAncPathLimit,
        tmnxMDAMcPathMgmtAdminState,
        tmnxMDAMcPathMgmtPriInUseBw,
        tmnxMDAMcPathMgmtSecInUseBw,
        tmnxMDAMcPathMgmtAncInUseBw,
        tmnxMDAMcPathMgmtBlkHoleInUseBw
    }
    STATUS      obsolete
    DESCRIPTION
        "The group of objects supporting management of Multicast Path
         Management feature for release 6.0 on Nokia SROS series systems."
    ::= { tmnxChassisGroups 24 }

tmnxCardV6v0NamedPoolPlcyGroup   OBJECT-GROUP
    OBJECTS     {
        tmnxCardNamedPoolAdminMode,
        tmnxCardNamedPoolOperMode
    }
    STATUS      current
    DESCRIPTION
        "The group of objects supporting named buffer pools for release 6.0 on
         Nokia SROS series systems."
    ::= { tmnxChassisGroups 25 }

tmnxChassisNotifyObjsV6v0Group   OBJECT-GROUP
    OBJECTS     {
        tmnxChassisNotifyCardName,
        tmnxChassisNotifyCardSyncFile
    }
    STATUS      current
    DESCRIPTION
        "The group of objects added in 6.0 release to support chassis hardware
         notifications on Nokia SROS series systems."
    ::= { tmnxChassisGroups 26 }

tmnxChassisV6v1Group             OBJECT-GROUP
    OBJECTS     {
        tmnxChassisPowerSupplyPemType,
        tmnxCardSoftReset,
        tmnxCardLastBootupReason
    }
    STATUS      current
    DESCRIPTION
        "The group of objects added in 6.1 release on Nokia 7xx0 SR series
         systems."
    ::= { tmnxChassisGroups 27 }

tmnxFPMcPathMgmtV6v1Group        OBJECT-GROUP
    OBJECTS     {
        tmnxFPMcPathMgmtBwPlcyName,
        tmnxFPMcPathMgmtAdminState,
        tmnxFPLastChanged,
        tmnxFPHiBwMcastSource,
        tmnxFPHiBwMcastAlarm,
        tmnxFPHiBwMcastTapCount,
        tmnxFPHiBwMcastGroup,
        tmnxFPHiBwMcastDefaultPathsOnly
    }
    STATUS      current
    DESCRIPTION
        "The group of objects supporting management of Multicast Path
         Management feature for release 6.1 on Nokia SROS series systems."
    ::= { tmnxChassisGroups 28 }

tmnxMDAV6v1Group                 OBJECT-GROUP
    OBJECTS     {
        tmnxMDASupportedTypes,
        tmnxMDAAssignedType,
        tmnxMDAEquippedType,
        tmnxMDAHwIndex,
        tmnxMDAMaxPorts,
        tmnxMDAEquippedPorts,
        tmnxMDATxTimingSelected,
        tmnxMDASyncIfTimingStatus,
        tmnxMDANetworkIngQueues,
        tmnxMDACapabilities,
        tmnxMDAMinChannelization,
        tmnxMDAMaxChannelization,
        tmnxMDAMaxChannels,
        tmnxMDAChannelsInUse,
        tmnxMdaTypeName,
        tmnxMdaTypeDescription,
        tmnxMdaTypeStatus,
        tmnxMDAReboot,
        tmnxMDAHiBwMcastSource,
        tmnxMDAHiBwMcastAlarm,
        tmnxMDAHiBwMcastTapCount,
        tmnxMDAHiBwMcastGroup,
        tmnxMDASynchronousEthernet
    }
    STATUS      obsolete
    DESCRIPTION
        "The group of objects supporting management of MDAs for release 6.1 on
         Nokia SROS series systems."
    ::= { tmnxChassisGroups 29 }

tmnxMDACcagV6v1Group             OBJECT-GROUP
    OBJECTS     {
        tmnxMDACcagId,
        tmnxCcagRowStatus,
        tmnxCcagDescription,
        tmnxCcagAdminStatus,
        tmnxCcagOperStatus,
        tmnxCcagCcaRate,
        tmnxCcagLastChanged,
        tmnxCcagAccessAdaptQos,
        tmnxCcagPathLastChanged,
        tmnxCcagPathRate,
        tmnxCcagPathRateOption,
        tmnxCcagPathWeight,
        tmnxCcagPathCcLastChanged,
        tmnxCcagPathCcEgrPoolResvCbs,
        tmnxCcagPathCcEgrPoolSlpPlcy,
        tmnxCcagPathCcIngPoolResvCbs,
        tmnxCcagPathCcIngPoolSlpPlcy,
        tmnxCcagPathCcAcctPolicyId,
        tmnxCcagPathCcCollectStats,
        tmnxCcagPathCcQueuePlcy,
        tmnxCcagPathCcMac,
        tmnxCcagPathCcMtu,
        tmnxCcagPathCcHwMac,
        tmnxCcagPathCcUserAssignedMac
    }
    STATUS      current
    DESCRIPTION
        "The group of objects supporting management of MDA CCAG for release 6.1
         on Nokia SROS series systems."
    ::= { tmnxChassisGroups 30 }

tmnxMdaXplV5v0Group              OBJECT-GROUP
    OBJECTS     {
        tmnxMDAXplErrorTime,
        tmnxMDAXplFailedCount
    }
    STATUS      current
    DESCRIPTION
        "The group of objects added in 5.0 release to support MDA XPL error
         indications on Nokia SROS series systems."
    ::= { tmnxChassisGroups 31 }

tmnxChassisNotifyObjsV5v0Group   OBJECT-GROUP
    OBJECTS     {
        tmnxCardComplexNumber,
        tmnxCardFwdDirection
    }
    STATUS      current
    DESCRIPTION
        "The group of objects added in 5.0 release to support chassis hardware
         notifications on Nokia SROS series systems."
    ::= { tmnxChassisGroups 32 }

tmnxChassisNotificationV5v0Group NOTIFICATION-GROUP
    NOTIFICATIONS {
        tmnxEqMdaXplError,
        tmnxEqCardPChipError,
        tmnxEqCardPChipMemoryEvent
    }
    STATUS      obsolete
    DESCRIPTION
        "The group of notifications added in 5.0 release to support the
         hardware notifications on Nokia SROS series systems."
    ::= { tmnxChassisGroups 33 }

tmnxChassisNotificationV6v1Group NOTIFICATION-GROUP
    NOTIFICATIONS {
        tmnxEnvTempTooHigh,
        tmnxEqPowerSupplyFailure,
        tmnxEqPowerSupplyInserted,
        tmnxEqPowerSupplyRemoved,
        tmnxEqFanFailure,
        tmnxEqCardFailure,
        tmnxEqCardInserted,
        tmnxEqCardRemoved,
        tmnxEqWrongCard,
        tmnxPeSoftwareVersionMismatch,
        tmnxRedPrimaryCPMFail,
        tmnxChassisNotificationClear,
        tmnxEqSyncIfTimingHoldover,
        tmnxEqSyncIfTimingHoldoverClear,
        tmnxEqSyncIfTimingRef1Alarm,
        tmnxEqSyncIfTimingRef1AlarmClear,
        tmnxEqSyncIfTimingRef2Alarm,
        tmnxEqSyncIfTimingRef2AlarmClear,
        tmnxEqFlashDataLoss,
        tmnxEqFlashDiskFull,
        tmnxPeSoftwareLoadFailed,
        tmnxPeBootloaderVersionMismatch,
        tmnxPeBootromVersionMismatch,
        tmnxPeFPGAVersionMismatch,
        tmnxEqSyncIfTimingBITSAlarm,
        tmnxEqSyncIfTimingBITSAlarmClear,
        tmnxEqCardFirmwareUpgraded,
        tmnxChassisUpgradeInProgress,
        tmnxChassisUpgradeComplete,
        tmnxChassisHiBwMcastAlarm,
        tmnxEqMdaCfgNotCompatible,
        tmnxCpmCardSyncFileNotPresent,
        tmnxEqMdaXplError,
        tmnxEqCardPChipError,
        tmnxEqCardSoftResetAlarm,
        tmnxEqCardPChipMemoryEvent,
        tmnxEqCardPChipCamEvent
    }
    STATUS      obsolete
    DESCRIPTION
        "The group of notifications supporting the management of chassis
         hardware for release 6.0 on Nokia SROS series systems."
    ::= { tmnxChassisGroups 34 }

tmnxChassisNotifyObjsV6v1Group   OBJECT-GROUP
    OBJECTS     {
        tmnxCardSoftResetState
    }
    STATUS      current
    DESCRIPTION
        "The group of objects added in 6.1 release to support chassis hardware
         notifications on Nokia SROS series systems."
    ::= { tmnxChassisGroups 35 }

tmnxChassisNotificationV7v0Group NOTIFICATION-GROUP
    NOTIFICATIONS {
        tmnxEnvTempTooHigh,
        tmnxEqPowerSupplyInserted,
        tmnxEqPowerSupplyRemoved,
        tmnxEqCardFailure,
        tmnxEqCardInserted,
        tmnxEqCardRemoved,
        tmnxEqWrongCard,
        tmnxPeSoftwareVersionMismatch,
        tmnxRedPrimaryCPMFail,
        tmnxChassisNotificationClear,
        tmnxEqSyncIfTimingHoldover,
        tmnxEqSyncIfTimingHoldoverClear,
        tmnxEqSyncIfTimingRef1Alarm,
        tmnxEqSyncIfTimingRef1AlarmClear,
        tmnxEqSyncIfTimingRef2Alarm,
        tmnxEqSyncIfTimingRef2AlarmClear,
        tmnxEqFlashDataLoss,
        tmnxEqFlashDiskFull,
        tmnxPeSoftwareLoadFailed,
        tmnxPeBootloaderVersionMismatch,
        tmnxPeBootromVersionMismatch,
        tmnxPeFPGAVersionMismatch,
        tmnxEqSyncIfTimingBITSAlarm,
        tmnxEqSyncIfTimingBITSAlarmClear,
        tmnxEqCardFirmwareUpgraded,
        tmnxChassisUpgradeInProgress,
        tmnxChassisUpgradeComplete,
        tmnxChassisHiBwMcastAlarm,
        tmnxEqMdaCfgNotCompatible,
        tmnxCpmCardSyncFileNotPresent,
        tmnxEqMdaXplError,
        tmnxEqCardPChipError,
        tmnxEqCardSoftResetAlarm,
        tmnxEqMdaSyncENotCompatible,
        tmnxIPsecIsaGrpActiveIsaChgd,
        tmnxEqCardPChipMemoryEvent,
        tmnxIPsecIsaGrpUnableToSwitch,
        tmnxEqCardPChipCamEvent,
        tmnxEqHwEnhancedCapability
    }
    STATUS      current
    DESCRIPTION
        "The group of notifications supporting the management of chassis
         hardware for release 7.0 on Nokia SROS series systems."
    ::= { tmnxChassisGroups 36 }

tmnxChassisUserModV7v0Group      OBJECT-GROUP
    OBJECTS     {
        tmnxCpmCardConfigUserLastModified
    }
    STATUS      current
    DESCRIPTION
        "The group of objects added in 7.0 release on Nokia 7xx0 SR series
         systems to track user modifications."
    ::= { tmnxChassisGroups 37 }

tmnxCardPchipV5v0Group           OBJECT-GROUP
    OBJECTS     {
        tmnxCardCmplx1IngrFcsOccur,
        tmnxCardCmplx1IngrFcsOccurTime,
        tmnxCardCmplx1EgrFcsOccur,
        tmnxCardCmplx1EgrFcsOccurTime,
        tmnxCardCmplx2IngrFcsOccur,
        tmnxCardCmplx2IngrFcsOccurTime,
        tmnxCardCmplx2EgrFcsOccur,
        tmnxCardCmplx2EgrFcsOccurTime,
        tmnxCardCmplx1MemParityOccur,
        tmnxCardCmplx1MemParityOccurTime,
        tmnxCardCmplx2MemParityOccur,
        tmnxCardCmplx2MemParityOccurTime
    }
    STATUS      current
    DESCRIPTION
        "The group of objects added in 5.0 release to support IOM Card Pchip
         error indications on Nokia SROS series systems."
    ::= { tmnxChassisGroups 38 }

tmnxFPWredV7v0Group              OBJECT-GROUP
    OBJECTS     {
        tmnxFPWredBufAllocMin,
        tmnxFPWredBufAllocMax,
        tmnxFPWredResvCbsMin,
        tmnxFPWredResvCbsMax,
        tmnxFPWredSlopePolicy,
        tmnxFPWredAdminState
    }
    STATUS      current
    DESCRIPTION
        "The group of objects supporting management of WRED Queue Management
         feature for release 7.0 on Nokia SROS series systems."
    ::= { tmnxChassisGroups 39 }

tmnxChassisV7v0Group             OBJECT-GROUP
    OBJECTS     {
        tmnxChassisFanRevision
    }
    STATUS      current
    DESCRIPTION
        "The group of objects added in 7.0 release on Nokia 7x50 SR series
         systems to track Fan Tray revisions."
    ::= { tmnxChassisGroups 40 }

tmnxIPsecV7v0Group               OBJECT-GROUP
    OBJECTS     {
        tmnxIPsecIsaGrpTunnels,
        tmnxIPsecIsaGrpMaxTunnels
    }
    STATUS      current
    DESCRIPTION
        "The group of objects added in 7.0 release on Nokia 7x50 SR series
         systems related to IPsec feature."
    ::= { tmnxChassisGroups 41 }

tmnxIPsecNotifV7v0Group          NOTIFICATION-GROUP
    NOTIFICATIONS {
        tmnxIPsecIsaGrpTnlLowWMark,
        tmnxIPsecIsaGrpTnlHighWMark,
        tmnxIPsecIsaGrpTnlMax
    }
    STATUS      current
    DESCRIPTION
        "The group of objects added in 7.0 release to support IPsec
         notifications on Nokia SROS series systems."
    ::= { tmnxChassisGroups 42 }

tmnxSyncV6v0Group                OBJECT-GROUP
    OBJECTS     {
        tmnxSyncIfTimingRef1State,
        tmnxSyncIfTimingRef2State,
        tmnxSyncIfTimingBITSState
    }
    STATUS      current
    DESCRIPTION
        "The group of objects added in 6.0 release on Nokia 7xx0 SR series
         systems related to system timing."
    ::= { tmnxChassisGroups 43 }

tmnxSyncIfTimingV8v0Group        OBJECT-GROUP
    OBJECTS     {
        tmnxSyncIfTimingBITSOutAdmStatus,
        tmnxSyncIfTimingBITSOutLineLen,
        tmnxSyncIfTimingRef1CfgQltyLevel,
        tmnxSyncIfTimingRef1RxQltyLevel,
        tmnxSyncIfTimingRef2CfgQltyLevel,
        tmnxSyncIfTimingRef2RxQltyLevel,
        tmnxSyncIfTimingBITSCfgQltyLevel,
        tmnxSyncIfTimingBITSRxQltyLevel,
        tmnxSyncIfTimingBITS2InUse,
        tmnxSyncIfTimingBITS2Qualified,
        tmnxSyncIfTimingBITS2Alarm,
        tmnxSyncIfTimingBITS2RxQltyLevel,
        tmnxSyncIfTimingBITS2State,
        tmnxSyncIfTimingRef1NationalUse,
        tmnxSyncIfTimingRef2NationalUse,
        tmnxSyncIfTimingBITSNationalUse,
        tmnxSyncIfTimingQLSelection,
        tmnxSyncIfTimingOtherCPMInUse,
        tmnxSyncIfTimingOtherCPMQual,
        tmnxSyncIfTimingOtherCPMAlarm,
        tmnxSyncIfTimingOtherCPMState,
        tmnxSyncIfTimingBITSOutRefSel,
        tmnxSyncIfTimingBITSTxQltyLevel,
        tmnxSyncIfTimingBITS2AdminStatus,
        tmnxSyncIfTimingSystemQltyLevel,
        tSyncIfTimingAdmBITSOutAdmStatus,
        tSyncIfTimingAdmBITSOutLineLen,
        tSyncIfTimingAdmRef1CfgQltyLevel,
        tSyncIfTimingAdmRef2CfgQltyLevel,
        tSyncIfTimingAdmBITSCfgQltyLevel,
        tSyncIfTimingAdmRef1NationalUse,
        tSyncIfTimingAdmRef2NationalUse,
        tSyncIfTimingAdmBITSNationalUse,
        tSyncIfTimingAdmQLSelection
    }
    STATUS      current
    DESCRIPTION
        "The group of objects added in 8.0 release to support new
         Sync-if-timing features on Nokia SROS series systems."
    ::= { tmnxChassisGroups 44 }

tmnxSyncIfTimingNotifV8v0Group   NOTIFICATION-GROUP
    NOTIFICATIONS {
        tmnxEqSyncIfTimingRef1Quality,
        tmnxEqSyncIfTimingRef2Quality,
        tmnxEqSyncIfTimingBITSQuality,
        tmnxEqSyncIfTimingBITS2Quality,
        tmnxEqSyncIfTimingRefSwitch,
        tmnxEqSyncIfTimingBITS2Alarm,
        tmnxEqSyncIfTimingBITS2AlarmClr,
        tmnxEqSyncIfTimingBITSOutRefChg,
        tmnxEqSyncIfTimingSystemQuality
    }
    STATUS      current
    DESCRIPTION
        "The group of objects added in 8.0 release to support Sync-If-Timing
         notifications on Nokia SROS series systems."
    ::= { tmnxChassisGroups 45 }

tmnxChassisV8v0Group             OBJECT-GROUP
    OBJECTS     {
        tmnxHwEquippedPlatform,
        tmnxChassisRedForcedSingleSfm,
        tmnxCardCapability
    }
    STATUS      current
    DESCRIPTION
        "The group of objects added in 8.0 release on Nokia SR series systems."
    ::= { tmnxChassisGroups 46 }

tmnxChassisMixedModeIomV8v0Group OBJECT-GROUP
    OBJECTS     {
        tmnxChassisMixedModeIomAdminMode,
        tmnxChassisMixedModeIomUpgrList
    }
    STATUS      current
    DESCRIPTION
        "The group of objects added in 8.0 release on Nokia SR series systems
         to support the Mixed Mode IOM feature."
    ::= { tmnxChassisGroups 47 }

tmnxCardCamErrorV6v1Group        OBJECT-GROUP
    OBJECTS     {
        tmnxCardCmplx1CAMErrorOccur,
        tmnxCardCmplx1CAMErrorOccurTime,
        tmnxCardCmplx2CAMErrorOccur,
        tmnxCardCmplx2CAMErrorOccurTime,
        tmnxCpmCardCmplxCAMErrOccur,
        tmnxCpmCardCmplxCAMErrOccurTime
    }
    STATUS      current
    DESCRIPTION
        "The group of objects added in 6.1 release on Nokia 7xx0 SR series
         systems related to Card CAM Failures."
    ::= { tmnxChassisGroups 48 }

tmnxChassisV6v0Group             OBJECT-GROUP
    OBJECTS     {
        tmnxCardLastBootupReason
    }
    STATUS      obsolete
    DESCRIPTION
        "The group of objects added in 6.0 release on Nokia 7xx0 SR series
         systems."
    ::= { tmnxChassisGroups 49 }

tmnxCardV7v0Group                OBJECT-GROUP
    OBJECTS     {
        tmnxCardFailOnError
    }
    STATUS      current
    DESCRIPTION
        "The group of objects added in 7.0 release on Nokia 7xx0 SR series
         systems for card management."
    ::= { tmnxChassisGroups 50 }

tmnxAtmGroup                     OBJECT-GROUP
    OBJECTS     {
        tmnxMDAAtmMode
    }
    STATUS      current
    DESCRIPTION
        "The group of objects on Nokia 7xx0 SR series systems for ATM
         management."
    ::= { tmnxChassisGroups 51 }

tmnxChassisHwV6v1Group           OBJECT-GROUP
    OBJECTS     {
        tmnxHwMfgAssemblyNumber
    }
    STATUS      current
    DESCRIPTION
        "The group of hardware related objects added in release 6.1 on Nokia
         7xx0 SR series systems."
    ::= { tmnxChassisGroups 52 }

tmnxChassisHwV9v0Group           OBJECT-GROUP
    OBJECTS     {
        tmnxCpmCardOscillatorType,
        tmnxHwFirmwareCodeVersion
    }
    STATUS      current
    DESCRIPTION
        "The group of hardware related objects added in release 9.0 on Nokia
         SROS series systems."
    ::= { tmnxChassisGroups 53 }

tmnxSyncIfTimingV9v0Group        OBJECT-GROUP
    OBJECTS     {
        tmnxSyncIfTimingRefOrder4,
        tmnxSyncIfTimingPTPAdminStatus,
        tmnxSyncIfTimingPTPInUse,
        tmnxSyncIfTimingPTPQualified,
        tmnxSyncIfTimingPTPAlarm,
        tmnxSyncIfTimingPTPCfgQltyLevel,
        tmnxSyncIfTimingPTPRxQltyLevel,
        tmnxSyncIfTimingPTPState,
        tmnxSyncIfTimingBITSOutSource,
        tSyncIfTimingAdmRefOrder4,
        tSyncIfTimingAdmPTPAdminStatus,
        tSyncIfTimingAdmPTPCfgQltyLevel,
        tSyncIfTimingAdmBITSOutSource
    }
    STATUS      current
    DESCRIPTION
        "The group of objects added in 9.0 release to support new
         Sync-if-timing features on Nokia SROS series systems."
    ::= { tmnxChassisGroups 54 }

tmnxSyncIfTimingNotifyV9v0Group  NOTIFICATION-GROUP
    NOTIFICATIONS {
        tmnxEqSyncIfTimingPTPQuality,
        tmnxEqSyncIfTimingPTPAlarm,
        tmnxEqSyncIfTimingPTPAlarmClear
    }
    STATUS      current
    DESCRIPTION
        "The group of notifications added in 9.0 release to support new
         Sync-if-timing features on Nokia SROS series systems."
    ::= { tmnxChassisGroups 55 }

tmnxChassisNotifyObjsV9v0Group   OBJECT-GROUP
    OBJECTS     {
        tmnxMdaNotifyType
    }
    STATUS      current
    DESCRIPTION
        "The group of notification objects extending chassis features for
         revision 9.0 on Nokia SROS series systems."
    ::= { tmnxChassisGroups 56 }

tmnxMDAV9v0Group                 OBJECT-GROUP
    OBJECTS     {
        tmnxMDAEgrHsmdaThrshLoBrstMult,
        tmnxMDAEgrHsmdaThrshHiBrstInc
    }
    STATUS      obsolete
    DESCRIPTION
        "The group of objects added in 9.0 release to support new HSMDA
         threshold limits on Nokia SROS series systems."
    ::= { tmnxChassisGroups 57 }

tmnxCardPchipV8v0Group           OBJECT-GROUP
    OBJECTS     {
        tmnxCardCmplx1EgrFcsSrcSlots,
        tmnxCardCmplx2EgrFcsSrcSlots
    }
    STATUS      current
    DESCRIPTION
        "The group of objects added in 8.0 release to enhance IOM Card Pchip
         error indications on Nokia SROS series systems."
    ::= { tmnxChassisGroups 58 }

tmnxChassisNotifyObjsV8v0Group   OBJECT-GROUP
    OBJECTS     {
        tmnxCardSrcSlotBitmap
    }
    STATUS      current
    DESCRIPTION
        "The group of objects added in 8.0 release to support chassis hardware
         notifications on Nokia SROS series systems."
    ::= { tmnxChassisGroups 59 }

tmnxFPQGrpGroup                  OBJECT-GROUP
    OBJECTS     {
        tmnxFPAccIngQGrpAcctgPolId,
        tmnxFPAccIngQGrpCollectStats,
        tmnxFPAccIngQGrpDescr,
        tmnxFPAccIngQGrpLastChgd,
        tmnxFPAccIngQGrpRowStatus,
        tmnxFPAccIngQGrpPolicerPol,
        tmnxFPAccIngQGrpTableLastChgd,
        tmnxFPNetIngQGrpAcctgPolId,
        tmnxFPNetIngQGrpCollectStats,
        tmnxFPNetIngQGrpDescr,
        tmnxFPNetIngQGrpLastChgd,
        tmnxFPNetIngQGrpRowStatus,
        tmnxFPNetIngQGrpPolicerPol,
        tmnxFPNetIngQGrpTableLastChgd,
        tmnxFPNetIngQGrpPStatMode,
        tmnxFPNetIngQgPStOffHPrioPkts,
        tmnxFPNetIngQgPStOffHPrioPktsL,
        tmnxFPNetIngQgPStOffHPrioPktsH,
        tmnxFPNetIngQgPStDrpHPrioPkts,
        tmnxFPNetIngQgPStDrpHPrioPktsL,
        tmnxFPNetIngQgPStDrpHPrioPktsH,
        tmnxFPNetIngQgPStOffLPrioPkts,
        tmnxFPNetIngQgPStOffLPrioPktsL,
        tmnxFPNetIngQgPStOffLPrioPktsH,
        tmnxFPNetIngQgPStDrpLPrioPkts,
        tmnxFPNetIngQgPStDrpLPrioPktsL,
        tmnxFPNetIngQgPStDrpLPrioPktsH,
        tmnxFPNetIngQgPStOffHPrioOcts,
        tmnxFPNetIngQgPStOffHPrioOctsL,
        tmnxFPNetIngQgPStOffHPrioOctsH,
        tmnxFPNetIngQgPStDrpHPrioOcts,
        tmnxFPNetIngQgPStDrpHPrioOctsL,
        tmnxFPNetIngQgPStDrpHPrioOctsH,
        tmnxFPNetIngQgPStOffLPrioOcts,
        tmnxFPNetIngQgPStOffLPrioOctsL,
        tmnxFPNetIngQgPStOffLPrioOctsH,
        tmnxFPNetIngQgPStDrpLPrioOcts,
        tmnxFPNetIngQgPStDrpLPrioOctsL,
        tmnxFPNetIngQgPStDrpLPrioOctsH,
        tmnxFPNetIngQgPStFwdInProfPkts,
        tmnxFPNetIngQgPStFwdInProfPktsL,
        tmnxFPNetIngQgPStFwdInProfPktsH,
        tmnxFPNetIngQgPStFwdOutProfPkts,
        tmnxFPNetIngQgPStFwdOutProfPktsL,
        tmnxFPNetIngQgPStFwdOutProfPktsH,
        tmnxFPNetIngQgPStFwdInProfOcts,
        tmnxFPNetIngQgPStFwdInProfOctsL,
        tmnxFPNetIngQgPStFwdInProfOctsH,
        tmnxFPNetIngQgPStFwdOutProfOcts,
        tmnxFPNetIngQgPStFwdOutProfOctsL,
        tmnxFPNetIngQgPStFwdOutProfOctsH,
        tmnxFPNetIngQgPStUncolPktsOff,
        tmnxFPNetIngQgPStUncolPktsOffL,
        tmnxFPNetIngQgPStUncolPktsOffH,
        tmnxFPNetIngQgPStUncolOctsOff,
        tmnxFPNetIngQgPStUncolOctsOffL,
        tmnxFPNetIngQgPStUncolOctsOffH,
        tmnxFPAccIngQGrpPStatMode,
        tmnxFPAccIngQgPStOffHPrioPkts,
        tmnxFPAccIngQgPStOffHPrioPktsL,
        tmnxFPAccIngQgPStOffHPrioPktsH,
        tmnxFPAccIngQgPStDrpHPrioPkts,
        tmnxFPAccIngQgPStDrpHPrioPktsL,
        tmnxFPAccIngQgPStDrpHPrioPktsH,
        tmnxFPAccIngQgPStOffLPrioPkts,
        tmnxFPAccIngQgPStOffLPrioPktsL,
        tmnxFPAccIngQgPStOffLPrioPktsH,
        tmnxFPAccIngQgPStDrpLPrioPkts,
        tmnxFPAccIngQgPStDrpLPrioPktsL,
        tmnxFPAccIngQgPStDrpLPrioPktsH,
        tmnxFPAccIngQgPStOffHPrioOcts,
        tmnxFPAccIngQgPStOffHPrioOctsL,
        tmnxFPAccIngQgPStOffHPrioOctsH,
        tmnxFPAccIngQgPStDrpHPrioOcts,
        tmnxFPAccIngQgPStDrpHPrioOctsL,
        tmnxFPAccIngQgPStDrpHPrioOctsH,
        tmnxFPAccIngQgPStOffLPrioOcts,
        tmnxFPAccIngQgPStOffLPrioOctsL,
        tmnxFPAccIngQgPStOffLPrioOctsH,
        tmnxFPAccIngQgPStDrpLPrioOcts,
        tmnxFPAccIngQgPStDrpLPrioOctsL,
        tmnxFPAccIngQgPStDrpLPrioOctsH,
        tmnxFPAccIngQgPStFwdInProfPkts,
        tmnxFPAccIngQgPStFwdInProfPktsL,
        tmnxFPAccIngQgPStFwdInProfPktsH,
        tmnxFPAccIngQgPStFwdOutProfPkts,
        tmnxFPAccIngQgPStFwdOutProfPktsL,
        tmnxFPAccIngQgPStFwdOutProfPktsH,
        tmnxFPAccIngQgPStFwdInProfOcts,
        tmnxFPAccIngQgPStFwdInProfOctsL,
        tmnxFPAccIngQgPStFwdInProfOctsH,
        tmnxFPAccIngQgPStFwdOutProfOcts,
        tmnxFPAccIngQgPStFwdOutProfOctsL,
        tmnxFPAccIngQgPStFwdOutProfOctsH,
        tmnxFPAccIngQgPStUncolPktsOff,
        tmnxFPAccIngQgPStUncolPktsOffL,
        tmnxFPAccIngQgPStUncolPktsOffH,
        tmnxFPAccIngQgPStUncolOctsOff,
        tmnxFPAccIngQgPStUncolOctsOffL,
        tmnxFPAccIngQgPStUncolOctsOffH,
        tFPNetIngQGrpArbitStatFwdPkts,
        tFPNetIngQGrpArbitStatFwdPktsL,
        tFPNetIngQGrpArbitStatFwdPktsH,
        tFPNetIngQGrpArbitStatFwdOcts,
        tFPNetIngQGrpArbitStatFwdOctsL,
        tFPNetIngQGrpArbitStatFwdOctsH,
        tFPAccIngQGrpArbitStatFwdPkts,
        tFPAccIngQGrpArbitStatFwdPktsL,
        tFPAccIngQGrpArbitStatFwdPktsH,
        tFPAccIngQGrpArbitStatFwdOcts,
        tFPAccIngQGrpArbitStatFwdOctsL,
        tFPAccIngQGrpArbitStatFwdOctsH
    }
    STATUS      current
    DESCRIPTION
        "The group of objects added in 10.0 release to support forwarding-plane
         queue-group objects on Nokia SROS series systems."
    ::= { tmnxChassisGroups 60 }

tmnxCardV10v0Group               OBJECT-GROUP
    OBJECTS     {
        tmnxCardHardResetUnsupMdas,
        tmnxCardRateCalcFastQueue,
        tmnxCardRateCalcSlowQueue,
        tmnxCardSchedRun,
        tmnxCardTaskScheduling,
        tmnxCardSlowQueueThresh
    }
    STATUS      current
    DESCRIPTION
        "The group of objects added in 10.0 release to enhance IOM Card
         features on Nokia SROS series systems."
    ::= { tmnxChassisGroups 61 }

tmnxIpsecV10v0Group              OBJECT-GROUP
    OBJECTS     {
        tmnxIPsecIsaGrpTunnelReassembly,
        tmnxIPsecIsaGrpOperFlags,
        tmnxIPsecIsaGrpIpTunnels,
        tmnxIPsecIsaGrpIpMaxTunnels
    }
    STATUS      current
    DESCRIPTION
        "The group of objects added in 10.0 release to ipsec features on Nokia
         SROS series systems."
    ::= { tmnxChassisGroups 62 }

tmnxChassisV10v0Group            OBJECT-GROUP
    OBJECTS     {
        tmnxFanTrayCompSpeed,
        tmnxFabricSupportedTypes,
        tmnxFabricReboot,
        tmnxFabricTypeName,
        tmnxFabricTypeDescription,
        tmnxFabricTypeStatus,
        tmnxHwResourceCurrentVoltage,
        tmnxHwResourcePeakVoltage,
        tmnxHwResourcePeakVoltageTime,
        tmnxHwResourceMinVoltage,
        tmnxHwResourceMinVoltageTime,
        tmnxHwResourceCurrentWattage,
        tmnxHwResourcePeakWattage,
        tmnxHwResourcePeakWattageTime,
        tmnxHwResourceMinWattage,
        tmnxHwResourceMinWattageTime,
        tmnxHwResourceCurrentAmperage,
        tmnxHwResourcePeakAmperage,
        tmnxHwResourcePeakAmperageTime,
        tmnxHwResourceMinAmperage,
        tmnxHwResourceMinAmperageTime,
        tmnxHwFirmwareRevisionStatus
    }
    STATUS      current
    DESCRIPTION
        "The group of objects added in 10.0 release to enhance hardware
         functionality on Nokia SROS series systems."
    ::= { tmnxChassisGroups 63 }

tmnxChassisNotificationV9v0Group NOTIFICATION-GROUP
    NOTIFICATIONS {
        tmnxPeFirmwareVersionWarning,
        tmnxEqCardQChipBufMemoryEvent,
        tmnxEqCardQChipStatsMemoryEvent,
        tmnxEqCardQChipIntMemoryEvent,
        tmnxEqCardChipIfDownEvent,
        tmnxEqCardChipIfCellEvent
    }
    STATUS      current
    DESCRIPTION
        "The group of notifications supporting the management of chassis
         hardware for release 9.0 on Nokia SROS series systems."
    ::= { tmnxChassisGroups 64 }

tmnxFPQGrpV10v0R4Group           OBJECT-GROUP
    OBJECTS     {
        tFPAccIngQGrpPlcrOvrTblLstChgd,
        tFPAccIngQGrpPlcrOvrRowStatus,
        tFPAccIngQGrpPlcrOvrLastChgd,
        tFPAccIngQGrpPlcrOvrAdminPIR,
        tFPAccIngQGrpPlcrOvrAdminCIR,
        tFPAccIngQGrpPlcrOvrStatMode,
        tFPAccIngQGrpPlcrOvrMBS,
        tFPAccIngQGrpPlcrOvrCBS,
        tFPAccIngQGrpPlcrOvrPktOffset
    }
    STATUS      current
    DESCRIPTION
        "The group of objects added in 10.0 release to support forwarding-plane
         queue-group policer override objects on Nokia SROS series systems."
    ::= { tmnxChassisGroups 65 }

tmnxMdaV10v0Group                OBJECT-GROUP
    OBJECTS     {
        tmnxMDAIsaTunnelGroup,
        tmnxIPsecIsaGrpIPsecRespondOnly,
        tmnxIPsecIsaGrpMultiActive,
        tmnxIPsecIsaGrpActiveMda,
        tmnxMDAIsaTunnelGroupInUse,
        tmnxMDAFailOnError,
        tmnxMDAEgrXplErrThreshold,
        tmnxMDAEgrXplErrWindow,
        tmnxMDAIngrXplErrThreshold,
        tmnxMDAIngrXplErrWindow
    }
    STATUS      obsolete
    DESCRIPTION
        "The group of objects added in 10.0 release to enhance IOM MDA features
         on Nokia SROS series systems."
    ::= { tmnxChassisGroups 66 }

tmnxMdaObsoletedV10v0Group       OBJECT-GROUP
    OBJECTS     {
        tmnxMDAIngHsmdaSchedPolicy,
        tmnxMDAIngHsmdaPoolPolicy,
        tmnxHsmdaMdaSchOvrTblLastChangd,
        tmnxHsmdaMdaSchOvrRowStatus,
        tmnxHsmdaMdaSchOvrLastChanged,
        tmnxHsmdaMdaSchOvrMaxRate,
        tmnxHsmdaMdaSchOvrGrp1Rate,
        tmnxHsmdaMdaSchOvrGrp2Rate,
        tmnxHsmdaMdaSchOvrClass1Rate,
        tmnxHsmdaMdaSchOvrClass1WtInGrp,
        tmnxHsmdaMdaSchOvrClass2Rate,
        tmnxHsmdaMdaSchOvrClass2WtInGrp,
        tmnxHsmdaMdaSchOvrClass3Rate,
        tmnxHsmdaMdaSchOvrClass3WtInGrp,
        tmnxHsmdaMdaSchOvrClass4Rate,
        tmnxHsmdaMdaSchOvrClass4WtInGrp,
        tmnxHsmdaMdaSchOvrClass5Rate,
        tmnxHsmdaMdaSchOvrClass5WtInGrp,
        tmnxHsmdaMdaSchOvrClass6Rate,
        tmnxHsmdaMdaSchOvrClass6WtInGrp,
        tmnxHsmdaMdaSchOvrClass7Rate,
        tmnxHsmdaMdaSchOvrClass7WtInGrp,
        tmnxHsmdaMdaSchOvrClass8Rate,
        tmnxHsmdaMdaSchOvrClass8WtInGrp
    }
    STATUS      current
    DESCRIPTION
        "The group of objects obsoleted in 10.0 release to enhance IOM MDA
         features on Nokia SROS series systems."
    ::= { tmnxChassisGroups 67 }

tmnxChassisNotifyV10v0Group      NOTIFICATION-GROUP
    NOTIFICATIONS {
        tmnxMDAIsaTunnelGroupChange
    }
    STATUS      current
    DESCRIPTION
        "The group of notifications supporting the management of chassis
         hardware for release 10.0 on Nokia SROS series systems."
    ::= { tmnxChassisGroups 69 }

tmnxMdaHsmdaPoolV10v0Group       OBJECT-GROUP
    OBJECTS     {
        tmnxMDAEgrHsmdaPoolPolicy
    }
    STATUS      current
    DESCRIPTION
        "The group of objects added in 10.0 release to enhance IOM MDA features
         related to HSMDA on Nokia SROS series systems."
    ::= { tmnxChassisGroups 70 }

tmnxChassisV11v0Groups           OBJECT IDENTIFIER ::= { tmnxChassisGroups 71 }

tmnxFPDCpuProtV11v0R0Group       OBJECT-GROUP
    OBJECTS     {
        tmnxFPDCpuProtDynEnfrcPlcrPool,
        tmnxFpDcpDynPlcrHiWtrMrkHitCnt,
        tmnxFpDcpDynPlcrHiWtrMrkTime,
        tmnxFpDcpDynPlcrAllocFailCount,
        tmnxFpDcpDynPlcrInUse
    }
    STATUS      current
    DESCRIPTION
        "The group of objects added in 11.0 release to support forwarding-plane
         objects on Nokia SROS series systems."
    ::= { tmnxChassisV11v0Groups 1 }

tmnxFPDcpNotifyObjsV11v0Group    OBJECT-GROUP
    OBJECTS     {
        tmnxDcpTimeEventOccured,
        tmnxDcpMissingNotificationCount,
        tmnxChassisNotifyCardSlotNum
    }
    STATUS      current
    DESCRIPTION
        "The group of objects supporting management of Distributed CPU
         Protection feature for forwarding-plane on version 11.0 Nokia SROS
         series systems."
    ::= { tmnxChassisV11v0Groups 2 }

tmnxFPDcpNotifyV11v0Group        NOTIFICATION-GROUP
    NOTIFICATIONS {
        tmnxDcpCardFpEventOvrflw,
        tmnxDcpCardSapEventOvrflw,
        tmnxDcpCardVrtrIfEventOvrflw,
        tmnxDcpFpDynPoolUsageHiAlmRaise,
        tmnxDcpFpDynPoolUsageHiAlmClear,
        tmnxDcpCardFpEventOvrflwClr,
        tmnxDcpCardSapEventOvrflwClr,
        tmnxDcpCardVrtrIfEventOvrflwClr
    }
    STATUS      current
    DESCRIPTION
        "The group of notifications supporting management of Distributed CPU
         Protection feature for forwarding-plane on version 11.0 Nokia SROS
         series systems."
    ::= { tmnxChassisV11v0Groups 3 }

tmnxChassisObsoleteGroupV11v0    OBJECT-GROUP
    OBJECTS     {
        tmnxHwMfgString
    }
    STATUS      current
    DESCRIPTION
        "The group of objects obsoleted in 11.0 release on Nokia SROS series
         systems."
    ::= { tmnxChassisV11v0Groups 4 }

tmnxChassisV11v0Group            OBJECT-GROUP
    OBJECTS     {
        tmnxChassisTotalNumber,
        tmnxChassisLastChange,
        tmnxChassisRowStatus,
        tmnxChassisName,
        tmnxChassisType,
        tmnxChassisLocation,
        tmnxChassisCoordinates,
        tmnxChassisNumSlots,
        tmnxChassisNumPorts,
        tmnxChassisCriticalLEDState,
        tmnxChassisMajorLEDState,
        tmnxChassisMinorLEDState,
        tmnxChassisBaseMacAddress,
        tmnxChassisCLLICode,
        tmnxChassisReboot,
        tmnxChassisUpgrade,
        tmnxChassisAdminMode,
        tmnxChassisOperMode,
        tmnxChassisModeForce,
        tmnxChassisUpdateTimeLeft,
        tmnxChassisTypeName,
        tmnxChassisTypeDescription,
        tmnxChassisTypeStatus
    }
    STATUS      current
    DESCRIPTION
        "The group of objects supporting management of generic chassis
         capabilities on release 11.0 of Nokia SROS series systems."
    ::= { tmnxChassisV11v0Groups 5 }

tmnxChassisFanV11v0Group         OBJECT-GROUP
    OBJECTS     {
        tmnxChassisNumFanTrays,
        tmnxChassisNumFans,
        tmnxChassisFanOperStatus,
        tmnxChassisFanSpeed
    }
    STATUS      current
    DESCRIPTION
        "The group of objects supporting management of chassis Fan hardware
         capabilities on release 11.0 of Nokia SROS series systems."
    ::= { tmnxChassisV11v0Groups 6 }

tmnxChassisPowerV11v0Group       OBJECT-GROUP
    OBJECTS     {
        tmnxChassisNumPwrSupplies,
        tmnxChassisPowerSupplyACStatus,
        tmnxChassisPowerSupplyDCStatus,
        tmnxChassisPowerSupplyTempStatus,
        tmnxChassisPowerSupplyTempThreshold,
        tmnxChassisPowerSupply1Status,
        tmnxChassisPowerSupply2Status,
        tmnxChassisPowerSupplyAssignedType
    }
    STATUS      current
    DESCRIPTION
        "The group of objects supporting management of chassis power-supply
         hardware capabilities on release 11.0 of Nokia SROS series systems."
    ::= { tmnxChassisV11v0Groups 7 }

tmnxChassisHwV11v0Group          OBJECT-GROUP
    OBJECTS     {
        tmnxHwLastChange,
        tmnxHwID,
        tmnxHwMfgBoardNumber,
        tmnxHwSerialNumber,
        tmnxHwManufactureDate,
        tmnxHwClass,
        tmnxHwName,
        tmnxHwAlias,
        tmnxHwAssetID,
        tmnxHwCLEI,
        tmnxHwIsFRU,
        tmnxHwContainedIn,
        tmnxHwParentRelPos,
        tmnxHwAdminState,
        tmnxHwOperState,
        tmnxHwTempSensor,
        tmnxHwTemperature,
        tmnxHwTempThreshold,
        tmnxHwBootCodeVersion,
        tmnxHwSoftwareCodeVersion,
        tmnxHwSwLastBoot,
        tmnxHwAlarmState,
        tmnxHwLastAlarmEvent,
        tmnxHwClearAlarms,
        tmnxHwSwImageSource,
        tmnxHwMfgDeviations,
        tmnxHwBaseMacAddress,
        tmnxHwFailureReason,
        tmnxHwContainedIndex
    }
    STATUS      current
    DESCRIPTION
        "The group of objects supporting management of chassis hardware
         capabilities on release 11.0 of Nokia SROS series systems."
    ::= { tmnxChassisV11v0Groups 8 }

tmnxChassisQGrpOvrGroup          OBJECT-GROUP
    OBJECTS     {
        tFPNetIngQGrpPlcrOvrTblLstChgd,
        tFPNetIngQGrpPlcrOvrRowStatus,
        tFPNetIngQGrpPlcrOvrLastChgd,
        tFPNetIngQGrpPlcrOvrAdminPIR,
        tFPNetIngQGrpPlcrOvrAdminCIR,
        tFPNetIngQGrpPlcrOvrStatMode,
        tFPNetIngQGrpPlcrOvrMBS,
        tFPNetIngQGrpPlcrOvrCBS,
        tFPNetIngQGrpPlcrOvrPktOffset,
        tFPAccIngQGrpPCPOvrLastChgd,
        tFPAccIngQGrpPCPOvrLvlLastChgd,
        tFPAccIngQGrpPCPOvrLvlMBS,
        tFPAccIngQGrpPCPOvrLvlTblLstChgd,
        tFPAccIngQGrpPCPOvrMaxRate,
        tFPAccIngQGrpPCPOvrMinMBSSep,
        tFPAccIngQGrpPCPOvrRowStatus,
        tFPAccIngQGrpPCPOvrTblLastChgd,
        tFPNetIngQGrpPCPOvrLastChgd,
        tFPNetIngQGrpPCPOvrLvlLastChgd,
        tFPNetIngQGrpPCPOvrLvlMBS,
        tFPNetIngQGrpPCPOvrLvlTblLstChgd,
        tFPNetIngQGrpPCPOvrMaxRate,
        tFPNetIngQGrpPCPOvrMinMBSSep,
        tFPNetIngQGrpPCPOvrRowStatus,
        tFPNetIngQGrpPCPOvrTblLastChgd
    }
    STATUS      current
    DESCRIPTION
        "The group of objects supporting management of policer control policies
         capabilities on release 11.0 of Nokia SROS series systems."
    ::= { tmnxChassisV11v0Groups 9 }

tmnxFPPoolSizingV11v0Group       OBJECT-GROUP
    OBJECTS     {
        tmnxFPStablePoolSizing
    }
    STATUS      current
    DESCRIPTION
        "The group of objects supporting management of policer control policies
         capabilities on release 11.0 of Nokia SROS series systems."
    ::= { tmnxChassisV11v0Groups 10 }

tmnxChassisPowerMgmtGroup        OBJECT-GROUP
    OBJECTS     {
        tmnxChassisPEQTableLastChg,
        tmnxChassisPEQLastChangedTime,
        tmnxChassisPowerMgmtTableLastChg,
        tmnxChassisPwrMgmtChangedTime,
        tmnxChassisPEQAssignedType,
        tmnxChassisPEQAvailableWattage,
        tmnxChassisPEQEquippedType,
        tmnxChassisPEQSupportedTypes,
        tmnxPEQTypeDescription,
        tmnxPEQTypeName,
        tmnxChassisPwrMgmtMode,
        tmnxChassisPwrMgmtSafetyLevel,
        tmnxChassisPwrMgmtSafetyAlert,
        tmnxMDAHwPowerPriority,
        tmnxHwResourceMaxRequiredWattage,
        tmnxHwPowerZone
    }
    STATUS      current
    DESCRIPTION
        "The group of objects supporting the management of power utilization
         capabilities on release 11.0 of Nokia SROS series systems."
    ::= { tmnxChassisV11v0Groups 11 }

tmnxChassisPowerMgmtNotifyObjs   OBJECT-GROUP
    OBJECTS     {
        tmnxChassisNotifyPowerZone,
        tmnxChassisNotifyPowerCapacity
    }
    STATUS      current
    DESCRIPTION
        "The group of notification-objects supporting the management of power
         utilization capabilities on release 11.0 of Nokia SROS series systems."
    ::= { tmnxChassisV11v0Groups 12 }

tmnxChassisPowerMgmtNotifyGroup  NOTIFICATION-GROUP
    NOTIFICATIONS {
        tmnxEqPowerCapacityExceeded,
        tmnxEqPowerCapacityExceededClear,
        tmnxEqPowerLostCapacity,
        tmnxEqPowerLostCapacityClear,
        tmnxEqPowerOverloadState,
        tmnxEqPowerOverloadStateClear,
        tmnxEqPowerSafetyAlertThreshold,
        tmnxEqPowerSafetyAlertClear,
        tmnxEqPowerSafetyLevelThreshold,
        tmnxEqPowerSafetyLevelClear,
        tmnxEqProvPowerCapacityAlm,
        tmnxEqProvPowerCapacityAlmClr
    }
    STATUS      current
    DESCRIPTION
        "The group of notifications supporting the management of power
         utilization capabilities on release 11.0 of Nokia SROS series systems."
    ::= { tmnxChassisV11v0Groups 13 }

tmnxChassisSmartPeqV11v0Group    OBJECT-GROUP
    OBJECTS     {
        tmnxChassisPowerSupplyInFeedDown
    }
    STATUS      current
    DESCRIPTION
        "The group of objects supporting the management of smart PEQ
         capabilities on release 11.0 of Nokia SROS series systems."
    ::= { tmnxChassisV11v0Groups 14 }

tmnxChassisSmartPeqNtfyV11v0Grp  NOTIFICATION-GROUP
    NOTIFICATIONS {
        tmnxEqPowerSupplyInputFeedAlm,
        tmnxEqPowerSupplyInputFeedAlmClr
    }
    STATUS      obsolete
    DESCRIPTION
        "The group of notifications supporting the management of smart PEQ
         capabilities on release 11.0 of Nokia SROS series systems."
    ::= { tmnxChassisV11v0Groups 15 }

tmnxChassisFabricV11v0Group      OBJECT-GROUP
    OBJECTS     {
        tmnxChassisFabricSpeed
    }
    STATUS      current
    DESCRIPTION
        "The group of objects supporting the management of the system fabric
         speed on release 11.0 of Nokia SROS series systems."
    ::= { tmnxChassisV11v0Groups 16 }

tmnxChassisSwitchFabNtfyV11v0Grp NOTIFICATION-GROUP
    NOTIFICATIONS {
        tmnxEqLowSwitchFabricCap,
        tmnxEqLowSwitchFabricCapClear
    }
    STATUS      current
    DESCRIPTION
        "The group of notifications supporting chassis switch fabric management
         on release 11.0 of Nokia SROS series systems."
    ::= { tmnxChassisV11v0Groups 17 }

tmnxCpmCardRebootHoldV11v0Group  OBJECT-GROUP
    OBJECTS     {
        tmnxCpmCardRebootHold
    }
    STATUS      current
    DESCRIPTION
        "The group of additional objects supporting CPM standby reboot hold in
         release 11.0 of Nokia SROS series systems."
    ::= { tmnxChassisV11v0Groups 18 }

tmnxChassisV9v0Groups            OBJECT IDENTIFIER ::= { tmnxChassisGroups 72 }

tmnxCpmCardCmplxMemErrV9v0Group  OBJECT-GROUP
    OBJECTS     {
        tmnxCpmCardCmplxMemErrOccur,
        tmnxCpmCardCmplxMemErrOccurTime
    }
    STATUS      current
    DESCRIPTION
        "The group of objects supporting management of CPM complex memory
         errors on release 9.0 of Nokia SROS series systems."
    ::= { tmnxChassisV9v0Groups 1 }

tmnxCardCmplQChipMemErrV9v0Group OBJECT-GROUP
    OBJECTS     {
        tmnxCardCmpl1BufMemErrOccur,
        tmnxCardCmpl1BufMemErrOccurTime,
        tmnxCardCmpl2BufMemErrOccur,
        tmnxCardCmpl2BufMemErrOccurTime,
        tmnxCardCmpl1StatMemErrOccur,
        tmnxCardCmpl1StatMemErrOccurTime,
        tmnxCardCmpl2StatMemErrOccur,
        tmnxCardCmpl2StatMemErrOccurTime,
        tmnxCardCmpl1IntMemErrOccur,
        tmnxCardCmpl1IntMemErrOccurTime,
        tmnxCardCmpl2IntMemErrOccur,
        tmnxCardCmpl2IntMemErrOccurTime,
        tmnxCpmCardCmplBufMemErrOcc,
        tmnxCpmCardCmplBufMemErrOccTime,
        tmnxCpmCardCmplStatMemErrOcc,
        tmnxCpmCardCmplStatMemErrOccTime,
        tmnxCpmCardCmplIntMemErrOcc,
        tmnxCpmCardCmplIntMemErrOccTime
    }
    STATUS      current
    DESCRIPTION
        "The group of objects supporting management of card complex Q-chip
         memory errors on release 9.0 of Nokia SROS series systems."
    ::= { tmnxChassisV9v0Groups 2 }

tmnxCardCmplChipIfErrV9v0Group   OBJECT-GROUP
    OBJECTS     {
        tmnxCardCmpl1ChipIfDownOcc,
        tmnxCardCmpl1ChipIfDownOccTime,
        tmnxCardCmpl2ChipIfDownOcc,
        tmnxCardCmpl2ChipIfDownOccTime,
        tmnxCardCmpl1ChipIfCellOcc,
        tmnxCardCmpl1ChipIfCellOccTime,
        tmnxCardCmpl2ChipIfCellOcc,
        tmnxCardCmpl2ChipIfCellOccTime,
        tmnxCpmCardCmplChipIfDownOcc,
        tmnxCpmCardCmplChipIfDownOccTime,
        tmnxCpmCardCmplChipIfCellOcc,
        tmnxCpmCardCmplChipIfCellOccTime
    }
    STATUS      current
    DESCRIPTION
        "The group of objects supporting management of card complex chip
         interface errors on release 9.0 of Nokia SROS series systems."
    ::= { tmnxChassisV9v0Groups 3 }

tmnxChassisHwEventGroup          OBJECT-GROUP
    OBJECTS     {
        tmnxCardHwEventNumOccurrences,
        tmnxCardHwEventLastOccurTime
    }
    STATUS      current
    DESCRIPTION
        "The group of additional objects supporting Hardware event detection
         and reporting in release 9.0 of Nokia SROS series systems."
    ::= { tmnxChassisV9v0Groups 4 }

tmnxChassisHwEventNotifyGroup    NOTIFICATION-GROUP
    NOTIFICATIONS {
        tmnxEqCardTChipParityEvent
    }
    STATUS      current
    DESCRIPTION
        "The group of additional notification-types supporting Hardware event
         detection and reporting in release 9.0 of Nokia SROS series systems."
    ::= { tmnxChassisV9v0Groups 5 }

tmnxChassisPowerSupplyV9v0Grp    OBJECT-GROUP
    OBJECTS     {
        tmnxChassisPowerSupplyPemACRect
    }
    STATUS      current
    DESCRIPTION
        "The group of additional objects supporting chassis power supplies in
         release 9.0 of Nokia SROS series systems."
    ::= { tmnxChassisV9v0Groups 6 }

tmnxChassisV12v0Groups           OBJECT IDENTIFIER ::= { tmnxChassisGroups 73 }

tmnxChassisResourceV12v0Group    OBJECT-GROUP
    OBJECTS     {
        tChassisResSapIngQosPolTotal,
        tChassisResSapIngQosPolAlloc,
        tChassisResSapEgrQosPolTotal,
        tChassisResSapEgrQosPolAlloc,
        tChassisResIngQGrpTmplTotal,
        tChassisResIngQGrpTmplAlloc,
        tChassisResEgrQGrpTmplTotal,
        tChassisResEgrQGrpTmplAlloc,
        tChassisResPortEgrQGrpInstTotal,
        tChassisResPortEgrQGrpInstAlloc,
        tChassisResFPIngQGrpInstTotal,
        tChassisResFPIngQGrpInstAlloc,
        tChassisResPortEgrVPortTotal,
        tChassisResPortEgrVPortAlloc,
        tCardResQosUserSchedsTotal,
        tCardResQosUserSchedsAlloc,
        tCardResQosIntSchedsTotal,
        tCardResQosIntSchedsAlloc,
        tCardResSubSPIQosOvrTotal,
        tCardResSubSPIQosOvrAlloc,
        tCardResHsmdaQOvrTotal,
        tCardResHsmdaQOvrAlloc,
        tCardResPortAccEgrQGrpInstTotal,
        tCardResPortAccEgrQGrpInstAlloc,
        tCardResPortNetEgrQGrpInstTotal,
        tCardResPortNetEgrQGrpInstAlloc,
        tCardResPortEgrQGrpInstTotal,
        tCardResPortEgrQGrpInstAlloc,
        tCardResFPIngQGrpInstTotal,
        tCardResFPIngQGrpInstAlloc,
        tCardResPortEgrVPortTotal,
        tCardResPortEgrVPortAlloc,
        tFPResSapIngQosPolTotal,
        tFPResSapIngQosPolAlloc,
        tFPResDynEgrClassTotal,
        tFPResDynEgrClassAlloc,
        tFPResDynEgrClassIUBSE,
        tFPResDynEgrClassIUBNE,
        tFPResIngQueueTotal,
        tFPResIngQueueAlloc,
        tFPResEgrQueueTotal,
        tFPResEgrQueueAlloc,
        tFPResIngPolicerTotal,
        tFPResIngPolicerAlloc,
        tFPResEgrPolicerTotal,
        tFPResEgrPolicerAlloc,
        tFPResIngPolicerStatTotal,
        tFPResIngPolicerStatAlloc,
        tFPResEgrPolicerStatTotal,
        tFPResEgrPolicerStatAlloc,
        tFPResIngRootArbiterTotal,
        tFPResIngRootArbiterAlloc,
        tFPResEgrRootArbiterTotal,
        tFPResEgrRootArbiterAlloc,
        tFPResIntArbiterTotal,
        tFPResIntArbiterAlloc,
        tFPResDynQueueTotal,
        tFPResDynQueueAlloc,
        tFPResDynQueueIUBI,
        tFPResDynQueueIUBE,
        tFPResDynPolicerTotal,
        tFPResDynPolicerAlloc,
        tFPResDynPolicerIUBI,
        tFPResDynPolicerIUBE,
        tFPResDynPolicerStatTotal,
        tFPResDynPolicerStatAlloc,
        tFPResDynPolicerStatIUBI,
        tFPResDynPolicerStatIUBE,
        tFPResIngAclEntryTotal,
        tFPResIngAclEntryAlloc,
        tFPResIngQosEntryTotal,
        tFPResIngQosEntryAlloc,
        tFPResIngAclQosEntryTotal,
        tFPResIngAclQosEntryAlloc,
        tFPResIngIPv6AclEntryTotal,
        tFPResIngIPv6AclEntryAlloc,
        tFPResIngIPv6QosEntryTotal,
        tFPResIngIPv6QosEntryAlloc,
        tFPResEgrAclEntryTotal,
        tFPResEgrAclEntryAlloc,
        tFPResEgrQosEntryTotal,
        tFPResEgrQosEntryAlloc,
        tFPResEgrAclQosEntryTotal,
        tFPResEgrAclQosEntryAlloc,
        tFPResEgrIPv6AclEntryTotal,
        tFPResEgrIPv6AclEntryAlloc,
        tFPResEgrIPv6QosEntryTotal,
        tFPResEgrIPv6QosEntryAlloc,
        tFPResIngAclFilterTotal,
        tFPResIngAclFilterAlloc,
        tFPResEgrAclFilterTotal,
        tFPResEgrAclFilterAlloc,
        tFPResDynSvcEntryTotal,
        tFPResDynSvcEntryAlloc,
        tFPResSubHostTotal,
        tFPResSubHostAlloc,
        tFPResEncapGrpMemberTotal,
        tFPResEncapGrpMemberAlloc,
        tFPResEgrNetQGrpMapTotal,
        tFPResEgrNetQGrpMapAlloc,
        tFPResMacFdbRecTotal,
        tFPResMacFdbRecAlloc,
        tFPResResRvplsFdbRecTotal,
        tFPResResRvplsFdbRecAlloc,
        tFPResDynQ2NamedPoolTotal,
        tFPResDynQ2NamedPoolAlloc,
        tFPResDynQ2NamedPoolIUBI,
        tFPResDynQ2NamedPoolIUBE,
        tFPResIngQ1NamedPoolTotal,
        tFPResIngQ1NamedPoolAlloc,
        tFPResEgrQ1NamedPoolTotal,
        tFPResEgrQ1NamedPoolAlloc,
        tFPResDynQ2WredPoolTotal,
        tFPResDynQ2WredPoolAlloc,
        tMDAResEgrHsmdaQGrpTotal,
        tMDAResEgrHsmdaQGrpAlloc,
        tMDAResEgrHsmdaSecShaperTotal,
        tMDAResEgrHsmdaSecShaperAlloc
    }
    STATUS      obsolete
    DESCRIPTION
        "The group of objects supporting management of System Resource
         Information on release 12.0 of Nokia SROS series systems."
    ::= { tmnxChassisV12v0Groups 1 }

tmnxFPBufAllocV12v0Group         OBJECT-GROUP
    OBJECTS     {
        tmnxFPIngressBufferAllocation
    }
    STATUS      current
    DESCRIPTION
        "The group of objects supporting management of buffer allocation for
         named pools on release 12.0 of Nokia SROS series systems."
    ::= { tmnxChassisV12v0Groups 2 }

tmnxFPPlcyAcctV12v0Group         OBJECT-GROUP
    OBJECTS     {
        tmnxFPPlcyAcctStatsPool,
        tmnxFPPlcyAcctStatsInUse
    }
    STATUS      current
    DESCRIPTION
        "The group of objects supporting management of stats pool for policy
         accounting on release 12.0 of Nokia SROS series systems."
    ::= { tmnxChassisV12v0Groups 3 }

tmnxPhysChassisGroup             OBJECT-GROUP
    OBJECTS     {
        tmnxPhysChassisRole,
        tmnxPhysChassisState,
        tmnxPhysChassisHwIndex,
        tmnxPhysChassisNumPwrSupplies,
        tmnxPhysChassisNumFanTrays,
        tmnxPhysChassisNumFans,
        tmnxPhysChassisName
    }
    STATUS      current
    DESCRIPTION
        "The group of objects supporting management of physical chassis on
         release 12.0 of Nokia SROS series systems."
    ::= { tmnxChassisV12v0Groups 4 }

tmnxChassisNotifV12v0Group       NOTIFICATION-GROUP
    NOTIFICATIONS {
        tmnxEqDataPathFailureProtImpact,
        tmnxExtStandbyCpmReboot,
        tmnxExtStandbyCpmRebootFail
    }
    STATUS      current
    DESCRIPTION
        "The group of notifications supporting chassis management on release
         12.0 of Nokia SROS series systems."
    ::= { tmnxChassisV12v0Groups 5 }

tmnxCpmCardRebootHoldV12v0Group  OBJECT-GROUP
    OBJECTS     {
        tmnxCpmCardRebootHold
    }
    STATUS      obsolete
    DESCRIPTION
        "The group of additional objects supporting CPM standby reboot hold in
         release 12.0 of Nokia SROS series systems."
    ::= { tmnxChassisV12v0Groups 6 }

tmnxChassisPlcyAcctNtfyV12v0Grp  NOTIFICATION-GROUP
    NOTIFICATIONS {
        tmnxPlcyAcctStatsPoolExcResource,
        tmnxPlcyAcctStatsPoolLowResource,
        tmnxPlcyAcctStatsEventOvrflw,
        tmnxPlcyAcctStatsEventOvrflwClr
    }
    STATUS      current
    DESCRIPTION
        "The group of notifications supporting the management of policy
         accounting on release 12.0 of Nokia SROS series systems."
    ::= { tmnxChassisV12v0Groups 7 }

tmnxChassisV12v0Group            OBJECT-GROUP
    OBJECTS     {
        tmnxChassisOperNumSlots,
        tmnxChassisOperTopology
    }
    STATUS      current
    DESCRIPTION
        "The group of objects supporting management of generic chassis
         capabilities on release 12.0 of Nokia SROS series systems."
    ::= { tmnxChassisV12v0Groups 8 }

tmnxChassisObsoleteV12v0Group    OBJECT-GROUP
    OBJECTS     {
        tmnxChassisAdminLastSetTimer,
        tmnxChassisAdminLastSetTimeout
    }
    STATUS      current
    DESCRIPTION
        "The group of objects obsoleted in 12.0 release on Nokia SROS series
         systems."
    ::= { tmnxChassisV12v0Groups 9 }

tmnxChassPANotifyObjsV12v0Grp    OBJECT-GROUP
    OBJECTS     {
        tmnxPlcyAcctMissingNotifCount,
        tmnxPlcyAcctTimeEventOccured
    }
    STATUS      current
    DESCRIPTION
        "The group of objects supporting the management of policy accounting on
         release 12.0 of Nokia SROS series systems."
    ::= { tmnxChassisV12v0Groups 10 }

tmnxChassisNotifyObjsV12v0Group  OBJECT-GROUP
    OBJECTS     {
        tmnxChassisNotifyCpmCardSlotNum,
        tmnxChassisNotifyFabricSlotNum
    }
    STATUS      current
    DESCRIPTION
        "The group of notification-objects supporting management of generic
         chassis capabilities on release 12.0 of Nokia SROS series systems."
    ::= { tmnxChassisV12v0Groups 11 }

tmnxIomResrcNotifyObjsV12v0Grp   OBJECT-GROUP
    OBJECTS     {
        tmnxIomResourceType,
        tmnxIomResourceLimitPct,
        tmnxIomResLimMissingNotifCount,
        tmnxIomResLimitTimeEventOccured,
        tmnxChassisNotifyFpNum
    }
    STATUS      current
    DESCRIPTION
        "The group of objects supporting the management of IOM resources on
         release 12.0 of Nokia SROS series systems."
    ::= { tmnxChassisV12v0Groups 12 }

tmnxIomResrcNotifyV12v0Group     NOTIFICATION-GROUP
    NOTIFICATIONS {
        tmnxIomResHighLimitReached,
        tmnxIomResExhausted,
        tmnxIomResStateClr,
        tmnxIomEventOverflow,
        tmnxIomEventOverflowClr
    }
    STATUS      current
    DESCRIPTION
        "The group of notifications supporting the management of IOM resources
         on release 12.0 of Nokia SROS series systems."
    ::= { tmnxChassisV12v0Groups 13 }

tmnxChassisFabricV12v0Group      OBJECT-GROUP
    OBJECTS     {
        tmnxChassisFabricSpeed
    }
    STATUS      obsolete
    DESCRIPTION
        "The group of objects supporting the management of the system fabric
         speed on release 12.0 of Nokia SROS series systems."
    ::= { tmnxChassisV12v0Groups 14 }

tmnxChassisPowerV12v0Group       OBJECT-GROUP
    OBJECTS     {
        tmnxChassisPowerSupplyFanDir
    }
    STATUS      current
    DESCRIPTION
        "The group of objects supporting the management of power supply
         hardware capabilities on release 12.0 of Nokia SROS series systems."
    ::= { tmnxChassisV12v0Groups 15 }

tmnxChassisPowerNotifV12v0Group  NOTIFICATION-GROUP
    NOTIFICATIONS {
        tmnxPowerSupplyWrongFanDir,
        tmnxPowerSupplyWrongFanDirClear
    }
    STATUS      obsolete
    DESCRIPTION
        "The group of notifications supporting the management of power supply
         hardware capabilities on release 12.0 of Nokia SROS series systems."
    ::= { tmnxChassisV12v0Groups 16 }

tmnxMDAResetOnRecoverErGrp       OBJECT-GROUP
    OBJECTS     {
        tmnxMDAResetOnRecoverableError
    }
    STATUS      current
    DESCRIPTION
        "The tmnxMDAResetOnRecoverErGrp contains objects for the MDA reset on
         recoverable error capability on Nokia SROS series systems for release
         12.0."
    ::= { tmnxChassisV12v0Groups 17 }

tmnxCardResetOnRecoverErGrp      OBJECT-GROUP
    OBJECTS     {
        tmnxCardResetOnRecoverableError
    }
    STATUS      current
    DESCRIPTION
        "The tmnxCardResetOnRecoverErGrp contains objects for the card reset on
         recoverable error capability on Nokia SROS series systems for release
         12.0."
    ::= { tmnxChassisV12v0Groups 18 }

tmnxCpmMemSizeNotifGroupV12v0    NOTIFICATION-GROUP
    NOTIFICATIONS {
        tmnxCpmMemSizeMismatch,
        tmnxCpmMemSizeMismatchClear
    }
    STATUS      current
    DESCRIPTION
        "The group of notifications supporting CPM memory size mismatch in
         release 12.0 on Nokia SROS series systems."
    ::= { tmnxChassisV12v0Groups 19 }

tmnxCpmPChipFcsObjGroupV12v0     OBJECT-GROUP
    OBJECTS     {
        tmnxCpmCardCmplxIngrFcsOccur,
        tmnxCpmCardCmplxIngrFcsOccurTime,
        tmnxCpmCardCmplxEgrFcsOccur,
        tmnxCpmCardCmplxEgrFcsOccurTime,
        tmnxCpmCardCmplxEgrFcsSrcSlots
    }
    STATUS      current
    DESCRIPTION
        "The group of objects supporting CPM PChip management in release 12.0
         on Nokia SROS series systems."
    ::= { tmnxChassisV12v0Groups 20 }

tmnxChassisV13v0Groups           OBJECT IDENTIFIER ::= { tmnxChassisGroups 74 }

tmnxChassisResourceV13v0Group    OBJECT-GROUP
    OBJECTS     {
        tChassisResDynSvcNHEntryTotal,
        tChassisResDynSvcNHEntryAlloc,
        tChassisResIpSecNHEntryTotal,
        tChassisResIpSecNHEntryAlloc,
        tChassisResSubNHEntryTotal,
        tChassisResSubNHEntryAlloc,
        tChassisResSapIngQosPolTotal,
        tChassisResSapIngQosPolAlloc,
        tChassisResSapEgrQosPolTotal,
        tChassisResSapEgrQosPolAlloc,
        tChassisResIngQGrpTmplTotal,
        tChassisResIngQGrpTmplAlloc,
        tChassisResEgrQGrpTmplTotal,
        tChassisResEgrQGrpTmplAlloc,
        tChassisResPortEgrQGrpInstTotal,
        tChassisResPortEgrQGrpInstAlloc,
        tChassisResFPIngQGrpInstTotal,
        tChassisResFPIngQGrpInstAlloc,
        tChassisResPortEgrVPortTotal,
        tChassisResPortEgrVPortAlloc,
        tCardResQosUserSchedsTotal,
        tCardResQosUserSchedsAlloc,
        tCardResSubSPIQosOvrTotal,
        tCardResSubSPIQosOvrAlloc,
        tCardResHsmdaQOvrTotal,
        tCardResHsmdaQOvrAlloc,
        tCardResPortAccEgrQGrpInstTotal,
        tCardResPortAccEgrQGrpInstAlloc,
        tCardResPortNetEgrQGrpInstTotal,
        tCardResPortNetEgrQGrpInstAlloc,
        tCardResPortEgrQGrpInstTotal,
        tCardResPortEgrQGrpInstAlloc,
        tCardResFPIngQGrpInstTotal,
        tCardResFPIngQGrpInstAlloc,
        tCardResPortEgrVPortTotal,
        tCardResPortEgrVPortAlloc,
        tCardResCategoryEntriesTotal,
        tCardResCategoryEntriesAlloc,
        tFPResSapIngQosPolTotal,
        tFPResSapIngQosPolAlloc,
        tFPResDynEgrClassTotal,
        tFPResDynEgrClassAlloc,
        tFPResDynEgrClassIUBSE,
        tFPResDynEgrClassIUBNE,
        tFPResIngQueueTotal,
        tFPResIngQueueAlloc,
        tFPResEgrQueueTotal,
        tFPResEgrQueueAlloc,
        tFPResIngPolicerTotal,
        tFPResIngPolicerAlloc,
        tFPResEgrPolicerTotal,
        tFPResEgrPolicerAlloc,
        tFPResIngPolicerStatTotal,
        tFPResIngPolicerStatAlloc,
        tFPResEgrPolicerStatTotal,
        tFPResEgrPolicerStatAlloc,
        tFPResIngRootArbiterTotal,
        tFPResIngRootArbiterAlloc,
        tFPResEgrRootArbiterTotal,
        tFPResEgrRootArbiterAlloc,
        tFPResIntArbiterTotal,
        tFPResIntArbiterAlloc,
        tFPResDynQueueTotal,
        tFPResDynQueueAlloc,
        tFPResDynQueueIUBI,
        tFPResDynQueueIUBE,
        tFPResDynPolicerTotal,
        tFPResDynPolicerAlloc,
        tFPResDynPolicerIUBI,
        tFPResDynPolicerIUBE,
        tFPResDynPolicerStatTotal,
        tFPResDynPolicerStatAlloc,
        tFPResDynPolicerStatIUBI,
        tFPResDynPolicerStatIUBE,
        tFPResIngAclEntryTotal,
        tFPResIngAclEntryAlloc,
        tFPResIngQosEntryTotal,
        tFPResIngQosEntryAlloc,
        tFPResIngAclQosEntryTotal,
        tFPResIngAclQosEntryAlloc,
        tFPResIngIPv6AclEntryTotal,
        tFPResIngIPv6AclEntryAlloc,
        tFPResIngIPv6QosEntryTotal,
        tFPResIngIPv6QosEntryAlloc,
        tFPResEgrAclEntryTotal,
        tFPResEgrAclEntryAlloc,
        tFPResEgrQosEntryTotal,
        tFPResEgrQosEntryAlloc,
        tFPResEgrAclQosEntryTotal,
        tFPResEgrAclQosEntryAlloc,
        tFPResEgrIPv6AclEntryTotal,
        tFPResEgrIPv6AclEntryAlloc,
        tFPResEgrIPv6QosEntryTotal,
        tFPResEgrIPv6QosEntryAlloc,
        tFPResIngAclFilterTotal,
        tFPResIngAclFilterAlloc,
        tFPResEgrAclFilterTotal,
        tFPResEgrAclFilterAlloc,
        tFPResDynSvcEntryTotal,
        tFPResDynSvcEntryAlloc,
        tFPResSubHostTotal,
        tFPResSubHostAlloc,
        tFPResEncapGrpMemberTotal,
        tFPResEncapGrpMemberAlloc,
        tFPResEgrNetQGrpMapTotal,
        tFPResEgrNetQGrpMapAlloc,
        tFPResMacFdbRecTotal,
        tFPResMacFdbRecAlloc,
        tFPResResRvplsFdbRecTotal,
        tFPResResRvplsFdbRecAlloc,
        tFPResDynQ2NamedPoolTotal,
        tFPResDynQ2NamedPoolAlloc,
        tFPResDynQ2NamedPoolIUBI,
        tFPResDynQ2NamedPoolIUBE,
        tFPResIngQ1NamedPoolTotal,
        tFPResIngQ1NamedPoolAlloc,
        tFPResEgrQ1NamedPoolTotal,
        tFPResEgrQ1NamedPoolAlloc,
        tFPResDynQ2WredPoolTotal,
        tFPResDynQ2WredPoolAlloc,
        tMDAResEgrHsmdaQGrpTotal,
        tMDAResEgrHsmdaQGrpAlloc,
        tMDAResEgrHsmdaSecShaperTotal,
        tMDAResEgrHsmdaSecShaperAlloc,
        tFPResIngIPv6AclFilterTotal,
        tFPResIngIPv6AclFilterAlloc,
        tFPResEgrIPv6AclFilterTotal,
        tFPResEgrIPv6AclFilterAlloc
    }
    STATUS      obsolete
    DESCRIPTION
        "The group of objects supporting management of System Resource
         Information on release 13.0 of Nokia SROS series systems."
    ::= { tmnxChassisV13v0Groups 1 }

tmnxCardVirtualSchAdjV13v0Group  OBJECT-GROUP
    OBJECTS     {
        tmnxCardInternalSchedWghtMode
    }
    STATUS      current
    DESCRIPTION
        "The group of objects supporting management of enhancing IOM Card
         features on release 13.0 of Nokia SROS series systems."
    ::= { tmnxChassisV13v0Groups 2 }

tmnxPhysChassisV13v0Group        OBJECT-GROUP
    OBJECTS     {
        tmnxPhysChassisDescription
    }
    STATUS      current
    DESCRIPTION
        "The group of objects supporting management of physical chassis on
         release 13.0 of Nokia SROS series systems."
    ::= { tmnxChassisV13v0Groups 3 }

tChassisResObsoletedV13v0Group   OBJECT-GROUP
    OBJECTS     {
        tCardResQosIntSchedsTotal,
        tCardResQosIntSchedsAlloc
    }
    STATUS      current
    DESCRIPTION
        "The group of objects obsoleted in release 13.0 of Nokia SROS series
         systems."
    ::= { tmnxChassisV13v0Groups 4 }

tmnxChassisV13v0Group            OBJECT-GROUP
    OBJECTS     {
        tmnxChassisPortIdScheme
    }
    STATUS      current
    DESCRIPTION
        "The group of additional objects supporting the management of chassis
         capabilities on release 13.0 of Nokia SROS series systems."
    ::= { tmnxChassisV13v0Groups 5 }

tmnxChassisMgmtEthRedNtfV13v0Grp NOTIFICATION-GROUP
    NOTIFICATIONS {
        tmnxEqMgmtEthRedStandbyRaise,
        tmnxEqMgmtEthRedStandbyClear
    }
    STATUS      current
    DESCRIPTION
        "The group of notifications supporting management Ethernet redundancy
         in release 13.0 of Nokia SROS series systems."
    ::= { tmnxChassisV13v0Groups 6 }

tmnxChassisMgmtEthRedV13v0Grp    OBJECT-GROUP
    OBJECTS     {
        tmnxChassisMgmtEthRed,
        tmnxChassisMgmtEthRedRevertTime,
        tmnxChassisMgmtEthRedStandby
    }
    STATUS      current
    DESCRIPTION
        "The group of objects supporting management Ethernet redundancy in
         release 13.0 of Nokia SROS series systems."
    ::= { tmnxChassisV13v0Groups 7 }

tmnxChassisPowerMgmtGroupV13v0   OBJECT-GROUP
    OBJECTS     {
        tmnxChassisPEQInputPowerMode,
        tmnxPEQTypeNumInputFeed
    }
    STATUS      current
    DESCRIPTION
        "The group of additional objects supporting the management of power
         utilization capabilities on release 13.0 of Nokia SROS series systems."
    ::= { tmnxChassisV13v0Groups 8 }

tmnxChassisNotifV13v0Group       NOTIFICATION-GROUP
    NOTIFICATIONS {
        tmnxSyncIfTimBITS2048khzUnsup,
        tmnxSyncIfTimBITS2048khzUnsupClr,
        tmnxEqBpEpromFail,
        tmnxEqBpEpromFailClear,
        tmnxEqBpEpromWarning,
        tmnxEqBpEpromWarningClear
    }
    STATUS      current
    DESCRIPTION
        "The group of additional notifications supporting chassis management in
         release 13.0 on Nokia SROS series systems."
    ::= { tmnxChassisV13v0Groups 9 }

tmnxChassisNotifyObjsV13v0Grp    OBJECT-GROUP
    OBJECTS     {
        tmnxChassisNotifyDiskFullReason,
        tmnxChassisNotifyMgmtEthRedPort
    }
    STATUS      current
    DESCRIPTION
        "The group of accessible-for-notify objects supporting chassis
         management in release 13.0 of Nokia SROS series systems."
    ::= { tmnxChassisV13v0Groups 10 }

tmnxChassisFpResourceV13v0Group  OBJECT-GROUP
    OBJECTS     {
        tFPResEgrQosBypassTotal,
        tFPResEgrQosBypassAlloc
    }
    STATUS      current
    DESCRIPTION
        "The group of objects supporting management of System Resource
         Information on release 13.0 of Nokia SROS series systems."
    ::= { tmnxChassisV13v0Groups 11 }

tmnxFPV13v0Group                 OBJECT-GROUP
    OBJECTS     {
        tmnxFPInitExtractDropPrioMode
    }
    STATUS      current
    DESCRIPTION
        "The group of additional objects supporting management of the
         forwarding plane on release 13.0 of Nokia SROS series systems."
    ::= { tmnxChassisV13v0Groups 12 }

tmnxCpmCardV13v0Group            OBJECT-GROUP
    OBJECTS     {
        tmnxCpmCardUuid
    }
    STATUS      current
    DESCRIPTION
        "The group of additional objects supporting management of CPM cards on
         release 13.0 of Nokia SROS series systems."
    ::= { tmnxChassisV13v0Groups 13 }

tmnxChassisV10v0Groups           OBJECT IDENTIFIER ::= { tmnxChassisGroups 75 }

tmnxChassisHwEventGroupV10v0     OBJECT-GROUP
    OBJECTS     {
        tmnxMdaHwEventNumOccurrences,
        tmnxMdaHwEventLastOccurTime
    }
    STATUS      current
    DESCRIPTION
        "The group of additional objects supporting Hardware event detection
         and reporting in release 10.0 of Nokia SROS series systems."
    ::= { tmnxChassisV10v0Groups 1 }

tmnxChassisHwEventNotifyGrpV10v0 NOTIFICATION-GROUP
    NOTIFICATIONS {
        tmnxEqMdaIngrXplError
    }
    STATUS      current
    DESCRIPTION
        "The group of additional notification-types supporting Hardware event
         detection and reporting in release 10.0 of Nokia SROS series systems."
    ::= { tmnxChassisV10v0Groups 2 }

tmnxChassisV14v0Groups           OBJECT IDENTIFIER ::= { tmnxChassisGroups 76 }

tmnxSyncIfTimingV14v0Group       OBJECT-GROUP
    OBJECTS     {
        tmnxSyncIfTimingBITSOutQlMin,
        tSyncIfTimingAdmBITSOutQlMin,
        tmnxSyncIfTimingBITSOutSquelch,
        tSyncIfTimingAdmBITSOutSquelch,
        tmnxSyncIfTimingQlMin,
        tSyncIfTimingAdmQlMin,
        tmnxSyncIfTimingWaitToRestorTime,
        tSyncIfTimingAdmWaitToRestorTime,
        tSyncIfTimingAdmChangedMask
    }
    STATUS      current
    DESCRIPTION
        "The group of additional objects supporting the management of
         synchronous interface timing capabilities in release 14.0 of Nokia
         SROS series systems."
    ::= { tmnxChassisV14v0Groups 1 }

tmnxChassisResourceV14v0Group    OBJECT-GROUP
    OBJECTS     {
        tCardResQosUserSchedOvrsTotal,
        tCardResQosUserSchedOvrsAlloc,
        tCardResCategoryEntriesTotal,
        tCardResCategoryEntriesAlloc,
        tChassisResSapTotal,
        tChassisResSapAlloc,
        tFPResSapInstanceTotal,
        tFPResSapInstanceAlloc,
        tMDAResSapInstanceTotal,
        tMDAResSapInstanceAlloc
    }
    STATUS      current
    DESCRIPTION
        "The group of objects supporting management of System Resource
         Information on release 14.0 of Nokia SROS series systems."
    ::= { tmnxChassisV14v0Groups 2 }

tmnxCpmFlashV14v0Group           OBJECT-GROUP
    OBJECTS     {
        tmnxCpmFlashPercentageUsed
    }
    STATUS      current
    DESCRIPTION
        "The group of additional objects supporting the management of compact
         flash in release 14.0 of Nokia SROS series systems."
    ::= { tmnxChassisV14v0Groups 3 }

tmnxPhysChassisGroupV14v0        OBJECT-GROUP
    OBJECTS     {
        tmnxPhysChassisFanOperStatus,
        tmnxPhysChassisFanSpeed,
        tmnxPhysChassisFanRevision,
        tmnxPhysChassPowerSupACStatus,
        tmnxPhysChassPowerSupDCStatus,
        tmnxPhysChassPowerSupTempStatus,
        tmnxPhysChassPowerSupTempThrshld,
        tmnxPhysChassPowerSup1Status,
        tmnxPhysChassPowerSup2Status,
        tmnxPhysChassPowerSupAssignType,
        tmnxPhysChassPowerSupInputStatus,
        tmnxPhysChassPowerSupOutptStatus,
        tmnxPhysChassPowerSupPemType,
        tmnxPhysChassPowerSupPemACRect,
        tmnxPhysChassPowerSupInFeedDown,
        tmnxPhysChassPowerSupFanDir
    }
    STATUS      current
    DESCRIPTION
        "The group of objects supporting management of physical chassis in
         release 14.0 of Nokia SROS series systems."
    ::= { tmnxChassisV14v0Groups 4 }

tFPFwdEngStatsGroup              OBJECT-GROUP
    OBJECTS     {
        tFwdEngDREgrEncapExceeded
    }
    STATUS      current
    DESCRIPTION
        "The group of objects supporting management of forward engine drop
         statictics on forwadring plane for release 14.0 on Nokia SROS series
         systems."
    ::= { tmnxChassisV14v0Groups 5 }

tmnxPhysChassisNotifGroupV14v0   NOTIFICATION-GROUP
    NOTIFICATIONS {
        tmnxEqPhysChassPowerSupOvrTmp,
        tmnxEqPhysChassPowerSupOvrTmpClr,
        tmnxEqPhysChassPowerSupAcFail,
        tmnxEqPhysChassPowerSupAcFailClr,
        tmnxEqPhysChassPowerSupDcFail,
        tmnxEqPhysChassPowerSupDcFailClr,
        tmnxEqPhysChassPowerSupInFail,
        tmnxEqPhysChassPowerSupInFailClr,
        tmnxEqPhysChassPowerSupOutFail,
        tmnxEqPhysChassPowerSupOutFailCl,
        tmnxEqPhysChassisFanFailure,
        tmnxEqPhysChassisFanFailureClear
    }
    STATUS      current
    DESCRIPTION
        "The group of notifications supporting physical chassis management in
         release 14.0 on Nokia SROS series systems."
    ::= { tmnxChassisV14v0Groups 6 }

tmnxIsaMemWMarkNotifGroupV14v0   NOTIFICATION-GROUP
    NOTIFICATIONS {
        tIPsecIsaMemLowWatermark,
        tIPsecIsaMemHighWatermark,
        tIPsecIsaMemMax
    }
    STATUS      current
    DESCRIPTION
        "The group of notifications supporting ISA card memory watermarks in
         release 14.0 on Nokia SROS series systems."
    ::= { tmnxChassisV14v0Groups 7 }

tmnxIsaGrpIsaScaleModeGroupV14v0 OBJECT-GROUP
    OBJECTS     {
        tmnxIPsecIsaGrpIsaScaleMode
    }
    STATUS      current
    DESCRIPTION
        "The group of objects supporting ISA scale mode in release 14.0 on
         Nokia SROS series systems."
    ::= { tmnxChassisV14v0Groups 9 }

tmnxCardVirtualGroupV14v0        OBJECT-GROUP
    OBJECTS     {
        tmnxCardVFpCpuCount,
        tmnxCardVFpAvgUtilization,
        tmnxCardVFpMaxUtilization,
        tmnxCardVCpuSchedHealth,
        tmnxCardVCpuSchedLastClearedTime
    }
    STATUS      current
    DESCRIPTION
        "The group of objects supporting management of virtual card statistics
         for release 14.0 on Nokia SROS series systems."
    ::= { tmnxChassisV14v0Groups 10 }

tmnxChassisV15v0Groups           OBJECT IDENTIFIER ::= { tmnxChassisGroups 77 }

tmnxCardFPEgrHsGroup             OBJECT-GROUP
    OBJECTS     {
        tmnxFPEgrHsPoolPolicy,
        tFPResEgrHsQGrpTotal,
        tFPResEgrHsQGrpAlloc,
        tFPResEgrHsPrimaryShapersTotal,
        tFPResEgrHsPrimaryShapersAlloc,
        tFPResEgrHsPrimaryShapersIUBES,
        tFPResEgrHsPrimaryShapersIUBMS,
        tFPResEgrHsSecondaryShapersTotal,
        tFPResEgrHsSecondaryShapersAlloc,
        tmnxFPEgrHsFixedHighThreshDelta,
        tFPResEgrHsTurboQGrpTotal,
        tFPResEgrHsTurboQGrpAlloc
    }
    STATUS      current
    DESCRIPTION
        "The group of objects supporting egress High Scale related objects on
         Nokia SROS series system."
    ::= { tmnxChassisV15v0Groups 1 }

tmnxChassisObsoletedV15v0Group   OBJECT-GROUP
    OBJECTS     {
        tmnxMDAHiBwMcastSource,
        tmnxMDAHiBwMcastAlarm,
        tmnxMDAHiBwMcastTapCount,
        tmnxMDAHiBwMcastGroup,
        tmnxMDAMcPathMgmtBwPlcyName,
        tmnxMDAMcPathMgmtPriPathLimit,
        tmnxMDAMcPathMgmtSecPathLimit,
        tmnxMDAMcPathMgmtAncPathLimit,
        tmnxMDAMcPathMgmtAdminState,
        tmnxMDAMcPathMgmtPriInUseBw,
        tmnxMDAMcPathMgmtSecInUseBw,
        tmnxMDAMcPathMgmtAncInUseBw,
        tmnxMDAMcPathMgmtBlkHoleInUseBw,
        tmnxPhysChassisFanSpeed,
        tmnxChassisFanOperStatus,
        tmnxChassisFanSpeed,
        tmnxChassisFanRevision,
        tmnxChassisFanSpeedPercent,
        tmnxChassisPowerSupplyACStatus,
        tmnxChassisPowerSupplyDCStatus,
        tmnxChassisPowerSupplyTempStatus,
        tmnxChassisPowerSupplyTempThreshold,
        tmnxChassisPowerSupply1Status,
        tmnxChassisPowerSupply2Status,
        tmnxChassisPowerSupplyAssignedType,
        tmnxChassisPowerSupplyInputStatus,
        tmnxChassisPowerSupplyOutputStatus,
        tmnxChassisPowerSupplyPemType,
        tmnxChassisPowerSupplyPemACRect,
        tmnxChassisPowerSupplyInFeedDown,
        tmnxChassisPowerSupplyFanDir,
        tmnxChassisPEQTableLastChg,
        tmnxChassisPEQLastChangedTime,
        tmnxChassisPEQAssignedType,
        tmnxChassisPEQEquippedType,
        tmnxChassisPEQSupportedTypes,
        tmnxChassisPEQAvailableWattage,
        tmnxChassisPEQInputPowerMode
    }
    STATUS      current
    DESCRIPTION
        "The group of chassis objects obsoleted in release 15.0 of Nokia SROS
         series systems."
    ::= { tmnxChassisV15v0Groups 2 }

tmnxChassisFanV15v0Group         OBJECT-GROUP
    OBJECTS     {
        tmnxChassisFanSpeedPercent,
        tmnxPhysChassisFanSpeedPercent
    }
    STATUS      current
    DESCRIPTION
        "The group of objects supporting fans in release 15.0 of Nokia SROS
         series systems."
    ::= { tmnxChassisV15v0Groups 3 }

tmnxPhysChassisGroupV15v0        OBJECT-GROUP
    OBJECTS     {
        tmnxPhysChassisPEQTableLastChg,
        tmnxPhysChassisPEQLastChangeTime,
        tmnxPhysChassisPEQAssignedType,
        tmnxPhysChassisPEQEquippedType,
        tmnxPhysChassisPEQSupportedTypes,
        tmnxPhysChassisPEQAvailableWatt,
        tmnxPhysChassisPEQInputPowerMode
    }
    STATUS      current
    DESCRIPTION
        "The group of objects supporting management of physical chassis in
         release 15.0 of Nokia SROS series systems."
    ::= { tmnxChassisV15v0Groups 4 }

tmnxPhysChassisNotifGroupV15v0   NOTIFICATION-GROUP
    NOTIFICATIONS {
        tmnxPhysChassPwrSupWrgFanDir,
        tmnxPhysChassPwrSupWrgFanDirClr,
        tmnxPhysChassPwrSupPemACRect,
        tmnxPhysChassPwrSupPemACRectClr,
        tmnxPhysChassPwrSupInputFeed,
        tmnxPhysChassPwrSupInputFeedClr
    }
    STATUS      current
    DESCRIPTION
        "The group of additional notifications supporting management of
         physical chassis in release 15.0 of Nokia SROS series systems."
    ::= { tmnxChassisV15v0Groups 5 }

tmnxIcmpMtuExceededStatGroup     OBJECT-GROUP
    OBJECTS     {
        tFwdEngDREgrMtuExceeded
    }
    STATUS      current
    DESCRIPTION
        "The group of objects supporting management of physical chassis in
         release 15.0 of Nokia SROS series systems."
    ::= { tmnxChassisV15v0Groups 6 }

tmnxChassisGroupV15v0            OBJECT-GROUP
    OBJECTS     {
        tmnxChassisVsrCongestionMgmt,
        tmnxChassisAlarmLEDState
    }
    STATUS      current
    DESCRIPTION
        "The group of objects supporting management of chassis in release 15.0
         of Nokia SROS series systems."
    ::= { tmnxChassisV15v0Groups 7 }

tmnxChassNotifsObsoletedGrpV15v0 NOTIFICATION-GROUP
    NOTIFICATIONS {
        tmnxEqFanFailure,
        tmnxEqPowerSupplyFailure,
        tmnxEqPowerSupplyInputFeedAlm,
        tmnxEqPowerSupplyInputFeedAlmClr,
        tmnxEqPowerSupplyPemACRectAlm,
        tmnxEqPowerSupplyPemACRectAlmClr,
        tmnxPowerSupplyWrongFanDir,
        tmnxPowerSupplyWrongFanDirClear
    }
    STATUS      current
    DESCRIPTION
        "The group of notifications supporting the management of chassis
         hardware made obsolete in release 15.0 on Nokia SROS series systems."
    ::= { tmnxChassisV15v0Groups 8 }

tmnxCardResMacFdbUsgNotifGroup   NOTIFICATION-GROUP
    NOTIFICATIONS {
        tmnxCardResMacFdbHighUsgSet,
        tmnxCardResMacFdbHighUsgClr
    }
    STATUS      current
    DESCRIPTION
        "The group notifications supporting  MAC scale feature on Nokia SROS
         series systems release 15.0."
    ::= { tmnxChassisV15v0Groups 9 }

tmnxMacScaleNotifyObjsV15v0Grp   OBJECT-GROUP
    OBJECTS     {
        tmnxMacScaleCardSlotNum
    }
    STATUS      current
    DESCRIPTION
        "The group of accessible-for-notify objects supporting MAC scale
         feature in release 15.0 of Nokia SROS series systems."
    ::= { tmnxChassisV15v0Groups 10 }

tmnxMDAV15v0Group                OBJECT-GROUP
    OBJECTS     {
        tmnxMDASupportedTypes,
        tmnxMDAAssignedType,
        tmnxMDAEquippedType,
        tmnxMDAHwIndex,
        tmnxMDAMaxPorts,
        tmnxMDAEquippedPorts,
        tmnxMDATxTimingSelected,
        tmnxMDASyncIfTimingStatus,
        tmnxMDANetworkIngQueues,
        tmnxMDACapabilities,
        tmnxMDAMinChannelization,
        tmnxMDAMaxChannelization,
        tmnxMDAMaxChannels,
        tmnxMDAChannelsInUse,
        tmnxMdaTypeName,
        tmnxMdaTypeDescription,
        tmnxMdaTypeStatus,
        tmnxMDAReboot,
        tmnxMDASynchronousEthernet,
        tmnxMDAEgrHsmdaThrshLoBrstMult,
        tmnxMDAEgrHsmdaThrshHiBrstInc,
        tmnxMDAIsaTunnelGroup,
        tmnxIPsecIsaGrpIPsecRespondOnly,
        tmnxIPsecIsaGrpMultiActive,
        tmnxIPsecIsaGrpActiveMda,
        tmnxMDAIsaTunnelGroupInUse,
        tmnxMDAFailOnError,
        tmnxMDAEgrXplErrThreshold,
        tmnxMDAEgrXplErrWindow,
        tmnxMDAIngrXplErrThreshold,
        tmnxMDAIngrXplErrWindow
    }
    STATUS      current
    DESCRIPTION
        "The group of objects supporting management of MDAs for release 15.0 on
         Nokia SROS series systems."
    ::= { tmnxChassisV15v0Groups 11 }

tmnxFPMcPathMgmtV15v0Group       OBJECT-GROUP
    OBJECTS     {
        tmnxFPMcPathMgmtPriInUseBw,
        tmnxFPMcPathMgmtSecInUseBw,
        tmnxFPMcPathMgmtBlkHoleInUseBw
    }
    STATUS      current
    DESCRIPTION
        "The group of additional objects supporting management of the
         forwarding plane on release 15.0 of Nokia SROS series systems."
    ::= { tmnxChassisV15v0Groups 12 }

tmnxChassisResourceV15v0Group    OBJECT-GROUP
    OBJECTS     {
        tChassisResDynSvcNHEntryTotal,
        tChassisResDynSvcNHEntryAlloc,
        tChassisResIpSecNHEntryTotal,
        tChassisResIpSecNHEntryAlloc,
        tChassisResSubNHEntryTotal,
        tChassisResSubNHEntryAlloc,
        tChassisResSapIngQosPolTotal,
        tChassisResSapIngQosPolAlloc,
        tChassisResSapEgrQosPolTotal,
        tChassisResSapEgrQosPolAlloc,
        tChassisResIngQGrpTmplTotal,
        tChassisResIngQGrpTmplAlloc,
        tChassisResEgrQGrpTmplTotal,
        tChassisResEgrQGrpTmplAlloc,
        tChassisResPortEgrQGrpInstTotal,
        tChassisResPortEgrQGrpInstAlloc,
        tChassisResFPIngQGrpInstTotal,
        tChassisResFPIngQGrpInstAlloc,
        tChassisResPortEgrVPortTotal,
        tChassisResPortEgrVPortAlloc,
        tCardResQosUserSchedsTotal,
        tCardResQosUserSchedsAlloc,
        tCardResSubSPIQosOvrTotal,
        tCardResSubSPIQosOvrAlloc,
        tCardResHsmdaQOvrTotal,
        tCardResHsmdaQOvrAlloc,
        tCardResPortAccEgrQGrpInstTotal,
        tCardResPortAccEgrQGrpInstAlloc,
        tCardResPortNetEgrQGrpInstTotal,
        tCardResPortNetEgrQGrpInstAlloc,
        tCardResPortEgrQGrpInstTotal,
        tCardResPortEgrQGrpInstAlloc,
        tCardResFPIngQGrpInstTotal,
        tCardResFPIngQGrpInstAlloc,
        tCardResPortEgrVPortTotal,
        tCardResPortEgrVPortAlloc,
        tCardResCategoryEntriesTotal,
        tCardResCategoryEntriesAlloc,
        tFPResSapIngQosPolTotal,
        tFPResSapIngQosPolAlloc,
        tFPResDynEgrClassTotal,
        tFPResDynEgrClassAlloc,
        tFPResDynEgrClassIUBSE,
        tFPResDynEgrClassIUBNE,
        tFPResIngQueueTotal,
        tFPResIngQueueAlloc,
        tFPResEgrQueueTotal,
        tFPResEgrQueueAlloc,
        tFPResIngPolicerTotal,
        tFPResIngPolicerAlloc,
        tFPResEgrPolicerTotal,
        tFPResEgrPolicerAlloc,
        tFPResIngPolicerStatTotal,
        tFPResIngPolicerStatAlloc,
        tFPResEgrPolicerStatTotal,
        tFPResEgrPolicerStatAlloc,
        tFPResIngRootArbiterTotal,
        tFPResIngRootArbiterAlloc,
        tFPResEgrRootArbiterTotal,
        tFPResEgrRootArbiterAlloc,
        tFPResIntArbiterTotal,
        tFPResIntArbiterAlloc,
        tFPResDynQueueTotal,
        tFPResDynQueueAlloc,
        tFPResDynQueueIUBI,
        tFPResDynQueueIUBE,
        tFPResDynPolicerTotal,
        tFPResDynPolicerAlloc,
        tFPResDynPolicerIUBI,
        tFPResDynPolicerIUBE,
        tFPResDynPolicerStatTotal,
        tFPResDynPolicerStatAlloc,
        tFPResDynPolicerStatIUBI,
        tFPResDynPolicerStatIUBE,
        tFPResIngAclEntryTotal,
        tFPResIngAclEntryAlloc,
        tFPResIngQosEntryTotal,
        tFPResIngQosEntryAlloc,
        tFPResIngAclQosEntryTotal,
        tFPResIngAclQosEntryAlloc,
        tFPResIngIPv6AclEntryTotal,
        tFPResIngIPv6AclEntryAlloc,
        tFPResIngIPv6QosEntryTotal,
        tFPResIngIPv6QosEntryAlloc,
        tFPResEgrAclEntryTotal,
        tFPResEgrAclEntryAlloc,
        tFPResEgrQosEntryTotal,
        tFPResEgrQosEntryAlloc,
        tFPResEgrAclQosEntryTotal,
        tFPResEgrAclQosEntryAlloc,
        tFPResEgrIPv6AclEntryTotal,
        tFPResEgrIPv6AclEntryAlloc,
        tFPResEgrIPv6QosEntryTotal,
        tFPResEgrIPv6QosEntryAlloc,
        tFPResIngAclFilterTotal,
        tFPResIngAclFilterAlloc,
        tFPResEgrAclFilterTotal,
        tFPResEgrAclFilterAlloc,
        tFPResDynSvcEntryTotal,
        tFPResDynSvcEntryAlloc,
        tFPResSubHostTotal,
        tFPResSubHostAlloc,
        tFPResEncapGrpMemberTotal,
        tFPResEncapGrpMemberAlloc,
        tFPResEgrNetQGrpMapTotal,
        tFPResEgrNetQGrpMapAlloc,
        tFPResMacFdbRecTotal,
        tFPResMacFdbRecAlloc,
        tFPResDynQ2NamedPoolTotal,
        tFPResDynQ2NamedPoolAlloc,
        tFPResDynQ2NamedPoolIUBI,
        tFPResDynQ2NamedPoolIUBE,
        tFPResIngQ1NamedPoolTotal,
        tFPResIngQ1NamedPoolAlloc,
        tFPResEgrQ1NamedPoolTotal,
        tFPResEgrQ1NamedPoolAlloc,
        tFPResDynQ2WredPoolTotal,
        tFPResDynQ2WredPoolAlloc,
        tMDAResEgrHsmdaQGrpTotal,
        tMDAResEgrHsmdaQGrpAlloc,
        tMDAResEgrHsmdaSecShaperTotal,
        tMDAResEgrHsmdaSecShaperAlloc,
        tFPResIngIPv6AclFilterTotal,
        tFPResIngIPv6AclFilterAlloc,
        tFPResEgrIPv6AclFilterTotal,
        tFPResEgrIPv6AclFilterAlloc
    }
    STATUS      current
    DESCRIPTION
        "The group of objects supporting management of System Resource
         Information on release 15.0 of Nokia SROS series systems."
    ::= { tmnxChassisV15v0Groups 13 }

tmnxChassisResrcObsoletedGroup   OBJECT-GROUP
    OBJECTS     {
        tFPResResRvplsFdbRecTotal,
        tFPResResRvplsFdbRecAlloc
    }
    STATUS      current
    DESCRIPTION
        "The group of obsoleted objects supporting management of System
         Resource Information on release 15.0 of Nokia SROS series systems."
    ::= { tmnxChassisV15v0Groups 14 }

tmnxCardFPResIngV15v0QGroup      OBJECT-GROUP
    OBJECTS     {
        tFPResIngQGrpRedirTotal,
        tFPResIngQGrpRedirAlloc
    }
    STATUS      current
    DESCRIPTION
        "The group of objects supporting ingress queue group related objects on
         Nokia SROS series system."
    ::= { tmnxChassisV15v0Groups 15 }

tmnxCardFPResEgrV15v0QGroup      OBJECT-GROUP
    OBJECTS     {
        tFPResSapInstEgrQGrpRedirTotal,
        tFPResSapInstEgrQGrpRedirAlloc
    }
    STATUS      current
    DESCRIPTION
        "The group of objects supporting egress queue group related objects on
         Nokia SROS series system."
    ::= { tmnxChassisV15v0Groups 16 }

tmnxMinFpGenerationGroupV15v0    OBJECT-GROUP
    OBJECTS     {
        tmnxFPGeneration,
        tmnxChassisFPGenerationFP2,
        tmnxChassisFPGenerationFP3,
        tmnxChassisFPGenerationFP4
    }
    STATUS      current
    DESCRIPTION
        "The group of objects supporting minimum Forwarding Plane (FP) network
         processor generation requirements in release 15.0 on Noka SROS series
         systems."
    ::= { tmnxChassisV15v0Groups 19 }

tmnxChassisDCCompliances         OBJECT IDENTIFIER ::= { tmnxChassisConformance 3 }

tmnxChassisDCGroups              OBJECT IDENTIFIER ::= { tmnxChassisConformance 4 }

tmnxHwNotification               OBJECT IDENTIFIER ::= { tmnxSRNotifyPrefix 2 }

tmnxChassisNotifyPrefix          OBJECT IDENTIFIER ::= { tmnxHwNotification 1 }

tmnxChassisNotification          OBJECT IDENTIFIER ::= { tmnxChassisNotifyPrefix 0 }

tmnxHwConfigChange               NOTIFICATION-TYPE
    OBJECTS     {
        tmnxChassisNotifyHwIndex,
        tmnxHwID,
        tmnxHwClass
    }
    STATUS      obsolete
    DESCRIPTION
        "A tmnxHwConfigChange notification is generated when the value of
         tmnxHwLastChange is updated.  It can be used by the NMS to trigger
         maintenance polls of the hardware configuration information.

         Only one tmnxHwConfigChange notification event will be generated
         in a 5 second throttling time period.  A notification event is
         the transmission of a single trap to a list of notification
         destinations configured in the SNMP-TARGET-MIB.

         If additional hardware configuration change occurs within the
         throttling period, the notification events for these changes are
         suppressed until the throttling period expires.  At the end of
         the throttling period, one notification event is generated if
         any addition configuration changes occurred within the just
         completed throttling period and another throttling period is
         started.

         The NMS should periodically check the value of tmnxHwConfigChange to
         detect any missed tmnxHwConfigChange traps.

         This notification was made obsolete in the 2.1 release.

         The tmnxHwConfigChange notification has been replaced with the generic
         change notifications from the TIMETRA-SYSTEM-MIB: tmnxConfigModify,
         tmnxConfigCreate, tmnxConfigDelete, tmnxStateChange."
    ::= { tmnxChassisNotification 1 }

tmnxEnvTempTooHigh               NOTIFICATION-TYPE
    OBJECTS     {
        tmnxChassisNotifyHwIndex,
        tmnxHwID,
        tmnxHwClass,
        tmnxHwTemperature,
        tmnxHwTempThreshold
    }
    STATUS      current
    DESCRIPTION
        "Generated when the temperature sensor reading on an equipment object
         is greater than its configured threshold."
    ::= { tmnxChassisNotification 2 }

tmnxEqPowerSupplyFailure         NOTIFICATION-TYPE
    OBJECTS     {
        tmnxChassisNotifyHwIndex,
        tmnxHwID,
        tmnxHwClass,
        tmnxChassisPowerSupplyACStatus,
        tmnxChassisPowerSupplyDCStatus,
        tmnxChassisPowerSupplyTempStatus,
        tmnxChassisPowerSupplyTempThreshold,
        tmnxChassisPowerSupply1Status,
        tmnxChassisPowerSupply2Status,
        tmnxChassisPowerSupplyInputStatus,
        tmnxChassisPowerSupplyOutputStatus
    }
    STATUS      obsolete
    DESCRIPTION
        "Generated when one of the chassis's power supplies fails.

         This notification was made obsolete in release 15.0."
    ::= { tmnxChassisNotification 3 }

tmnxEqPowerSupplyInserted        NOTIFICATION-TYPE
    OBJECTS     {
        tmnxChassisNotifyHwIndex,
        tmnxHwID,
        tmnxHwClass
    }
    STATUS      current
    DESCRIPTION
        "Generated when one of the chassis's power supplies is inserted."
    ::= { tmnxChassisNotification 4 }

tmnxEqPowerSupplyRemoved         NOTIFICATION-TYPE
    OBJECTS     {
        tmnxChassisNotifyHwIndex,
        tmnxHwID,
        tmnxHwClass
    }
    STATUS      current
    DESCRIPTION
        "[CAUSE] The tmnxEqPowerSupplyRemoved notification is generated when
         one of the power supplies is removed from the chassis or low input
         voltage is detected. The operating voltage range for the 7750 SR-7 and
         7750 SR-12 is -40 to -72 VDC. The notification is generated if the
         system detects that the voltage of the power supply has dropped to
         -42.5 VDC.

         [EFFECT] Reduced power can cause intermittent errors and could also
         cause permanent damage to components.

         [RECOVERY] Re-insert the power supply or raise the input voltage above
         -42.5 VDC."
    ::= { tmnxChassisNotification 5 }

tmnxEqFanFailure                 NOTIFICATION-TYPE
    OBJECTS     {
        tmnxChassisNotifyHwIndex,
        tmnxHwID,
        tmnxHwClass,
        tmnxChassisFanOperStatus,
        tmnxChassisFanSpeedPercent
    }
    STATUS      obsolete
    DESCRIPTION
        "Generated when one of the fans in a fan tray has failed.

         This notification was made obsolete in release 15.0."
    ::= { tmnxChassisNotification 6 }

tmnxEqCardFailure                NOTIFICATION-TYPE
    OBJECTS     {
        tmnxChassisNotifyHwIndex,
        tmnxHwID,
        tmnxHwClass,
        tmnxHwOperState,
        tmnxChassisNotifyCardFailureReason
    }
    STATUS      current
    DESCRIPTION
        "Generated when one of the cards in a chassis has failed.  The card
         type may be IOM, Fabric, MDA, MCM, CCM, CPM module, compact flash
         module, etc. tmnxChassisNotifyCardFailureReason contains the reason
         for card failure."
    ::= { tmnxChassisNotification 7 }

tmnxEqCardInserted               NOTIFICATION-TYPE
    OBJECTS     {
        tmnxChassisNotifyHwIndex,
        tmnxHwID,
        tmnxHwClass,
        tmnxChassisNotifyCardName
    }
    STATUS      current
    DESCRIPTION
        "Generated when a card is inserted into the chassis.  The card type
         may be IOM, Fabric, MDA, MCM, CCM CPM module, compact flash module,
         etc."
    ::= { tmnxChassisNotification 8 }

tmnxEqCardRemoved                NOTIFICATION-TYPE
    OBJECTS     {
        tmnxChassisNotifyHwIndex,
        tmnxHwID,
        tmnxHwClass,
        tmnxChassisNotifyCardName
    }
    STATUS      current
    DESCRIPTION
        "Generated when a card is removed from the chassis.  The card type
         may be IOM, Fabric, MDA, MCM, CCM, CPM module, compact flash module,
         etc."
    ::= { tmnxChassisNotification 9 }

tmnxEqWrongCard                  NOTIFICATION-TYPE
    OBJECTS     {
        tmnxChassisNotifyHwIndex,
        tmnxHwID,
        tmnxHwClass
    }
    STATUS      current
    DESCRIPTION
        "Generated when the wrong type of card is inserted into a slot of
         the chassis.  Even though a card may be physically supported by
         the slot, it may have been administratively configured to allow
         only certain card types in a particular slot location.  The card
         type may be IOM, Fabric, MDA, MCM, CPM module, etc."
    ::= { tmnxChassisNotification 10 }

tmnxEqCpuFailure                 NOTIFICATION-TYPE
    OBJECTS     {
        tmnxChassisNotifyHwIndex,
        tmnxHwID,
        tmnxHwClass
    }
    STATUS      obsolete
    DESCRIPTION
        "Generated when a failure is detected for a CPU on an IOM card or CPM
         module.

         This notification was made obsolete in the 2.1 release.

         A cpu failure on a CPM card is detected by the hardware bootup and is
         indicated by the boot diagnostic display. If there is no working
         redundant CPM card, the system does not come up.

         A failure of an IOM card or standby redundant CPM card causes the
         tmnxEqCardFailure notification to be sent."
    ::= { tmnxChassisNotification 11 }

tmnxEqMemoryFailure              NOTIFICATION-TYPE
    OBJECTS     {
        tmnxChassisNotifyHwIndex,
        tmnxHwID,
        tmnxHwClass
    }
    STATUS      obsolete
    DESCRIPTION
        "Generated when a memory module failure is detected for an IOM card or
         CPM module.

         This notification was made obsolete in the 2.1 release.

         A failure of the memory device is detected by the
         hardware bootup and is indicated by the boot diagnostic
         display.  If there is no working redundant CPM card,
         the system does not come up.

         A failure of the memory device during run-time causes the system to
         fail and the 'admin tech-support' information to be saved.

         A failure of an IOM card or standby redundant CPM card causes the
         tmnxEqCardFailure notification to be sent."
    ::= { tmnxChassisNotification 12 }

tmnxEqBackdoorBusFailure         NOTIFICATION-TYPE
    OBJECTS     {
        tmnxChassisNotifyChassisId
    }
    STATUS      obsolete
    DESCRIPTION
        "Generated when the backdoor bus has failed.

         This notification was made obsolete in the 2.1 release."
    ::= { tmnxChassisNotification 13 }

tmnxPeSoftwareError              NOTIFICATION-TYPE
    OBJECTS     {
        tmnxChassisNotifyHwIndex,
        tmnxHwID,
        tmnxHwClass
    }
    STATUS      obsolete
    DESCRIPTION
        "Generated when a software error has been detected.

         This notification was made obsolete in the 2.1 release.

         Many of the other notifications more specifically indicate detection
         of some type of software error.

         The 'admin tech-support' information helps developers diagnose a
         failure of the software in the field."
    ::= { tmnxChassisNotification 14 }

tmnxPeSoftwareAbnormalHalt       NOTIFICATION-TYPE
    OBJECTS     {
        tmnxChassisNotifyHwIndex,
        tmnxHwID,
        tmnxHwClass
    }
    STATUS      obsolete
    DESCRIPTION
        "Generated when the software has abnormally terminated.

         This notification was made obsolete in the 2.1 release.

          Many of the other notifications more specifically
          indicate detection of some type of software error.

          The 'admin tech-support' information helps developers
          diagnose a failure of the software in the field."
    ::= { tmnxChassisNotification 15 }

tmnxPeSoftwareVersionMismatch    NOTIFICATION-TYPE
    OBJECTS     {
        tmnxChassisNotifyHwIndex,
        tmnxHwID,
        tmnxHwClass,
        tmnxChassisNotifyMismatchedVer,
        tmnxHwSoftwareCodeVersion
    }
    STATUS      current
    DESCRIPTION
        "Generated when there is a mismatch between software versions of the
         active CPM and standby CPM or the CPM and IOM.
         tmnxChassisNotifyHwIndex identifies the mismatched CPM/IOM card and
         tmnxChassisNotifyMismatchedVer will contain the version of the
         mismatched card. The tmnxHwSoftwareCodeVersion object will contain the
         expected version."
    ::= { tmnxChassisNotification 16 }

tmnxPeOutOfMemory                NOTIFICATION-TYPE
    OBJECTS     {
        tmnxChassisNotifyHwIndex,
        tmnxHwID,
        tmnxHwClass
    }
    STATUS      obsolete
    DESCRIPTION
        "Generated when there is an out of memory error detected.

         This notification was made obsolete in the 2.1 release.

         The tmnxPeOutOfMemory notification has been replaced with the module
         specific notification from the TIMETRA-SYSTEM-MIB:
         tmnxModuleMallocFailed."
    ::= { tmnxChassisNotification 17 }

tmnxPeConfigurationError         NOTIFICATION-TYPE
    OBJECTS     {
        tmnxChassisNotifyHwIndex,
        tmnxHwID,
        tmnxHwClass
    }
    STATUS      obsolete
    DESCRIPTION
        "Generated when a configuration error has been detected.

         This notification was made obsolete in the 2.1 release.

         Many other notifications more specifically indicate
         detection of a configuration error.  In most cases the
         SNMP SET request that tries to make an invalid
         configuration results in an error response.

         In some cases the configuration parameters are valid
         and the SNMP SET request succeeds but the system cannot
         successfully apply the new parameters.  The affected
         object may then put into an operational 'down' state.
         A state change notification such as tmnxStateChange or
         a more specific notification is sent to alert about the
         problem.

         For example, an attempt to create an event log with a file-type
         destination when the specified cflash media is full or not present
         results in TIMETRA-LOG-MIB notifications tmnxLogSpaceContention,
         tmnxLogAdminLocFailed, or tmnxLogBackupLocFailed."
    ::= { tmnxChassisNotification 18 }

tmnxPeStorageProblem             NOTIFICATION-TYPE
    OBJECTS     {
        tmnxChassisNotifyHwIndex,
        tmnxHwID,
        tmnxHwClass
    }
    STATUS      obsolete
    DESCRIPTION
        "Generated when there is a storage capacity problem.

         This notification was made obsolete in the 2.1 release.

         The only 'storage' devices on the SR7750 are the cflash
         drives.  Cflash write errors cause a tmnxEqFlashDataLoss
         notification to be sent.  The tmnxEqFlashDiskFull
         notification is sent when the driver detects that the
         cflash device is full."
    ::= { tmnxChassisNotification 19 }

tmnxPeCpuCyclesExceeded          NOTIFICATION-TYPE
    OBJECTS     {
        tmnxChassisNotifyHwIndex,
        tmnxHwID,
        tmnxHwClass
    }
    STATUS      obsolete
    DESCRIPTION
        "Generated when the CPU cycle usage limit has been exceeded.

         This notification was made obsolete in the 2.1 release.

         It does not apply. The SR7750 software architecture does not restrict
         CPU cycles used by a specific code module."
    ::= { tmnxChassisNotification 20 }

tmnxRedPrimaryCPMFail            NOTIFICATION-TYPE
    OBJECTS     {
        tmnxChassisNotifyHwIndex,
        tmnxHwID,
        tmnxHwClass
    }
    STATUS      current
    DESCRIPTION
        "Generated when the primary CPM fails."
    ::= { tmnxChassisNotification 21 }

tmnxRedSecondaryCPMStatusChange  NOTIFICATION-TYPE
    OBJECTS     {
        tmnxChassisNotifyHwIndex,
        tmnxHwID,
        tmnxHwClass,
        tmnxRedSecondaryCPMStatus
    }
    STATUS      obsolete
    DESCRIPTION
        "Generated when there is a change in the secondary CPM status.

         This notification was made obsolete in the 2.1 release.

         There is no way to administratively enable or disable CPM cards so
         there is no need for a status change event for administrative state
         changes.

         Operational changes detected about the standby CPM card are indicated
         by more specific notifications such as tmnxEqCardFailure,
         tmnxEqCardRemoved, tmnxEqCardInserted
         TIMETRA-SYSTEM-MIB::ssiRedStandbyReady,
         TIMETRA-SYSTEM-MIB::ssiRedStandbySyncLost, and
         TIMETRA-SYSTEM-MIB::ssiRedStandbySyncLost."
    ::= { tmnxChassisNotification 22 }

tmnxRedRestoreSuccess            NOTIFICATION-TYPE
    OBJECTS     {
        tmnxChassisNotifyHwIndex,
        tmnxHwID,
        tmnxHwClass
    }
    STATUS      obsolete
    DESCRIPTION
        "Generated when the secondary CPM successfully restores the config and
         state.

         This notification was made obsolete in the 2.1 release.

         It does not apply. This event was originally created for an early
         redundancy mechanism that was never released."
    ::= { tmnxChassisNotification 23 }

tmnxRedRestoreFail               NOTIFICATION-TYPE
    OBJECTS     {
        tmnxChassisNotifyHwIndex,
        tmnxHwID,
        tmnxHwClass
    }
    STATUS      obsolete
    DESCRIPTION
        "Generated when the secondary CPM fails to restore the config and
         state.

         This notification was made obsolete in the 2.1 release.

         It does not apply. This event was originally created for an early
         redundancy mechanism that was never released."
    ::= { tmnxChassisNotification 24 }

tmnxChassisNotificationClear     NOTIFICATION-TYPE
    OBJECTS     {
        tmnxChassisNotifyHwIndex,
        tmnxHwID,
        tmnxHwClass,
        tmnxChassisNotifyOID
    }
    STATUS      current
    DESCRIPTION
        "A trap indicating the clear of a chassis notification identified by
         tmnxChassisNotifyOID."
    ::= { tmnxChassisNotification 25 }

tmnxEqSyncIfTimingHoldover       NOTIFICATION-TYPE
    OBJECTS     {
        tmnxChassisNotifyHwIndex,
        tmnxHwID,
        tmnxHwClass
    }
    STATUS      current
    DESCRIPTION
        "Generated when the synchronous equipment timing subsystem transitions
         into a holdover state. This notification will have the same indices as
         those of the tmnxCpmCardTable."
    ::= { tmnxChassisNotification 26 }

tmnxEqSyncIfTimingHoldoverClear  NOTIFICATION-TYPE
    OBJECTS     {
        tmnxChassisNotifyHwIndex,
        tmnxHwID,
        tmnxHwClass
    }
    STATUS      current
    DESCRIPTION
        "Generated when the synchronous equipment timing subsystem transitions
         out of the holdover state. This notification will have the same
         indices as those of the tmnxCpmCardTable."
    ::= { tmnxChassisNotification 27 }

tmnxEqSyncIfTimingRef1Alarm      NOTIFICATION-TYPE
    OBJECTS     {
        tmnxChassisNotifyHwIndex,
        tmnxHwID,
        tmnxHwClass,
        tmnxSyncIfTimingNotifyAlarm
    }
    STATUS      current
    DESCRIPTION
        "Generated when an alarm condition on the first timing reference is
         detected. This notification will have the same indices as those of the
         tmnxCpmCardTable."
    ::= { tmnxChassisNotification 28 }

tmnxEqSyncIfTimingRef1AlarmClear NOTIFICATION-TYPE
    OBJECTS     {
        tmnxChassisNotifyHwIndex,
        tmnxHwID,
        tmnxHwClass,
        tmnxSyncIfTimingNotifyAlarm
    }
    STATUS      current
    DESCRIPTION
        "Generated when an alarm condition on the first timing reference is
         cleared. This notification will have the same indices as those of the
         tmnxCpmCardTable."
    ::= { tmnxChassisNotification 29 }

tmnxEqSyncIfTimingRef2Alarm      NOTIFICATION-TYPE
    OBJECTS     {
        tmnxChassisNotifyHwIndex,
        tmnxHwID,
        tmnxHwClass,
        tmnxSyncIfTimingNotifyAlarm
    }
    STATUS      current
    DESCRIPTION
        "Generated when an alarm condition on the second timing reference is
         detected. This notification will have the same indices as those of the
         tmnxCpmCardTable."
    ::= { tmnxChassisNotification 30 }

tmnxEqSyncIfTimingRef2AlarmClear NOTIFICATION-TYPE
    OBJECTS     {
        tmnxChassisNotifyHwIndex,
        tmnxHwID,
        tmnxHwClass,
        tmnxSyncIfTimingNotifyAlarm
    }
    STATUS      current
    DESCRIPTION
        "Generated when an alarm condition on the second timing reference is
         cleared. This notification will have the same indices as those of the
         tmnxCpmCardTable."
    ::= { tmnxChassisNotification 31 }

tmnxEqFlashDataLoss              NOTIFICATION-TYPE
    OBJECTS     {
        tmnxChassisNotifyHwIndex,
        tmnxHwID,
        tmnxHwClass,
        tmnxHwOperState
    }
    STATUS      current
    DESCRIPTION
        "tmnxEqFlashDataLoss is generated when an error occurs while data was
         being written to the compact flash. This notification indicates a
         probable data loss."
    ::= { tmnxChassisNotification 32 }

tmnxEqFlashDiskFull              NOTIFICATION-TYPE
    OBJECTS     {
        tmnxChassisNotifyHwIndex,
        tmnxHwID,
        tmnxHwClass,
        tmnxHwOperState,
        tmnxChassisNotifyDiskFullReason
    }
    STATUS      current
    DESCRIPTION
        "tmnxEqFlashDiskFull is generated when there is no space left on the
         compact flash. No more data can be written to it."
    ::= { tmnxChassisNotification 33 }

tmnxPeSoftwareLoadFailed         NOTIFICATION-TYPE
    OBJECTS     {
        tmnxChassisNotifyHwIndex,
        tmnxHwID,
        tmnxHwClass,
        tmnxChassisNotifySoftwareLocation
    }
    STATUS      current
    DESCRIPTION
        "Generated when the CPM fails to load the software from a specified
         location. tmnxChassisNotifyHwIndex identifies the card for which the
         software load failed and tmnxChassisNotifySoftwareLocation contains
         the location from where the software load was attempted."
    ::= { tmnxChassisNotification 34 }

tmnxPeBootloaderVersionMismatch  NOTIFICATION-TYPE
    OBJECTS     {
        tmnxChassisNotifyHwIndex,
        tmnxHwID,
        tmnxHwClass,
        tmnxChassisNotifyMismatchedVer,
        tmnxHwSoftwareCodeVersion
    }
    STATUS      current
    DESCRIPTION
        "Generated when there is a mismatch between the CPM and boot loader
         versions. tmnxChassisNotifyHwIndex identifies the CPM card.
         tmnxChassisNotifyMismatchedVer contains the mismatched version of
         bootloader and tmnxHwSoftwareCodeVersion contains the expected version
         of the bootloader."
    ::= { tmnxChassisNotification 35 }

tmnxPeBootromVersionMismatch     NOTIFICATION-TYPE
    OBJECTS     {
        tmnxChassisNotifyHwIndex,
        tmnxHwID,
        tmnxHwClass,
        tmnxChassisNotifyMismatchedVer,
        tmnxHwSoftwareCodeVersion
    }
    STATUS      current
    DESCRIPTION
        "Generated when there is a mismatch between the boot rom versions.
         tmnxChassisNotifyHwIndex identifies the IOM card.
         tmnxChassisNotifyMismatchedVer contains the mismatched version of
         bootrom and tmnxHwSoftwareCodeVersion contains the expected version of
         the bootrom."
    ::= { tmnxChassisNotification 36 }

tmnxPeFPGAVersionMismatch        NOTIFICATION-TYPE
    OBJECTS     {
        tmnxChassisNotifyHwIndex,
        tmnxHwID,
        tmnxHwClass,
        tmnxChassisNotifyMismatchedVer,
        tmnxHwSoftwareCodeVersion
    }
    STATUS      current
    DESCRIPTION
        "Generated when there is a mismatch between the FPGA versions.
         tmnxChassisNotifyHwIndex identifies the IOM card.
         tmnxChassisNotifyMismatchedVer contains the mismatched version of FPGA
         and tmnxHwSoftwareCodeVersion contains the expected version of the
         FPGA."
    ::= { tmnxChassisNotification 37 }

tmnxEqSyncIfTimingBITSAlarm      NOTIFICATION-TYPE
    OBJECTS     {
        tmnxChassisNotifyHwIndex,
        tmnxHwID,
        tmnxHwClass,
        tmnxSyncIfTimingNotifyAlarm
    }
    STATUS      current
    DESCRIPTION
        "Generated when an alarm condition on the BITS timing reference is
         detected. This notification will have the same indices as those of the
         tmnxCpmCardTable."
    ::= { tmnxChassisNotification 38 }

tmnxEqSyncIfTimingBITSAlarmClear NOTIFICATION-TYPE
    OBJECTS     {
        tmnxChassisNotifyHwIndex,
        tmnxHwID,
        tmnxHwClass,
        tmnxSyncIfTimingNotifyAlarm
    }
    STATUS      current
    DESCRIPTION
        "Generated when an alarm condition on the BITS timing reference is
         cleared. This notification will have the same indices as those of the
         tmnxCpmCardTable."
    ::= { tmnxChassisNotification 39 }

tmnxEqCardFirmwareUpgraded       NOTIFICATION-TYPE
    OBJECTS     {
        tmnxChassisNotifyHwIndex,
        tmnxHwID,
        tmnxHwClass
    }
    STATUS      current
    DESCRIPTION
        "Generated when a card is hot-inserted into the chassis and its
         firmware is automatically upgraded.  The card type may be IOM or
         CPM module."
    ::= { tmnxChassisNotification 40 }

tmnxChassisUpgradeInProgress     NOTIFICATION-TYPE
    OBJECTS     {
        tmnxChassisNotifyHwIndex,
        tmnxHwID,
        tmnxHwClass
    }
    STATUS      current
    DESCRIPTION
        "The tmnxChassisUpgradeInProgress notification is generated only after
         a CPM switchover occurs and the new active CPM is running new
         software, while the IOMs are still running old software. This is the
         start of the upgrade process. The tmnxChassisUpgradeInProgress
         notification will continue to be generated every 30 minutes while at
         least one IOM is still running older software."
    ::= { tmnxChassisNotification 41 }

tmnxChassisUpgradeComplete       NOTIFICATION-TYPE
    OBJECTS     {
        tmnxChassisNotifyHwIndex,
        tmnxHwID,
        tmnxHwClass
    }
    STATUS      current
    DESCRIPTION
        "The tmnxChassisUpgradeComplete notification is generated to indicate
         that all the IOMs are running matching software versions in reference
         to the active CPM software version changed as part of the upgrade
         process."
    ::= { tmnxChassisNotification 42 }

tmnxChassisHiBwMcastAlarm        NOTIFICATION-TYPE
    OBJECTS     {
        tmnxChassisNotifyHwIndex,
        tmnxHwID,
        tmnxHwClass
    }
    STATUS      current
    DESCRIPTION
        "The tmnxChassisHiBwMcastAlarm notification is generated when a plane
         is  shared by more than one high bandwidth multicast tap."
    ::= { tmnxChassisNotification 43 }

tmnxEqMdaCfgNotCompatible        NOTIFICATION-TYPE
    OBJECTS     {
        tmnxChassisNotifyHwIndex,
        tmnxHwID,
        tmnxHwClass,
        tmnxMdaNotifyType
    }
    STATUS      current
    DESCRIPTION
        "Generated when a supported MDA is inserted into a slot of an IOM, the
         MDA is compatible with the currently provisioned MDA, but the current
         configuration on the MDA's ports is not compatible with the inserted
         MDA.

         [EFFECT] Though services can still be created, if the
         tmnxMdaNotifyType is the same as the tmnxMDAEquippedType then the MDA
         will fail to operate as configured and will be in a failed state.

         [RECOVERY] Change the configuration to reflect the capabilities of the
         MDA port, or switch out/re-provision the MDA for one that is
         compatible."
    ::= { tmnxChassisNotification 44 }

tmnxCpmCardSyncFileNotPresent    NOTIFICATION-TYPE
    OBJECTS     {
        tmnxChassisNotifyHwIndex,
        tmnxHwID,
        tmnxHwClass,
        tmnxChassisNotifyCardSyncFile
    }
    STATUS      current
    DESCRIPTION
        "The tmnxCpmCardSyncFileNotPresent notification is generated when the
         redundancy file synchronization failed to locate an optional file."
    ::= { tmnxChassisNotification 45 }

tmnxEqMdaXplError                NOTIFICATION-TYPE
    OBJECTS     {
        tmnxMDAXplFailedCount
    }
    STATUS      current
    DESCRIPTION
        "[CAUSE] The tmnxEqMdaXplError notification is generated when an MDA
         exhibits persistent egress XPL errors, and the tmnxEqMdaIngrXplError
         notification is generated when ingress XPL errors occur.

         [EFFECT] Contact Nokia customer support.

         [RECOVERY] Contact Nokia customer support."
    ::= { tmnxChassisNotification 46 }

tmnxEqCardPChipError             NOTIFICATION-TYPE
    OBJECTS     {
        tmnxChassisNotifyHwIndex,
        tmnxHwID,
        tmnxHwClass,
        tmnxCardComplexNumber,
        tmnxCardFwdDirection,
        tmnxCardSrcSlotBitmap
    }
    STATUS      current
    DESCRIPTION
        "The tmnxEqCardPChipError notification is generated when persistent FCS
         errors are detected by the P chip in either the ingress or egress
         datapath/complex.  The value tmnxCardSrcSlotBitmap is only used for the
         egress datapath/complex direction."
    ::= { tmnxChassisNotification 47 }

tmnxEqCardSoftResetAlarm         NOTIFICATION-TYPE
    OBJECTS     {
        tmnxChassisNotifyHwIndex,
        tmnxHwID,
        tmnxHwClass,
        tmnxCardSoftResetState
    }
    STATUS      current
    DESCRIPTION
        "The tmnxEqCardSoftResetAlarm notification is generated when an IOM
         card enters and exits the 'soft-reset' state."
    ::= { tmnxChassisNotification 48 }

tmnxEqMdaSyncENotCompatible      NOTIFICATION-TYPE
    OBJECTS     {
        tmnxChassisNotifyHwIndex,
        tmnxHwID,
        tmnxHwClass,
        tmnxMdaNotifyType
    }
    STATUS      current
    DESCRIPTION
        "The tmnxEqMdaSyncENotCompatible notification is generated when an MDA
         card is inserted into a slot of an IOM. The MDA is compatible with the
         currently provisioned MDA, but the currently configured synchronous
         ethernet, tmnxMDASynchronousEthernet, is not compatible with the
         inserted MDA.

         [EFFECT] Though services can still be created, if the
         tmnxMdaNotifyType is the same as the tmnxMDAEquippedType then the MDA
         will fail to operate as configured and will be in a failed state.

         [RECOVERY] Change the configuration to reflect the capabilities of the
         MDA port, or switch out/re-provision the MDA for one that is
         compatible."
    ::= { tmnxChassisNotification 49 }

tmnxIPsecIsaGrpActiveIsaChgd     NOTIFICATION-TYPE
    OBJECTS     {
        tmnxIPsecIsaGrpPrimaryIsa,
        tmnxIPsecIsaGrpBackupIsa,
        tmnxIPsecIsaGrpActiveIsa
    }
    STATUS      current
    DESCRIPTION
        "The tmnxIPsecIsaGrpActiveIsaChgd notification is generated when a
         change in the active ISA (Integrated Service Adaptor) occurs in an
         IPsec ISA module group."
    ::= { tmnxChassisNotification 50 }

tmnxEqCardPChipMemoryEvent       NOTIFICATION-TYPE
    OBJECTS     {
        tmnxChassisNotifyHwIndex,
        tmnxHwID,
        tmnxHwClass,
        tmnxCardComplexNumber
    }
    STATUS      current
    DESCRIPTION
        "The tmnxEqCardPChipMemoryEvent notification is generated when a P-chip
         experiences an occurrence of a memory error."
    ::= { tmnxChassisNotification 51 }

tmnxIPsecIsaGrpUnableToSwitch    NOTIFICATION-TYPE
    OBJECTS     {
        tmnxIPsecIsaGrpActiveIsa
    }
    STATUS      current
    DESCRIPTION
        "The tmnxIPsecIsaGrpUnableToSwitch notification is generated when an
         IPsec ISA (Integrated Service Adaptor) module group is unable to
         switch due to lack of resources.

         In such an event the IPsec ISA group is left without an active MDA and
         the tmnxIPsecIsaGrpOperState is set to 'outOfService'.

         Recovery is possible by releasing resources, and setting the
         tmnxIPsecIsaGrpAdminState object to 'outOfService' followed by a reset
         to 'inService' to bring up the ISA group."
    ::= { tmnxChassisNotification 52 }

tmnxIPsecIsaGrpTnlLowWMark       NOTIFICATION-TYPE
    OBJECTS     {
        tmnxIPsecIsaGrpTunnels,
        tmnxIPsecIsaGrpMaxTunnels
    }
    STATUS      current
    DESCRIPTION
        "The tmnxIPsecIsaGrpTnlLowWMark notification is generated when number
         of tunnels for an IPsec ISA (Integrated Service Adaptor) module has
         dropped to the low watermark which is 90% of the
         tmnxIPsecIsaGrpMaxTunnels."
    ::= { tmnxChassisNotification 53 }

tmnxIPsecIsaGrpTnlHighWMark      NOTIFICATION-TYPE
    OBJECTS     {
        tmnxIPsecIsaGrpTunnels,
        tmnxIPsecIsaGrpMaxTunnels
    }
    STATUS      current
    DESCRIPTION
        "The tmnxIPsecIsaGrpTnlHighWMark notification is generated when number
         of tunnels for an IPsec ISA (Integrated Service Adaptor) module has
         reached to the high watermark which is 95% of the
         tmnxIPsecIsaGrpMaxTunnels."
    ::= { tmnxChassisNotification 54 }

tmnxIPsecIsaGrpTnlMax            NOTIFICATION-TYPE
    OBJECTS     {
        tmnxIPsecIsaGrpTunnels,
        tmnxIPsecIsaGrpMaxTunnels
    }
    STATUS      current
    DESCRIPTION
        "The tmnxIPsecIsaGrpTnlMax notification is generated when number of
         tunnels for an IPsec ISA (Integrated Service Adaptor) module has
         reached the maximum of the tmnxIPsecIsaGrpMaxTunnels."
    ::= { tmnxChassisNotification 55 }

tmnxEqSyncIfTimingRef1Quality    NOTIFICATION-TYPE
    OBJECTS     {
        tmnxSyncIfTimingRef1RxQltyLevel
    }
    STATUS      current
    DESCRIPTION
        "Generated when there is a change of the received quality level on
         timing reference 1."
    ::= { tmnxChassisNotification 56 }

tmnxEqSyncIfTimingRef2Quality    NOTIFICATION-TYPE
    OBJECTS     {
        tmnxSyncIfTimingRef2RxQltyLevel
    }
    STATUS      current
    DESCRIPTION
        "Generated when there is a change of the received quality level on
         timing reference 2."
    ::= { tmnxChassisNotification 57 }

tmnxEqSyncIfTimingBITSQuality    NOTIFICATION-TYPE
    OBJECTS     {
        tmnxSyncIfTimingBITSRxQltyLevel
    }
    STATUS      current
    DESCRIPTION
        "Generated when there is a change of the received quality level on the
         bits interface."
    ::= { tmnxChassisNotification 58 }

tmnxEqSyncIfTimingBITS2Quality   NOTIFICATION-TYPE
    OBJECTS     {
        tmnxSyncIfTimingBITS2RxQltyLevel
    }
    STATUS      current
    DESCRIPTION
        "Generated when there is a change of the received quality level on the
         second bits interface."
    ::= { tmnxChassisNotification 59 }

tmnxEqSyncIfTimingRefSwitch      NOTIFICATION-TYPE
    OBJECTS     {
        tmnxSyncIfTimingRef1InUse,
        tmnxSyncIfTimingRef2InUse,
        tmnxSyncIfTimingBITSInUse,
        tmnxSyncIfTimingBITS2InUse,
        tmnxSyncIfTimingPTPInUse
    }
    STATUS      current
    DESCRIPTION
        "Generated when there is a change of which timing reference is
         providing timing for the system."
    ::= { tmnxChassisNotification 60 }

tmnxEqSyncIfTimingBITS2Alarm     NOTIFICATION-TYPE
    OBJECTS     {
        tmnxChassisNotifyHwIndex,
        tmnxHwID,
        tmnxHwClass,
        tmnxSyncIfTimingNotifyAlarm
    }
    STATUS      current
    DESCRIPTION
        "Generated when an alarm condition on the BITS 2 timing reference is
         detected. This notification will have the same indices as those of the
         tmnxCpmCardTable."
    ::= { tmnxChassisNotification 61 }

tmnxEqSyncIfTimingBITS2AlarmClr  NOTIFICATION-TYPE
    OBJECTS     {
        tmnxChassisNotifyHwIndex,
        tmnxHwID,
        tmnxHwClass,
        tmnxSyncIfTimingNotifyAlarm
    }
    STATUS      current
    DESCRIPTION
        "Generated when an alarm condition on the BITS 2 timing reference is
         cleared. This notification will have the same indices as those of the
         tmnxCpmCardTable."
    ::= { tmnxChassisNotification 62 }

tmnxEqSyncIfTimingBITSOutRefChg  NOTIFICATION-TYPE
    OBJECTS     {
        tmnxSyncIfTimingBITSOutRefSel
    }
    STATUS      current
    DESCRIPTION
        "Generated when the BITS Out timing reference selection changes."
    ::= { tmnxChassisNotification 63 }

tmnxEqCardPChipCamEvent          NOTIFICATION-TYPE
    OBJECTS     {
        tmnxChassisNotifyHwIndex,
        tmnxHwID,
        tmnxHwClass,
        tmnxCardComplexNumber
    }
    STATUS      current
    DESCRIPTION
        "[CAUSE] The tmnxEqCardPChipCamEvent notification is generated when
         either an IOM or a CPM experiences a persistent occurrence of a PChip
         CAM error. On a CPM card, the tmnxCardComplexNumber will be fixed to
         the value zero (0).

         [EFFECT] Contact Nokia customer support.

         [RECOVERY] Contact Nokia customer support."
    ::= { tmnxChassisNotification 64 }

tmnxEqSyncIfTimingSystemQuality  NOTIFICATION-TYPE
    OBJECTS     {
        tmnxSyncIfTimingSystemQltyLevel
    }
    STATUS      current
    DESCRIPTION
        "The tmnxEqSyncIfTimingSystemQuality notification is generated when
         there is a change in the system timing quality level. This
         notification is a point-in-time state change event.

         [CAUSE] This notification may be triggered for the following reasons:

         1) There has been a switch in the timing reference in use by the
            network element, either because the previously active timing
            reference was disqualified, or to ensure that the network element
            is using the timing reference with the best timing quality.
         2) There has been a change in the active timing reference's quality
            and the change does not result in a timing reference switch.
         3) The network element has transitioned into or out of the holdover
            state.

         [EFFECT] The system quality level is used to determine the SSM code
         transmitted on synchronous interfaces. This may affect the SSM code
         transmitted on some or all interfaces, which may affect the
         distribution of timing throughout the network.

         [RECOVERY] If the customer is expecting the system to be locked to a
         reference of a particular quality and the system quality has
         decreased, the customer will need to determine the root cause (for
         example, loss of communication with a satellite) and resolve the
         issue."
    ::= { tmnxChassisNotification 65 }

tmnxEqHwEnhancedCapability       NOTIFICATION-TYPE
    OBJECTS     {
        tmnxChassisNotifyHwIndex,
        tmnxHwID,
        tmnxHwClass
    }
    STATUS      current
    DESCRIPTION
        "The tmnxEqHwEnhancedCapability notification is generated when the
         hardware, specified by the supplied objects, consists of enhanced
         capabilities as compared to the active hardware.

         [EFFECT] The system behaves normally under this situation, however,
         switching to the newer hardware will put the system in an incompatible
         state with the currently active hardware. That is, once this device
         takes activity, the lesser capable hardware will fail to communicate
         with it.

         In this mode, the system is deemed to be in a 'one-way upgrade'
         scenario.

         [RECOVERY] Two modes of recovery exist for this notification:
            1. Remove the enhanced hardware, and supply a more compatible
               device (status quo) with the active hardware.
            2. Switch to the enhanced device, and replace the older hardware
               with a similarly enhanced device (upgrade)."
    ::= { tmnxChassisNotification 66 }

tmnxEqSyncIfTimingPTPQuality     NOTIFICATION-TYPE
    OBJECTS     {
        tmnxSyncIfTimingPTPRxQltyLevel
    }
    STATUS      current
    DESCRIPTION
        "Generated when there is a change of the received quality level on the
         Precision Timing Protocol (PTP)."
    ::= { tmnxChassisNotification 67 }

tmnxEqSyncIfTimingPTPAlarm       NOTIFICATION-TYPE
    OBJECTS     {
        tmnxChassisNotifyHwIndex,
        tmnxHwID,
        tmnxHwClass,
        tmnxSyncIfTimingNotifyAlarm
    }
    STATUS      current
    DESCRIPTION
        "Generated when an alarm condition on the Precision Timing Protocol
         (PTP) timing reference is detected. This notification will have the
         same indices as those of the tmnxCpmCardTable."
    ::= { tmnxChassisNotification 68 }

tmnxEqSyncIfTimingPTPAlarmClear  NOTIFICATION-TYPE
    OBJECTS     {
        tmnxChassisNotifyHwIndex,
        tmnxHwID,
        tmnxHwClass,
        tmnxSyncIfTimingNotifyAlarm
    }
    STATUS      current
    DESCRIPTION
        "Generated when an alarm condition on the Precision Timing Protocol
         (PTP) timing reference is cleared. This notification will have the
         same indices as those of the tmnxCpmCardTable."
    ::= { tmnxChassisNotification 69 }

tmnxPeFirmwareVersionWarning     NOTIFICATION-TYPE
    OBJECTS     {
        tmnxChassisNotifyHwIndex,
        tmnxHwID,
        tmnxHwClass,
        tmnxHwFirmwareCodeVersion
    }
    STATUS      current
    DESCRIPTION
        "Generated when a card is running compatible yet older firmware
         than the firmware associated with the current software release.
         tmnxChassisNotifyHwIndex identifies the card.  The
         tmnxHwFirmwareCodeVersion object will contain the programmed
         the firmware version."
    ::= { tmnxChassisNotification 70 }

tmnxMDAIsaTunnelGroupChange      NOTIFICATION-TYPE
    OBJECTS     {
        tmnxMDAIsaTunnelGroupInUse,
        tmnxMDAIsaTunnelGroup
    }
    STATUS      current
    DESCRIPTION
        "[CAUSE] The tmnxMDAIsaTunnelGroupChange notification is generated when
         IPsec ISA (Integrated Service Adaptor) tunnel-group in-use for the MDA
         changes value.

         [EFFECT] There is no operational impact due to this event.

         [RECOVERY] None required."
    ::= { tmnxChassisNotification 71 }

tmnxDcpCardFpEventOvrflw         NOTIFICATION-TYPE
    OBJECTS     {
        tmnxChassisNotifyChassisId,
        tmnxChassisNotifyCardSlotNum,
        tmnxDcpTimeEventOccured
    }
    STATUS      current
    DESCRIPTION
        "[CAUSE] The tmnxDcpCardFpEventOvrflw notification is generated when a
         flood of distibuted CPU FP protection events occur on a particular
         card and some of the events are lost due to event throttling
         mechanism.

         [EFFECT] Some FP notifications configured on the card may not be
         received.

         [RECOVERY] Notifications will resume once the event throttling ends."
    ::= { tmnxChassisNotification 72 }

tmnxDcpCardSapEventOvrflw        NOTIFICATION-TYPE
    OBJECTS     {
        tmnxChassisNotifyChassisId,
        tmnxChassisNotifyCardSlotNum,
        tmnxDcpTimeEventOccured
    }
    STATUS      current
    DESCRIPTION
        "[CAUSE] The tmnxDcpCardSapEventOvrflw notification is generated when a
         flood of distibuted CPU protection SAP events occur on a particular
         card and some of the events are lost due to event throttling
         mechanism.

         [EFFECT] Some SAP notifications configured on the card may not be
         received.

         [RECOVERY] Notifications will resume once the event throttling ends."
    ::= { tmnxChassisNotification 73 }

tmnxDcpCardVrtrIfEventOvrflw     NOTIFICATION-TYPE
    OBJECTS     {
        tmnxChassisNotifyChassisId,
        tmnxChassisNotifyCardSlotNum,
        tmnxDcpTimeEventOccured
    }
    STATUS      current
    DESCRIPTION
        "[CAUSE] The tmnxDcpCardVrtrIfEventOvrflw notification is generated
         when a flood of distibuted CPU protection network-interface events
         occur on a particular card and some of the events are lost due to
         event throttling mechanism.

         [EFFECT] Some network-interface notifications configured on the card
         may not be received.

         [RECOVERY] Notifications will resume once the event throttling ends."
    ::= { tmnxChassisNotification 74 }

tmnxDcpFpDynPoolUsageHiAlmRaise  NOTIFICATION-TYPE
    OBJECTS     {
        tmnxFPDCpuProtDynEnfrcPlcrPool,
        tmnxDcpTimeEventOccured
    }
    STATUS      current
    DESCRIPTION
        "[CAUSE] The tmnxDcpFpDynPoolUsageHiAlmRaise notification is generated
         when the dynamic enforcement policer pool usage on the forwarding
         plane is nearly exhausted.

         [EFFECT] Dynamic enforcement policers may not get allocated on the
         forwarding plane.

         [RECOVERY] This notification will be cleared when either the dynamic
         enforcement policer pool is increased or the usage drops."
    ::= { tmnxChassisNotification 75 }

tmnxDcpFpDynPoolUsageHiAlmClear  NOTIFICATION-TYPE
    OBJECTS     {
        tmnxFPDCpuProtDynEnfrcPlcrPool,
        tmnxDcpTimeEventOccured
    }
    STATUS      current
    DESCRIPTION
        "[CAUSE] The tmnxDcpFpDynPoolUsageHiAlmClear notification is generated
         when the dynamic enforcement policer pool usage on the forwarding
         plane is no longer exhausted.

         [EFFECT] Dynamic enforcement policers are available in the free pool
         to be allocated when needed.

         [RECOVERY] There is no recovery required for this notification."
    ::= { tmnxChassisNotification 76 }

tmnxDcpCardFpEventOvrflwClr      NOTIFICATION-TYPE
    OBJECTS     {
        tmnxChassisNotifyChassisId,
        tmnxChassisNotifyCardSlotNum,
        tmnxDcpTimeEventOccured,
        tmnxDcpMissingNotificationCount
    }
    STATUS      current
    DESCRIPTION
        "[CAUSE] The tmnxDcpCardFpEventOvrflwClr notification is generated when
         the event throttling has ended for distibuted CPU protection FP events
         on a particular card.

         [EFFECT] Notifications are received again since the event throttling
         has ended.

         [RECOVERY] There is no recovery for this notification."
    ::= { tmnxChassisNotification 77 }

tmnxDcpCardSapEventOvrflwClr     NOTIFICATION-TYPE
    OBJECTS     {
        tmnxChassisNotifyChassisId,
        tmnxChassisNotifyCardSlotNum,
        tmnxDcpTimeEventOccured,
        tmnxDcpMissingNotificationCount
    }
    STATUS      current
    DESCRIPTION
        "[CAUSE] The tmnxDcpCardSapEventOvrflwClr notification is generated
         when the event throttling has ended for distibuted CPU protection SAP
         events on a particular card.

         [EFFECT] Notifications are received again since the event throttling
         has ended.

         [RECOVERY] There is no recovery for this notification."
    ::= { tmnxChassisNotification 78 }

tmnxDcpCardVrtrIfEventOvrflwClr  NOTIFICATION-TYPE
    OBJECTS     {
        tmnxChassisNotifyChassisId,
        tmnxChassisNotifyCardSlotNum,
        tmnxDcpTimeEventOccured,
        tmnxDcpMissingNotificationCount
    }
    STATUS      current
    DESCRIPTION
        "[CAUSE] The tmnxDcpCardVrtrIfEventOvrflwClr notification is generated
         when the event throttling has ended for distibuted CPU protection
         network-interface events on a particular card.

         [EFFECT] Notifications are received again since the event throttling
         has ended.

         [RECOVERY] There is no recovery for this notification."
    ::= { tmnxChassisNotification 79 }

tmnxEqPowerCapacityExceeded      NOTIFICATION-TYPE
    OBJECTS     {
        tmnxChassisNotifyChassisId,
        tmnxChassisNotifyPowerZone,
        tmnxChassisNotifyPowerCapacity
    }
    STATUS      current
    DESCRIPTION
        "[CAUSE] The tmnxEqPowerCapacityExceeded alarm is generated when a
         device needs power to boot, but there is not enough power capacity to
         support the device.

         [EFFECT] A non-powered device will not boot until the power capacity
         is increased to support the device.

         [RECOVERY] Add a new power supply to the system or change the faulty
         power supply for a working one."
    ::= { tmnxChassisNotification 80 }

tmnxEqPowerCapacityExceededClear NOTIFICATION-TYPE
    OBJECTS     {
        tmnxChassisNotifyChassisId,
        tmnxChassisNotifyPowerZone
    }
    STATUS      current
    DESCRIPTION
        "[CAUSE] The tmnxEqPowerCapacityExceededClear notification is generated
         when the available power capacity exceeds the required power to boot
         all inserted devices.

         [EFFECT] Devices that failed to boot due to power constrains, power
         up."
    ::= { tmnxChassisNotification 81 }

tmnxEqPowerLostCapacity          NOTIFICATION-TYPE
    OBJECTS     {
        tmnxChassisNotifyChassisId,
        tmnxChassisNotifyPowerZone,
        tmnxChassisNotifyPowerCapacity
    }
    STATUS      current
    DESCRIPTION
        "[CAUSE] The tmnxEqPowerLostCapacity alarm is generated when a power
         supply fails or is removed which puts the system in an overloaded
         situation.

         [EFFECT] Devices are powered off in order of lowest power priority
         (tmnxMDAHwPowerPriority) until the available power capacity can
         support the powered devices.

         [RECOVERY] Add a new power supply to the system or change the faulty
         power supply for a working one."
    ::= { tmnxChassisNotification 82 }

tmnxEqPowerLostCapacityClear     NOTIFICATION-TYPE
    OBJECTS     {
        tmnxChassisNotifyChassisId,
        tmnxChassisNotifyPowerZone
    }
    STATUS      current
    DESCRIPTION
        "[CAUSE] The tmnxEqPowerLostCapacityClear notification is generated
         when the available power capacity exceeds the required power to boot
         all inserted devices.

         [EFFECT] Devices that powered off due to power constrains, power up."
    ::= { tmnxChassisNotification 83 }

tmnxEqPowerOverloadState         NOTIFICATION-TYPE
    OBJECTS     {
        tmnxChassisNotifyChassisId,
        tmnxChassisNotifyPowerZone,
        tmnxChassisNotifyPowerCapacity
    }
    STATUS      current
    DESCRIPTION
        "[CAUSE] The tmnxEqPowerOverloadState alarm is generated when the
         overloaded power capacity can not support the power requirements and
         there are no further devices that can be powered off.

         [EFFECT] The system runs a risk of experiencing brownouts while the
         available power capacity does not meet the required power consumption.

         [RECOVERY] Add power capacity or manually shut down devices until the
         power capacity meets the power needs."
    ::= { tmnxChassisNotification 84 }

tmnxEqPowerOverloadStateClear    NOTIFICATION-TYPE
    OBJECTS     {
        tmnxChassisNotifyChassisId,
        tmnxChassisNotifyPowerZone
    }
    STATUS      current
    DESCRIPTION
        "[CAUSE] The tmnxEqPowerOverloadStateClear notification is generated
         when the available power capacity meets or exceeds the power needs of
         the powered on devices."
    ::= { tmnxChassisNotification 85 }

tmnxEqCardQChipBufMemoryEvent    NOTIFICATION-TYPE
    OBJECTS     {
        tmnxHwID,
        tmnxHwClass,
        tmnxCardComplexNumber
    }
    STATUS      current
    DESCRIPTION
        "[CAUSE] The tmnxEqCardQChipBufMemoryEvent notification is generated
         when a Q-chip experiences an occurrence of a buffer memory error.

         [EFFECT] Contact Nokia customer support.

         [RECOVERY] Contact Nokia customer support."
    ::= { tmnxChassisNotification 86 }

tmnxEqCardQChipStatsMemoryEvent  NOTIFICATION-TYPE
    OBJECTS     {
        tmnxHwID,
        tmnxHwClass,
        tmnxCardComplexNumber
    }
    STATUS      current
    DESCRIPTION
        "[CAUSE] The tmnxEqCardQChipStatsMemoryEvent notification is generated
         when a Q-chip experiences an occurrence of a statistics memory error.

         [EFFECT] Contact Nokia customer support.

         [RECOVERY] Contact Nokia customer support."
    ::= { tmnxChassisNotification 87 }

tmnxEqCardQChipIntMemoryEvent    NOTIFICATION-TYPE
    OBJECTS     {
        tmnxHwID,
        tmnxHwClass,
        tmnxCardComplexNumber
    }
    STATUS      current
    DESCRIPTION
        "[CAUSE] The tmnxEqCardQChipIntMemoryEvent notification is generated
         when a Q-chip experiences an occurrence of an internal memory error.

         [EFFECT] Contact Nokia customer support.

         [RECOVERY] Contact Nokia customer support."
    ::= { tmnxChassisNotification 88 }

tmnxEqCardChipIfDownEvent        NOTIFICATION-TYPE
    OBJECTS     {
        tmnxHwID,
        tmnxHwClass,
        tmnxCardComplexNumber
    }
    STATUS      current
    DESCRIPTION
        "[CAUSE] The tmnxEqCardChipIfDownEvent notification is generated when
         an inter-chip interface (XPL2 bundle) experiences an internal datapath
         problem.

         [EFFECT] 7750 SR/7450 ESS: The IOM or IMM will either remain
         operational or the card will reset along with its associated MDAs.
         7950 XRS: The associated XMA (MDA CLI context) will either remain
         operational or it will reset. The XCM (CLI card context) will not
         reset.

         [RECOVERY] Contact Nokia customer support."
    ::= { tmnxChassisNotification 89 }

tmnxEqCardChipIfCellEvent        NOTIFICATION-TYPE
    OBJECTS     {
        tmnxHwID,
        tmnxHwClass,
        tmnxCardComplexNumber
    }
    STATUS      current
    DESCRIPTION
        "[CAUSE] The tmnxEqCardChipIfCellEvent notification is generated when
         an inter-chip interface (XPL2 bundle) experiences internal datapath
         cell errors.

         [EFFECT] Contact Nokia customer support.

         [RECOVERY] Contact Nokia customer support."
    ::= { tmnxChassisNotification 90 }

tmnxEqLowSwitchFabricCap         NOTIFICATION-TYPE
    OBJECTS     {
        tmnxHwClass
    }
    STATUS      current
    DESCRIPTION
        "[CAUSE] The tmnxEqLowSwitchFabricCap alarm is generated when the total
         switch fabric capacity becomes less than the IOM capacity due to link
         failures. At least one of the taps on the IOM is below 100% capacity.

         [EFFECT] There is diminished switch fabric capacity to forward
         service-impacting information.

         [RECOVERY] If the system does not self-recover, the IOM must be
         rebooted."
    ::= { tmnxChassisNotification 91 }

tmnxEqLowSwitchFabricCapClear    NOTIFICATION-TYPE
    OBJECTS     {
        tmnxHwClass
    }
    STATUS      current
    DESCRIPTION
        "[CAUSE] The tmnxEqLowSwitchFabricCapClear notification is generated
         when the link failures that resulted in the tmnxEqLowSwitchFabricCap
         alarm to be raised have been resolved.

         [EFFECT] There is sufficient switch fabric capacity to forward
         service-impacting information."
    ::= { tmnxChassisNotification 92 }

tmnxEqPowerSafetyAlertThreshold  NOTIFICATION-TYPE
    OBJECTS     {
        tmnxChassisPwrMgmtSafetyAlert
    }
    STATUS      current
    DESCRIPTION
        "[CAUSE] The tmnxEqPowerSafetyAlertThreshold notification is generated
         when the system power capacity drops below the configured safety alert
         threshold.

         [EFFECT] This event is for notification only."
    ::= { tmnxChassisNotification 93 }

tmnxEqPowerSafetyAlertClear      NOTIFICATION-TYPE
    OBJECTS     {
        tmnxChassisPwrMgmtSafetyAlert
    }
    STATUS      current
    DESCRIPTION
        "[CAUSE] The tmnxEqPowerSafetyAlertClear notification is generated when
         the system power capacity meets or exceeds the configured safety alert
         threshold.

         [EFFECT] This event is for notification only."
    ::= { tmnxChassisNotification 94 }

tmnxEqPowerSafetyLevelThreshold  NOTIFICATION-TYPE
    OBJECTS     {
        tmnxChassisPwrMgmtSafetyLevel
    }
    STATUS      current
    DESCRIPTION
        "[CAUSE] The tmnxEqPowerSafetyLevelThreshold notification is generated
         when the peak nodal power consumption exceeds the configured safety
         level threshold.

         [EFFECT] This event is for notification only."
    ::= { tmnxChassisNotification 95 }

tmnxEqPowerSafetyLevelClear      NOTIFICATION-TYPE
    OBJECTS     {
        tmnxChassisPwrMgmtSafetyLevel
    }
    STATUS      current
    DESCRIPTION
        "[CAUSE] The tmnxEqPowerSafetyLevelClear notification is generated when
         the peak nodal power consumption drops below the configured safety
         level threshold.

         [EFFECT] This event is for notification only."
    ::= { tmnxChassisNotification 96 }

tmnxEqCardTChipParityEvent       NOTIFICATION-TYPE
    OBJECTS     {
        tmnxHwID,
        tmnxHwClass,
        tmnxCardComplexNumber
    }
    STATUS      current
    DESCRIPTION
        "[CAUSE] The tmnxEqCardTChipParityEvent notification is generated when
         a T-chip experiences an occurrence of an internal memory error.

         [EFFECT] Contact Nokia customer support.

         [RECOVERY] Contact Nokia customer support."
    ::= { tmnxChassisNotification 97 }

tmnxEqPowerSupplyPemACRectAlm    NOTIFICATION-TYPE
    OBJECTS     {
        tmnxHwClass,
        tmnxChassisPowerSupplyPemACRect
    }
    STATUS      obsolete
    DESCRIPTION
        "[CAUSE] The tmnxEqPowerSupplyPemACRectAlm alarm is generated if any
         one of the AC rectifiers for a given power supply is in a failed state
         or is missing.

         [EFFECT] There is an increased risk of the power supply failing,
         causing insufficient power to the system.

         [RECOVERY] Bring the AC rectifiers back online.

         This notification was made obsolete in release 15.0."
    ::= { tmnxChassisNotification 98 }

tmnxEqPowerSupplyPemACRectAlmClr NOTIFICATION-TYPE
    OBJECTS     {
        tmnxHwClass
    }
    STATUS      obsolete
    DESCRIPTION
        "[CAUSE] The tmnxEqPowerSupplyPemACRectAlmClr notification is generated
         when the last of the failed or missing AC rectifiers has been brought
         back online.

         [EFFECT] The power supply AC rectifiers are fully operational.

         This notification was made obsolete in release 15.0."
    ::= { tmnxChassisNotification 99 }

tmnxEqPowerSupplyInputFeedAlm    NOTIFICATION-TYPE
    OBJECTS     {
        tmnxHwClass,
        tmnxChassisPowerSupplyInFeedDown
    }
    STATUS      obsolete
    DESCRIPTION
        "[CAUSE] The tmnxEqPowerSupplyInputFeedAlm alarm is generated if any
         one of the input feeds for a given power supply is not supplying
         power.

         [EFFECT] There is an increased risk of system power brown-outs or
         black-outs.

         [RECOVERY] Restore all of the input feeds that are not supplying
         power.

         This notification was made obsolete in release 15.0."
    ::= { tmnxChassisNotification 100 }

tmnxEqPowerSupplyInputFeedAlmClr NOTIFICATION-TYPE
    OBJECTS     {
        tmnxHwClass
    }
    STATUS      obsolete
    DESCRIPTION
        "[CAUSE] The tmnxEqPowerSupplyInputFeedAlmClr notification is generated
         when the last of the missing input feeds has been brought back online.

         [EFFECT] All power supply input feeds are supplying power.

         This notification was made obsolete in release 15.0."
    ::= { tmnxChassisNotification 101 }

tmnxEqProvPowerCapacityAlm       NOTIFICATION-TYPE
    OBJECTS     {
        tmnxHwClass,
        tmnxHwPowerZone,
        tmnxChassisNotifyPowerCapacity
    }
    STATUS      current
    DESCRIPTION
        "[CAUSE] The tmnxEqProvPowerCapacityAlm notification is generated if a
         power zone's provisioned power capacity can no longer support
         configured devices.

         [EFFECT] There is an increased risk of device power outages that may
         be service affecting.

         [RECOVERY] Increase the provisioned power capacity."
    ::= { tmnxChassisNotification 102 }

tmnxEqProvPowerCapacityAlmClr    NOTIFICATION-TYPE
    OBJECTS     {
        tmnxHwClass,
        tmnxHwPowerZone
    }
    STATUS      current
    DESCRIPTION
        "[CAUSE] The tmnxEqProvPowerCapacityAlmClr notification is generated
         when the power zone's provisioned power capacity can support
         configured devices.

         [EFFECT] All configured devices in the power zone have enough
         provisioned power capacity."
    ::= { tmnxChassisNotification 103 }

tmnxPlcyAcctStatsPoolExcResource NOTIFICATION-TYPE
    OBJECTS     {
        tmnxFPPlcyAcctStatsPool,
        tmnxFPPlcyAcctStatsInUse
    }
    STATUS      current
    DESCRIPTION
        "[CAUSE] The tmnxPlcyAcctStatsPoolExcResource notification is generated
         when the number of in-use stats resource usage as specified by
         tmnxFPPlcyAcctStatsInUse exceeds 95 percent of the stats pool limit as
         specified by tmnxFPPlcyAcctStatsPool.

         [EFFECT] The affected device may not provide accurate and complete
         statistics.

         [RECOVERY] There is no recovery required for this notification."
    ::= { tmnxChassisNotification 104 }

tmnxPlcyAcctStatsPoolLowResource NOTIFICATION-TYPE
    OBJECTS     {
        tmnxFPPlcyAcctStatsPool,
        tmnxFPPlcyAcctStatsInUse
    }
    STATUS      current
    DESCRIPTION
        "[CAUSE] The tmnxPlcyAcctStatsPoolLowResource notification is generated
         when the number of in-use stats resource as specified by
         tmnxFPPlcyAcctStatsInUse is below 85 percent of the stats pool limit
         as specified by tmnxFPPlcyAcctStatsPool.

         [EFFECT] The configured stats pool limit is cleared when the number of
         in-use stats resources falls below 85 percent of the stats pool limit.

         [RECOVERY] There is no recovery required for this notification."
    ::= { tmnxChassisNotification 105 }

tmnxPlcyAcctStatsEventOvrflwClr  NOTIFICATION-TYPE
    OBJECTS     {
        tmnxChassisNotifyChassisId,
        tmnxChassisNotifyCardSlotNum,
        tmnxPlcyAcctTimeEventOccured,
        tmnxPlcyAcctMissingNotifCount
    }
    STATUS      current
    DESCRIPTION
        "[CAUSE] The tmnxPlcyAcctStatsEventOvrflwClr notification is generated
         when the CPM polls the IOM for traps and the overflow is cleared by
         logging an overflow-clear on a particular card.

         [EFFECT] Notifications are received again since the event throttling
         has ended.

         [RECOVERY] There is no recovery for this notification."
    ::= { tmnxChassisNotification 106 }

tmnxPlcyAcctStatsEventOvrflw     NOTIFICATION-TYPE
    OBJECTS     {
        tmnxChassisNotifyChassisId,
        tmnxChassisNotifyCardSlotNum,
        tmnxPlcyAcctTimeEventOccured
    }
    STATUS      current
    DESCRIPTION
        "[CAUSE] The tmnxPlcyAcctStatsEventOvrflw notification is generated
         when tmnxPlcyAcctStatsPoolExcResource and
         tmnxPlcyAcctStatsPoolLowResource occur more than 200 times because of
         resource usage fluctuation. The IOM raises the final trap to indicate
         overflow and stops logging traps.

         [EFFECT] Some FP notifications configured on the card may not be
         received.

         [RECOVERY] Notifications will resume once the Overflow clear is set."
    ::= { tmnxChassisNotification 107 }

tmnxIomResHighLimitReached       NOTIFICATION-TYPE
    OBJECTS     {
        tmnxChassisNotifyChassisId,
        tmnxChassisNotifyCardSlotNum,
        tmnxIomResourceType,
        tmnxIomResourceLimitPct,
        tmnxIomResLimitTimeEventOccured,
        tmnxChassisNotifyFpNum
    }
    STATUS      current
    DESCRIPTION
        "[CAUSE] The tmnxIomResHighLimitReached notification is generated when
         the resource (of type tmnxIomResourceType) utilization on IOM has
         reached the value of tmnxIomResourceLimitPct.

         [EFFECT] The specified resource limit is cleared when the number of
         in-use stats resources falls below the clear threshold of the stats
         pool limit.

         [RECOVERY] There is no recovery required for this notification."
    ::= { tmnxChassisNotification 108 }

tmnxIomResExhausted              NOTIFICATION-TYPE
    OBJECTS     {
        tmnxChassisNotifyChassisId,
        tmnxChassisNotifyCardSlotNum,
        tmnxIomResourceType,
        tmnxIomResLimitTimeEventOccured,
        tmnxChassisNotifyFpNum
    }
    STATUS      current
    DESCRIPTION
        "[CAUSE] The tmnxIomResExhausted notification is  generated when
         the type of resources on IOM as specified by tmnxIomResourceType has
         reached the 100% of its utilization threshold.

         [EFFECT] The specified resource has reached the stats pool limit.

         [RECOVERY] Intervention may be required to recover resources."
    ::= { tmnxChassisNotification 109 }

tmnxIomResStateClr               NOTIFICATION-TYPE
    OBJECTS     {
        tmnxChassisNotifyChassisId,
        tmnxChassisNotifyCardSlotNum,
        tmnxIomResourceType,
        tmnxIomResourceLimitPct,
        tmnxIomResLimitTimeEventOccured,
        tmnxChassisNotifyFpNum
    }
    STATUS      current
    DESCRIPTION
        "[CAUSE] The tmnxIomResStateClr notification is generated when the type
         of resources on IOM as specified by tmnxIomResourceType has dropped
         back down below the value of tmnxIomResourceLimitPct.

         [EFFECT] The specified resource limit is cleared when the number of
         in-use stats resources falls below tmnxIomResourceLimitPct of the
         stats pool limit.

         [RECOVERY] There is no recovery required for this notification."
    ::= { tmnxChassisNotification 110 }

tmnxIomEventOverflow             NOTIFICATION-TYPE
    OBJECTS     {
        tmnxChassisNotifyChassisId,
        tmnxChassisNotifyCardSlotNum,
        tmnxIomResLimitTimeEventOccured,
        tmnxIomResourceType
    }
    STATUS      current
    DESCRIPTION
        "[CAUSE] The tmnxIomEventOverflow notification is generated when
         tmnxIomResStateClr, tmnxIomResExhausted and tmnxIomResHighLimitReached
         occur more than 200 times because of resource usage fluctuation. The
         IOM raises the final trap to indicate overflow and stops logging
         traps.

         [EFFECT] Some FP notifications configured on the card may not be
         received.

         [RECOVERY] Notifications will resume once the Overflow clear is set."
    ::= { tmnxChassisNotification 111 }

tmnxIomEventOverflowClr          NOTIFICATION-TYPE
    OBJECTS     {
        tmnxChassisNotifyChassisId,
        tmnxChassisNotifyCardSlotNum,
        tmnxIomResLimitTimeEventOccured,
        tmnxIomResLimMissingNotifCount,
        tmnxIomResourceType
    }
    STATUS      current
    DESCRIPTION
        "[CAUSE] The tmnxIomEventOverflowClr notification is generated when the
         CPM polls the IOM for traps and the overflow is cleared by logging an
         overflow-clear on a particular card.

         [EFFECT] Notifications are received again since the event throttling
         has ended.

         [RECOVERY] There is no recovery for this notification."
    ::= { tmnxChassisNotification 112 }

tmnxEqDataPathFailureProtImpact  NOTIFICATION-TYPE
    OBJECTS     {
        tmnxHwClass
    }
    STATUS      current
    DESCRIPTION
        "[CAUSE] The tmnxEqDataPathFailureProtImpact notification is generated
         when a slot experienced a data path failure which impacted a protocol.

         [EFFECT] Services-related data associated with the impacted protocol
         may be lost."
    ::= { tmnxChassisNotification 113 }

tmnxExtStandbyCpmReboot          NOTIFICATION-TYPE
    OBJECTS     {
        tmnxChassisNotifyChassisId,
        tmnxChassisNotifyCpmCardSlotNum
    }
    STATUS      current
    DESCRIPTION
        "[CAUSE] The tmnxExtStandbyCpmReboot notification is generated after a
         master standby CPM reboots and it is determined that the master
         standby CPM has transitioned into or out of an ISSU state. This
         detected transition will cause a reboot of the extension standby CPM
         (this reboot is necessary and expected for ISSU operation). This
         notification helps an operator understand why an extension standby CPM
         may have rebooted.

         [EFFECT] The extension standby CPM will reboot.

         [RECOVERY] There is no recovery for this notification."
    ::= { tmnxChassisNotification 114 }

tmnxExtStandbyCpmRebootFail      NOTIFICATION-TYPE
    OBJECTS     {
        tmnxChassisNotifyChassisId
    }
    STATUS      current
    DESCRIPTION
        "[CAUSE] The tmnxExtStandbyCpmRebootFail notification is generated
         after a master standby CPM reboots and it is determined that the
         master standby CPM has transitioned into or out of an ISSU state. The
         system will attempt to reboot the extension standby CPM as part of the
         normal ISSU process. If the system determines that it cannot reboot
         the extension standby CPM (i.e. it is not reachable) then this log
         event is raised.

         [EFFECT] The extension standby CPM may not transition to the ISSU
         state in which case the ISSU cannot proceed normally.

         [RECOVERY] Resetting the extension standby CPM can be attempted to try
         and get the CPM into an ISSU state. If that is not successful, then
         the ISSU should be aborted."
    ::= { tmnxChassisNotification 115 }

tmnxEqMdaIngrXplError            NOTIFICATION-TYPE
    OBJECTS     {
        tmnxMdaHwEventNumOccurrences
    }
    STATUS      current
    DESCRIPTION
        "[CAUSE] The tmnxEqMdaIngrXplError notification is generated when an
         MDA exhibits persistent ingress XPL errors, and the tmnxEqMdaXplError
         notification is generated when egress XPL errors occur.

         [EFFECT] Contact Nokia customer support.

         [RECOVERY] Contact Nokia customer support."
    ::= { tmnxChassisNotification 116 }

tmnxPowerSupplyWrongFanDir       NOTIFICATION-TYPE
    OBJECTS     {
        tmnxHwClass,
        tmnxChassisPowerSupplyFanDir
    }
    STATUS      obsolete
    DESCRIPTION
        "[CAUSE] The tmnxPowerSupplyWrongFanDir notification is generated when
         the airflow direction of the power supply's fan is incorrect.

         [EFFECT] The power supply is not cooling properly and may overheat.

         [RECOVERY] Replace the power supply with one that has the proper fan
         direction.

         This notification was made obsolete in release 15.0."
    ::= { tmnxChassisNotification 119 }

tmnxPowerSupplyWrongFanDirClear  NOTIFICATION-TYPE
    OBJECTS     {
        tmnxHwClass
    }
    STATUS      obsolete
    DESCRIPTION
        "[CAUSE] The tmnxPowerSupplyWrongFanDirClear notification is generated
         when the airflow direction of the power supply's fan is corrected.

         [EFFECT] The fan is cooling the power supply in the proper direction.

         [RECOVERY] No recovery required.

         This notification was made obsolete in release 15.0."
    ::= { tmnxChassisNotification 120 }

tmnxEqMgmtEthRedStandbyRaise     NOTIFICATION-TYPE
    OBJECTS     {
        tmnxHwClass,
        tmnxChassisNotifyMgmtEthRedPort
    }
    STATUS      current
    DESCRIPTION
        "[CAUSE] The tmnxEqMgmtEthRedStandbyRaise notification is generated
         when the active CPM's management Ethernet port goes operationally down
         and the standby CPM's management Ethernet port is operationally up and
         now serving as the system's management Ethernet port.

         [EFFECT] The management Ethernet port is no longer redundant. The node
         can be managed via the standby CPM's management Ethernet port only.

         [RECOVERY] Bring the active CPM's management Ethernet port
         operationally up."
    ::= { tmnxChassisNotification 121 }

tmnxEqMgmtEthRedStandbyClear     NOTIFICATION-TYPE
    OBJECTS     {
        tmnxHwClass,
        tmnxChassisNotifyMgmtEthRedPort
    }
    STATUS      current
    DESCRIPTION
        "[CAUSE] The tmnxEqMgmtEthRedStandbyClear notification is generated
         when the active CPM's management Ethernet port goes operationally up
         and the management Ethernet port reverts from the standby CPM to the
         active CPM.

         [EFFECT] The management of the node is operating from the active CPM's
         management Ethernet port and is redundant.

         [RECOVERY] No recovery required."
    ::= { tmnxChassisNotification 122 }

tmnxSyncIfTimBITS2048khzUnsup    NOTIFICATION-TYPE
    OBJECTS     {
        tmnxHwClass
    }
    STATUS      current
    DESCRIPTION
        "[CAUSE] The tmnxSyncIfTimBITS2048khzUnsup notification is generated
         when the value of tSyncIfTimingAdmBITSIfType is set to 'g703-2048khz
         (5)' and the CPM does not meet the specifications for the 2048kHz BITS
         output signal under G.703.

         [EFFECT] The BITS input will not be used as the Sync reference and the
         2048kHz BITS output signal generated by the CPM is squelched.

         [RECOVERY] Replace the CPM with one that is capable of generating the
         2048kHz BITS output signal, or set tSyncIfTimingAdmBITSIfType to a
         value other than 'g703-2048khz (5)'."
    REFERENCE
        "G.703, 'Physical/Electrical Characteristics of Hierarchical Digital
         Interfaces', Section 13, November 2001."
    ::= { tmnxChassisNotification 123 }

tmnxSyncIfTimBITS2048khzUnsupClr NOTIFICATION-TYPE
    OBJECTS     {
        tmnxHwClass
    }
    STATUS      current
    DESCRIPTION
        "[CAUSE] The tmnxSyncIfTimBITS2048khzUnsupClr notification is generated
         when a tmnxSyncIfTimBITS2048khzUnsup notification is outstanding and
         the CPM was replaced with one that meets the specifications for the
         2048kHz BITS output signal under G.703 or tSyncIfTimingAdmBITSIfType
         is set to a value other than 'g703-2048khz (5)'.

         [EFFECT] The CPM can now support the configuration of
         tSyncIfTimingAdmBITSIfType.

         [RECOVERY] No recovery required."
    REFERENCE
        "G.703, 'Physical/Electrical Characteristics of Hierarchical Digital
         Interfaces', Section 13, November 2001."
    ::= { tmnxChassisNotification 124 }

tmnxEqPhysChassPowerSupOvrTmp    NOTIFICATION-TYPE
    OBJECTS     {
        tmnxHwClass,
        tmnxPhysChassPowerSupTempStatus,
        tmnxPhysChassPowerSupTempThrshld
    }
    STATUS      current
    DESCRIPTION
        "[CAUSE] The tmnxEqPhysChassPowerSupOvrTmp notification is generated
         when a power supply's temperature surpasses the threshold of the
         particular physical chassis.

         [EFFECT] The power supply is no longer operational.

         [RECOVERY] Check input feed and/or insert a new power supply."
    ::= { tmnxChassisNotification 125 }

tmnxEqPhysChassPowerSupOvrTmpClr NOTIFICATION-TYPE
    OBJECTS     {
        tmnxHwClass,
        tmnxPhysChassPowerSupTempStatus,
        tmnxPhysChassPowerSupTempThrshld
    }
    STATUS      current
    DESCRIPTION
        "[CAUSE] The tmnxEqPhysChassPowerSupOvrTmpClr notification is generated
         when a power supply's temperature is reduced below the threshold of
         the particular physical chassis.

         [EFFECT] The power supply is operational again.

         [RECOVERY] There is no recovery for this notification."
    ::= { tmnxChassisNotification 126 }

tmnxEqPhysChassPowerSupAcFail    NOTIFICATION-TYPE
    OBJECTS     {
        tmnxHwClass,
        tmnxPhysChassPowerSupACStatus,
        tmnxPhysChassPowerSup1Status,
        tmnxPhysChassPowerSup2Status
    }
    STATUS      current
    DESCRIPTION
        "[CAUSE] The tmnxEqPhysChassPowerSupAcFail notification is generated
         when an AC failure occurs on the power supply.

         [EFFECT] The power supply is no longer operational.

         [RECOVERY] Insert a new power supply."
    ::= { tmnxChassisNotification 127 }

tmnxEqPhysChassPowerSupAcFailClr NOTIFICATION-TYPE
    OBJECTS     {
        tmnxHwClass,
        tmnxPhysChassPowerSupACStatus,
        tmnxPhysChassPowerSup1Status,
        tmnxPhysChassPowerSup2Status
    }
    STATUS      current
    DESCRIPTION
        "[CAUSE] The tmnxEqPhysChassPowerSupAcFailClr notification is generated
         when the AC failure is cleared on the power supply.

         [EFFECT] The power supply is operational again.

         [RECOVERY] There is no recovery for this notification."
    ::= { tmnxChassisNotification 128 }

tmnxEqPhysChassPowerSupDcFail    NOTIFICATION-TYPE
    OBJECTS     {
        tmnxHwClass,
        tmnxPhysChassPowerSupDCStatus,
        tmnxPhysChassPowerSup1Status
    }
    STATUS      current
    DESCRIPTION
        "[CAUSE] The tmnxEqPhysChassPowerSupDcFail notification is generated
         when a DC failure occurs on the power supply.

         [EFFECT] The power supply is no longer operational.

         [RECOVERY] Insert a new power supply."
    ::= { tmnxChassisNotification 129 }

tmnxEqPhysChassPowerSupDcFailClr NOTIFICATION-TYPE
    OBJECTS     {
        tmnxHwClass,
        tmnxPhysChassPowerSupDCStatus,
        tmnxPhysChassPowerSup1Status
    }
    STATUS      current
    DESCRIPTION
        "[CAUSE] The tmnxEqPhysChassPowerSupDcFailClr notification is generated
         when the DC failure is cleared on the power supply.

         [EFFECT] The power supply is operational again.

         [RECOVERY] There is no recovery for this notification."
    ::= { tmnxChassisNotification 130 }

tmnxEqPhysChassPowerSupInFail    NOTIFICATION-TYPE
    OBJECTS     {
        tmnxHwClass,
        tmnxPhysChassPowerSupInputStatus
    }
    STATUS      current
    DESCRIPTION
        "[CAUSE] The tmnxEqPhysChassPowerSupInFail notification is generated
         when an input failure occurs on the power supply.

         [EFFECT] The power supply is no longer operational.

         [RECOVERY] Check input feed and/or insert a new power supply."
    ::= { tmnxChassisNotification 131 }

tmnxEqPhysChassPowerSupInFailClr NOTIFICATION-TYPE
    OBJECTS     {
        tmnxHwClass,
        tmnxPhysChassPowerSupInputStatus
    }
    STATUS      current
    DESCRIPTION
        "[CAUSE] The tmnxEqPhysChassPowerSupInFailClr notification is generated
         when the input failure is cleared on the power supply.

         [EFFECT] The power supply is operational again.

         [RECOVERY] There is no recovery for this notification."
    ::= { tmnxChassisNotification 132 }

tmnxEqPhysChassPowerSupOutFail   NOTIFICATION-TYPE
    OBJECTS     {
        tmnxHwClass,
        tmnxPhysChassPowerSupOutptStatus
    }
    STATUS      current
    DESCRIPTION
        "[CAUSE] The tmnxEqPhysChassPowerSupOutFail notification is generated
         when an output failure occurs on the power supply.

         [EFFECT] The power supply is no longer operational.

         [RECOVERY] Insert a new power supply."
    ::= { tmnxChassisNotification 133 }

tmnxEqPhysChassPowerSupOutFailCl NOTIFICATION-TYPE
    OBJECTS     {
        tmnxHwClass,
        tmnxPhysChassPowerSupOutptStatus
    }
    STATUS      current
    DESCRIPTION
        "[CAUSE] The tmnxEqPhysChassPowerSupOutFailCl notification is generated
         when an output failure is cleared on the power supply.

         [EFFECT] The power supply is operational again.

         [RECOVERY] There is no recovery for this notification."
    ::= { tmnxChassisNotification 134 }

tmnxEqPhysChassisFanFailure      NOTIFICATION-TYPE
    OBJECTS     {
        tmnxHwClass,
        tmnxPhysChassisFanOperStatus,
        tmnxPhysChassisFanSpeedPercent
    }
    STATUS      current
    DESCRIPTION
        "[CAUSE] The tmnxEqPhysChassisFanFailure notification is generated when
         one of the fans in a fan tray fails on a particular physical chassis.

         [EFFECT] The fan is no longer operational.

         [RECOVERY] Insert a new fan."
    ::= { tmnxChassisNotification 135 }

tmnxEqPhysChassisFanFailureClear NOTIFICATION-TYPE
    OBJECTS     {
        tmnxHwClass,
        tmnxPhysChassisFanOperStatus,
        tmnxPhysChassisFanSpeedPercent
    }
    STATUS      current
    DESCRIPTION
        "[CAUSE] The tmnxEqPhysChassisFanFailureClear notification is generated
         when the fan failure is cleared on the particular physical chassis.

         [EFFECT] The fan is operational again.

         [RECOVERY] There is no recovery for this notification."
    ::= { tmnxChassisNotification 136 }

tIPsecIsaMemLowWatermark         NOTIFICATION-TYPE
    OBJECTS     {
        tmnxMDAHwIndex
    }
    STATUS      current
    DESCRIPTION
        "[CAUSE] A tIPsecIsaMemLowWatermark notification is generated when the
         ISA card memory usage ratio has dropped back to the normal level.

         [EFFECT] The system accepts new IKE states.

         [RECOVERY] There is no recovery required for this notification."
    ::= { tmnxChassisNotification 137 }

tIPsecIsaMemHighWatermark        NOTIFICATION-TYPE
    OBJECTS     {
        tmnxMDAHwIndex
    }
    STATUS      current
    DESCRIPTION
        "[CAUSE] A tIPsecIsaMemHighWatermark notification is generated when the
         ISA card memory usage ratio has almost reached the maximum value.

         [EFFECT] The system may stop accepting new IKE states shortly.

         [RECOVERY] Use fewer SAs for each IKE tunnel."
    ::= { tmnxChassisNotification 138 }

tIPsecIsaMemMax                  NOTIFICATION-TYPE
    OBJECTS     {
        tmnxMDAHwIndex
    }
    STATUS      current
    DESCRIPTION
        "[CAUSE] A tIPsecIsaMemMax notification is generated when the ISA card
         memory usage ratio has reached the maximum value.

         [EFFECT] The system stops accepting new IKE states.

         [RECOVERY] Use fewer SAs for each IKE tunnel."
    ::= { tmnxChassisNotification 139 }

tmnxCpmMemSizeMismatch           NOTIFICATION-TYPE
    OBJECTS     {
        tmnxHwClass,
        tmnxChassisNotifyCpmCardSlotNum,
        tmnxChassisNotifyHwIndex
    }
    STATUS      current
    DESCRIPTION
        "[CAUSE] A tmnxCpmMemSizeMismatch notification is generated when the
         RAM memory size of the standby CPM (i.e.,
         tmnxChassisNotifyCpmCardSlotNum) is different than the active CPM
         (i.e., tmnxChassisNotifyHwIndex).

         [EFFECT] There is an increased risk of the memory overflow on the
         standby CPM during the CPM switchover.

         [RECOVERY] Use CPMs with the same memory size."
    ::= { tmnxChassisNotification 140 }

tmnxCpmMemSizeMismatchClear      NOTIFICATION-TYPE
    OBJECTS     {
        tmnxHwClass,
        tmnxChassisNotifyCpmCardSlotNum,
        tmnxChassisNotifyHwIndex
    }
    STATUS      current
    DESCRIPTION
        "[CAUSE] A tmnxCpmMemSizeMismatchClear notification is generated when
         the RAM memory sizes of the standby (i.e.,
         tmnxChassisNotifyCpmCardSlotNum) and active (i.e.,
         tmnxChassisNotifyHwIndex) CPMs become matched.

         [EFFECT] The tmnxCpmMemSizeMismatch notification is cleared.

         [RECOVERY] There is no recovery required for this notification."
    ::= { tmnxChassisNotification 141 }

tmnxPhysChassPwrSupWrgFanDir     NOTIFICATION-TYPE
    OBJECTS     {
        tmnxHwClass,
        tmnxPhysChassPowerSupFanDir
    }
    STATUS      current
    DESCRIPTION
        "[CAUSE] The tmnxPhysChassPwrSupWrgFanDir notification is generated
         when the airflow direction of the power supply's fan is incorrect.

         [EFFECT] The power supply is not cooling properly and may overheat.

         [RECOVERY] Replace the power supply with one that has the proper fan
         direction."
    ::= { tmnxChassisNotification 142 }

tmnxPhysChassPwrSupWrgFanDirClr  NOTIFICATION-TYPE
    OBJECTS     {
        tmnxHwClass,
        tmnxPhysChassPowerSupFanDir
    }
    STATUS      current
    DESCRIPTION
        "[CAUSE] The tmnxPhysChassPwrSupWrgFanDirClr notification is generated
         when the airflow direction of the power supply's fan is corrected.

         [EFFECT] The fan is cooling the power supply in the proper direction.

         [RECOVERY] No recovery required."
    ::= { tmnxChassisNotification 143 }

tmnxPhysChassPwrSupPemACRect     NOTIFICATION-TYPE
    OBJECTS     {
        tmnxHwClass,
        tmnxPhysChassPowerSupPemACRect
    }
    STATUS      current
    DESCRIPTION
        "[CAUSE] The tmnxPhysChassPwrSupPemACRect notification is generated if
         any one of the AC rectifiers for a given power supply is in a failed
         state or is missing.

         [EFFECT] There is an increased risk of the power supply failing,
         causing insufficient power to the system.

         [RECOVERY] Bring the AC rectifiers back online."
    ::= { tmnxChassisNotification 144 }

tmnxPhysChassPwrSupPemACRectClr  NOTIFICATION-TYPE
    OBJECTS     {
        tmnxHwClass,
        tmnxPhysChassPowerSupPemACRect
    }
    STATUS      current
    DESCRIPTION
        "[CAUSE] The tmnxPhysChassPwrSupPemACRectClr notification is generated
         when the last of the failed or missing AC rectifiers has been brought
         back online.

         [EFFECT] The power supply AC rectifiers are fully operational.

         [RECOVERY] No recovery required."
    ::= { tmnxChassisNotification 145 }

tmnxPhysChassPwrSupInputFeed     NOTIFICATION-TYPE
    OBJECTS     {
        tmnxHwClass,
        tmnxPhysChassPowerSupInFeedDown
    }
    STATUS      current
    DESCRIPTION
        "[CAUSE] The tmnxPhysChassPwrSupInputFeed notification is generated if
         any one of the input feeds for a given power supply is not supplying
         power.

         [EFFECT] There is an increased risk of system power brown-outs or
         black-outs.

         [RECOVERY] Restore all of the input feeds that are not supplying
         power."
    ::= { tmnxChassisNotification 146 }

tmnxPhysChassPwrSupInputFeedClr  NOTIFICATION-TYPE
    OBJECTS     {
        tmnxHwClass,
        tmnxPhysChassPowerSupInFeedDown
    }
    STATUS      current
    DESCRIPTION
        "[CAUSE] The tmnxPhysChassPwrSupInputFeedClr notification is generated
         when the last of the missing input feeds has been brought back online.

         [EFFECT] All power supply input feeds are supplying power.

         [RECOVERY] No recovery required."
    ::= { tmnxChassisNotification 147 }

tmnxCardResMacFdbHighUsgSet      NOTIFICATION-TYPE
    OBJECTS     {
        tmnxMacScaleCardSlotNum
    }
    STATUS      current
    DESCRIPTION
        "[CAUSE] The tmnxCardResMacFdbHighUsgSet notification is generated when
         the FDB table size exceeds 95% of the card limit.

         [EFFECT] The FDB table size for the card exceeds 95% of the card
         limit.

         [RECOVERY] None needed."
    ::= { tmnxChassisNotification 148 }

tmnxCardResMacFdbHighUsgClr      NOTIFICATION-TYPE
    OBJECTS     {
        tmnxMacScaleCardSlotNum
    }
    STATUS      current
    DESCRIPTION
        "[CAUSE] The tmnxCardResMacFdbHighUsgClr notification is generated when
         the FDB table size drops below 90% of the card limit.

         [EFFECT] The FDB table size for the card drops below 90% of the card
         limit.

         [RECOVERY] None needed."
    ::= { tmnxChassisNotification 149 }

tmnxEqBpEpromFail                NOTIFICATION-TYPE
    OBJECTS     {
        tmnxHwClass
    }
    STATUS      current
    DESCRIPTION
        "[CAUSE] The tmnxEqBpEpromFail notification is generated when the
         active CPM is no longer able to access the backplane EPROM due to a
         hardware defect.

         [EFFECT] The active CPM is at risk of failing to initialize after node
         reboot due to not being able to access the BP EPROM to read the
         chassis type.

         [RECOVERY] Contact Nokia customer support."
    ::= { tmnxChassisNotification 150 }

tmnxEqBpEpromFailClear           NOTIFICATION-TYPE
    OBJECTS     {
        tmnxHwClass
    }
    STATUS      current
    DESCRIPTION
        "[CAUSE] The tmnxEqBpEpromFailClear notification is generated when the
         EPROM error condition is cleared."
    ::= { tmnxChassisNotification 151 }

tmnxEqBpEpromWarning             NOTIFICATION-TYPE
    OBJECTS     {
        tmnxHwClass
    }
    STATUS      current
    DESCRIPTION
        "[CAUSE] The tmnxEqBpEpromWarning notification is generated when the
         active CPM is no longer able to access one backplane EPROM due to a
         hardware defect but a redundant EPROM is present and accessible.

         [EFFECT] There is no effect on system operation.

         [RECOVERY] No recovery action required."
    ::= { tmnxChassisNotification 152 }

tmnxEqBpEpromWarningClear        NOTIFICATION-TYPE
    OBJECTS     {
        tmnxHwClass
    }
    STATUS      current
    DESCRIPTION
        "[CAUSE] The tmnxEqBpEpromWarningClear notification is generated when
         the backplane EPROM warning condition is cleared."
    ::= { tmnxChassisNotification 153 }

END
