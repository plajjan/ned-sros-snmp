TIMETRA-MC-REDUNDANCY-MIB DEFINITIONS ::= BEGIN

IMPORTS
    InetAddress, InetAddressType
                                                         FROM INET-ADDRESS-MIB
    MODULE-COMPLIANCE, NOTIFICATION-GROUP,
    OBJECT-GROUP
                                                         FROM SNMPv2-CONF
    Counter32, Gauge32, Integer32,
    MODULE-IDENTITY, NOTIFICATION-TYPE,
    OBJECT-TYPE, Unsigned32
                                                         FROM SNMPv2-SMI
    DisplayString, MacAddress, RowStatus,
    TEXTUAL-CONVENTION, TimeInterval,
    TimeStamp, TruthValue
                                                         FROM SNMPv2-TC
    tmnxDiamPlcyName
                                                         FROM TIMETRA-DIAMETER-MIB
    timetraSRMIBModules, tmnxSRConfs,
    tmnxSRNotifyPrefix, tmnxSRObjs
                                                         FROM TIMETRA-GLOBAL-MIB
    sapEncapValue, sapPortId
                                                         FROM TIMETRA-SAP-MIB
    SdpId, svcId, svcTlsInfoEntry
                                                         FROM TIMETRA-SERV-MIB
    TmnxMobGwId
                                                         FROM TIMETRA-TC-MG-MIB
    LAGInterfaceNumber, TItemDescription,
    TNamedItem, TNamedItemOrEmpty,
    TmnxActionType, TmnxAdminState,
    TmnxAdminStateOld, TmnxEnabledDisabled,
    TmnxEncapVal, TmnxOperState, TmnxPortID,
    TmnxServId, TmnxSrrpPriorityStep,
    TmnxTunnelGroupId,
    TmnxTunnelGroupIdOrZero, TmnxVRtrID
                                                         FROM TIMETRA-TC-MIB
    vRtrID, vRtrIfIndex
                                                         FROM TIMETRA-VRTR-MIB
    ;

timetraMcRedundancyMIBModule     MODULE-IDENTITY
    LAST-UPDATED "201601010000Z"
    ORGANIZATION "Nokia"
    CONTACT-INFO
        "Nokia SROS Support
         Web: http://www.nokia.com"
    DESCRIPTION
        "This document is the SNMP MIB module to manage and provision the
         multi-chassis redundancy for the Nokia SROS device.

         Copyright 2006-2017 Nokia. All rights reserved. Reproduction of this
         document is authorized on the condition that the foregoing copyright
         notice is included.

         This SNMP MIB module (Specification) embodies Nokia's proprietary
         intellectual property. Nokia retains all title and ownership in the
         Specification, including any revisions.

         Nokia grants all interested parties a non-exclusive license to use and
         distribute an unmodified copy of this Specification in connection with
         management of Nokia products, and without fee, provided this copyright
         notice and license appear on all copies.

         This Specification is supplied 'as is', and Nokia makes no warranty,
         either express or implied, as to the use, operation, condition, or
         performance of the Specification."

    REVISION    "201601010000Z"
    DESCRIPTION
        "Rev 14.0               1 Jan 2016 00:00
         14.0 release of the TIMETRA-MC-REDUNDANCY-MIB."

    REVISION    "201501010000Z"
    DESCRIPTION
        "Rev 13.0               1 Jan 2015 00:00
         13.0 release of the TIMETRA-MC-REDUNDANCY-MIB."

    REVISION    "201401010000Z"
    DESCRIPTION
        "Rev 12.0               1 Jan 2014 00:00
         12.0 release of the TIMETRA-MC-REDUNDANCY-MIB."

    REVISION    "201102010000Z"
    DESCRIPTION
        "Rev 9.0                1 Feb 2011 00:00
         9.0 release of the TIMETRA-MC-REDUNDANCY-MIB."

    REVISION    "200902280000Z"
    DESCRIPTION
        "Rev 7.0                28 Feb 2009 00:00
         7.0 release of the TIMETRA-MC-REDUNDANCY-MIB."

    REVISION    "200807010000Z"
    DESCRIPTION
        "Rev 6.1                01 Jul 2008 00:00
         6.1 release of the TIMETRA-MC-REDUNDANCY-MIB."

    REVISION    "200801010000Z"
    DESCRIPTION
        "Rev 6.0                01 Jan 2008 00:00
         6.0 release of the TIMETRA-MC-REDUNDANCY-MIB."

    REVISION    "200607250000Z"
    DESCRIPTION
        "Rev 0.1                25 Jul 2006 00:00
         First version of the TIMETRA-MC-REDUNDANCY-MIB."

    ::= { timetraSRMIBModules 40 }

TmnxMcsClientApp                 ::= TEXTUAL-CONVENTION
    STATUS      current
    DESCRIPTION
        "Indicates an Multi-Chassis Synchronization (MCS) client application."
    SYNTAX      INTEGER {
        igmp         (0),
        igmpSnooping (1),
        subMgmtIpoe  (2),
        srrp         (3),
        mcRing       (4),
        mldSnooping  (5),
        dhcpServer   (6),
        subHostTrk   (7),
        subMgmtPppoe (8),
        mcIpsec      (9),
        mld          (10),
        python       (11),
        l2tp         (12),
        diamProxy    (13),
        pimSnpgSap   (14),
        pimSnpgSdp   (15)
    }

TmnxMcsAccessProtection          ::= TEXTUAL-CONVENTION
    STATUS      current
    DESCRIPTION
        "Represents a method to protect access of subscriber traffic to the
         Multi-Chassis Redundancy system(s)."
    SYNTAX      INTEGER {
        srrp (1)
    }

TmnxMcRingOperState              ::= TEXTUAL-CONVENTION
    STATUS      current
    DESCRIPTION
        "The TmnxMcRingOperState data type is an enumerated integer
         that describes the values used to identify the operational state of
         a multi-chassis ring.
                 unknown
                 shutdown
                 configErr
                 noPeer          : the peer has no corresponding ring configured;
                 connected       : the inband control connection with the peer
                                   is operational;
                 broken          : the inband control connection with the peer
                                   has timed out;
                 localBroken     : the inband control connection with the peer
                                   is known to be broken because of a local
                                   failure or local administrative action;
                 conflict        : the inband control connection with the peer
                                   has timed out but the physical connection is
                                   probably still OK; the failure of the inband
                                   signaling connection is caused by some
                                   misconfiguration.
                                   E.g. a conflict between the configuration of
                                   this system and its peer, or a misconfiguration
                                   on one of the ring access node systems.
                 testingRing     : the inband control connection with the peer
                                   is being set up. Waiting for result.
                 halfBroken      : the inband control connection indicates that
                                   the ring is broken in one direction (towards
                                   the peer);
                 waitingForPeer  : verifying if this ring is configured on the
                                   peer."
    SYNTAX      INTEGER {
        unknown        (1),
        shutdown       (2),
        configErr      (3),
        noPeer         (4),
        connected      (5),
        broken         (6),
        localBroken    (7),
        conflict       (8),
        testingRing    (9),
        halfBroken     (10),
        waitingForPeer (11)
    }

TmnxMcRingInbCtrlOperState       ::= TEXTUAL-CONVENTION
    STATUS      current
    DESCRIPTION
        "The TmnxMcRingInbCtrlOperState data type is an enumerated integer
         that describes the values used to identify the operational state of
         a multi-chassis ring's inband control connection.
                 unknown
                 connected       : the inband control connection with the peer
                                   is operational;
                 broken          : the inband control connection with the peer
                                   has timed out;
                 testing         : the inband control connection with the peer
                                   is being set up. Waiting for result.
                 peerDetectsDown : the peer detects that the inband control
                                   connection is down;
                 notConfigured   : the inband control connection with the peer
                                   is not configured."
    SYNTAX      INTEGER {
        unknown         (1),
        connected       (2),
        broken          (3),
        testing         (4),
        peerDetectsDown (5),
        notConfigured   (6)
    }

TmnxMcRingNodeOperState          ::= TEXTUAL-CONVENTION
    STATUS      current
    DESCRIPTION
        "The TmnxMcRingNodeOperState data type is an enumerated integer that
         describes the values used to identify the operational state of a
         multi-chassis ring access node."
    SYNTAX      INTEGER {
        unknown        (1),
        notProvisioned (2),
        configErr      (3),
        notTested      (4),
        testing        (5),
        connected      (6),
        disconnected   (7)
    }

TmnxSrrpAssoBfdIntfSessOperState ::= TEXTUAL-CONVENTION
    STATUS      current
    DESCRIPTION
        "The TmnxSrrpAssoBfdIntfSessOperState data type is an enumerated
         integer that describes the values used to identify the operational
         state of a BFD session the SRRP instance is relying upon for its fast
         triggering mechanism."
    SYNTAX      INTEGER {
        unknown         (1),
        connected       (2),
        broken          (3),
        peerDetectsDown (4),
        notConfigured   (5),
        noResources     (6)
    }

TmnxMcRingType                   ::= TEXTUAL-CONVENTION
    STATUS      current
    DESCRIPTION
        "The TmnxMcRingType data type is an enumerated integer that describes
         the type of the multi-chassis ring."
    SYNTAX      INTEGER {
        layer2 (1),
        layer3 (2)
    }

TMcPeerIPsecTnlGrpMasterState    ::= TEXTUAL-CONVENTION
    STATUS      current
    DESCRIPTION
        "The TMcPeerIPsecTnlGrpMasterState indicates the result of the
         mastership election between this tunnel group entity and its peer.

         The master state can be one of the following:

         discovery   - no election during initial peer discovery interval
         notEligible - no election, and not eligible for mastership
         eligible    - no election, but eligible for mastership
         standby     - elected standby
         master      - elected master"
    SYNTAX      INTEGER {
        discovery   (1),
        notEligible (2),
        eligible    (3),
        standby     (4),
        master      (5)
    }

TMcPeerIPsecTnlGrpProtectionStatus ::= TEXTUAL-CONVENTION
    STATUS      current
    DESCRIPTION
        "The TMcPeerIPsecTnlGrpProtectionStatus value indicates the readiness
         of the tunnel group to perform a forced switchover of mastership from
         the current master chassis to the standby chassis.

         The protection status value can be one of the following:

         nominal  - forcing a mastership switchover may impact traffic
         notReady - forcing a mastership switchover may significantly
                    impact traffic."
    SYNTAX      INTEGER {
        nominal  (1),
        notReady (2)
    }

tmnxMcRedundancy                 OBJECT IDENTIFIER ::= { tmnxSRObjs 40 }

tmnxMcRedundancyObjs             OBJECT IDENTIFIER ::= { tmnxMcRedundancy 1 }

tmnxMcPeerTable                  OBJECT-TYPE
    SYNTAX      SEQUENCE OF TmnxMcPeerEntry
    MAX-ACCESS  not-accessible
    STATUS      current
    DESCRIPTION
        "The tmnxMcPeerTable has an entry for each multi-chassis peer
         configured on this system."
    ::= { tmnxMcRedundancyObjs 1 }

tmnxMcPeerEntry                  OBJECT-TYPE
    SYNTAX      TmnxMcPeerEntry
    MAX-ACCESS  not-accessible
    STATUS      current
    DESCRIPTION
        "Each row entry represents a particular multi-chassis peer. Entries are
         create/deleted by the user."
    INDEX       {
        tmnxMcPeerIpType,
        tmnxMcPeerIpAddr
    }
    ::= { tmnxMcPeerTable 1 }

TmnxMcPeerEntry                  ::= SEQUENCE
{
    tmnxMcPeerIpType                 InetAddressType,
    tmnxMcPeerIpAddr                 InetAddress,
    tmnxMcPeerRowStatus              RowStatus,
    tmnxMcPeerDescription            TItemDescription,
    tmnxMcPeerAuthKey                OCTET STRING,
    tmnxMcPeerSrcIpType              InetAddressType,
    tmnxMcPeerSrcIpAddr              InetAddress,
    tmnxMcPeerAdminState             TmnxAdminStateOld,
    tmnxMcPeerSrcIpOperType          InetAddressType,
    tmnxMcPeerSrcIpOperAddr          InetAddress,
    tmnxMcPeerRingsOperState         TmnxOperState,
    tmnxMcPeerName                   TNamedItemOrEmpty,
    tmnxMcPeerWarmStandby            TruthValue,
    tmnxMcPeerRemoteWarmStandby      TruthValue
}

tmnxMcPeerIpType                 OBJECT-TYPE
    SYNTAX      InetAddressType
    MAX-ACCESS  not-accessible
    STATUS      current
    DESCRIPTION
        "The value of tmnxMcPeerIpType indicates the address type of
         tmnxMcPeerIpAddr."
    ::= { tmnxMcPeerEntry 1 }

tmnxMcPeerIpAddr                 OBJECT-TYPE
    SYNTAX      InetAddress (SIZE (4|16|20))
    MAX-ACCESS  not-accessible
    STATUS      current
    DESCRIPTION
        "The value of tmnxMcPeerIpAddr indicates the address of the
         multi-chassis peer. Its type is specified by tmnxMcPeerIpType.

         It must be a valid unicast address."
    ::= { tmnxMcPeerEntry 2 }

tmnxMcPeerRowStatus              OBJECT-TYPE
    SYNTAX      RowStatus
    MAX-ACCESS  read-create
    STATUS      current
    DESCRIPTION
        "The value of tmnxMcPeerRowStatus is used for creation/deletion of
         multi-chassis peers."
    ::= { tmnxMcPeerEntry 3 }

tmnxMcPeerDescription            OBJECT-TYPE
    SYNTAX      TItemDescription
    MAX-ACCESS  read-create
    STATUS      current
    DESCRIPTION
        "The value of tmnxMcPeerDescription specifies the textual description
         of this multi-chassis peer."
    DEFVAL      { "" }
    ::= { tmnxMcPeerEntry 4 }

tmnxMcPeerAuthKey                OBJECT-TYPE
    SYNTAX      OCTET STRING (SIZE (0..20))
    MAX-ACCESS  read-create
    STATUS      current
    DESCRIPTION
        "The value of tmnxMcPeerAuthKey specifies the authentication key used
         between this node and the multi-chassis peer. The authentication key
         can be any combination of letters or numbers. This object will always
         return an empty string on a read."
    DEFVAL      { ''H }
    ::= { tmnxMcPeerEntry 5 }

tmnxMcPeerSrcIpType              OBJECT-TYPE
    SYNTAX      InetAddressType
    MAX-ACCESS  read-create
    STATUS      current
    DESCRIPTION
        "The value of tmnxMcPeerSrcIpType specifies the address type of
         tmnxMcPeerSrcIpAddr."
    DEFVAL      { unknown }
    ::= { tmnxMcPeerEntry 6 }

tmnxMcPeerSrcIpAddr              OBJECT-TYPE
    SYNTAX      InetAddress (SIZE (0|4|16))
    MAX-ACCESS  read-create
    STATUS      current
    DESCRIPTION
        "The value of tmnxMcPeerSrcIpAddr specifies the source address used to
         communicate with the multi-chassis peer. Its type is specified by
         tmnxMcPeerSrcIpType.

         It must be a valid unicast address."
    DEFVAL      { ''H }
    ::= { tmnxMcPeerEntry 7 }

tmnxMcPeerAdminState             OBJECT-TYPE
    SYNTAX      TmnxAdminStateOld
    MAX-ACCESS  read-create
    STATUS      current
    DESCRIPTION
        "The value of tmnxMcPeerAdminState specifies the administrative state
         of this multi-chassis peer."
    DEFVAL      { outOfService }
    ::= { tmnxMcPeerEntry 8 }

tmnxMcPeerSrcIpOperType          OBJECT-TYPE
    SYNTAX      InetAddressType
    MAX-ACCESS  read-only
    STATUS      current
    DESCRIPTION
        "The value of tmnxMcPeerSrcIpOperType indicates the operational source
         address type of tmnxMcPeerSrcIpOperAddr, the multi-chassis peer source
         IP address."
    ::= { tmnxMcPeerEntry 9 }

tmnxMcPeerSrcIpOperAddr          OBJECT-TYPE
    SYNTAX      InetAddress (SIZE (0|4|16))
    MAX-ACCESS  read-only
    STATUS      current
    DESCRIPTION
        "The value of tmnxMcPeerSrcIpOperAddr indicates the operational source
         address in use to communicate with the multi-chassis peer. Its type is
         specified by tmnxMcPeerSrcIpOperType."
    ::= { tmnxMcPeerEntry 10 }

tmnxMcPeerRingsOperState         OBJECT-TYPE
    SYNTAX      TmnxOperState
    MAX-ACCESS  read-only
    STATUS      current
    DESCRIPTION
        "The value of tmnxMcPeerRingsOperState indicates the operational state
         of this multi-chassis peer with respect to multi-chassis ring
         operation.

         If there are no entries in the tmnxMcRingTable associated with this
         peer, the value of tmnxMcPeerRingsOperState is 'unknown'."
    ::= { tmnxMcPeerEntry 11 }

tmnxMcPeerName                   OBJECT-TYPE
    SYNTAX      TNamedItemOrEmpty
    MAX-ACCESS  read-create
    STATUS      current
    DESCRIPTION
        "The value of tmnxMcPeerName specifies the name of this multi-chassis
         peer."
    DEFVAL      { "" }
    ::= { tmnxMcPeerEntry 12 }

tmnxMcPeerWarmStandby            OBJECT-TYPE
    SYNTAX      TruthValue
    MAX-ACCESS  read-create
    STATUS      current
    DESCRIPTION
        "The value of tmnxMcPeerWarmStandby specifies if this peer operates in
         warm standby mode.

         The value of tmnxMcPeerWarmStandby may only be modified while the
         value of tmnxMcPeerAdminState is equal to 'outOfService'.

         For all peers that are administratively enabled, the value of
         tmnxMcPeerWarmStandby must be the same.

         This object is used for Oversubscribed Multi-Chassis Redundancy
         (OMCR), also referred to as N-to-one redundancy."
    DEFVAL      { false }
    ::= { tmnxMcPeerEntry 15 }

tmnxMcPeerRemoteWarmStandby      OBJECT-TYPE
    SYNTAX      TruthValue
    MAX-ACCESS  read-only
    STATUS      current
    DESCRIPTION
        "The value of tmnxMcPeerRemoteWarmStandby indicates if the remote
         system connected with this peer is known to operate in warm standby
         mode."
    ::= { tmnxMcPeerEntry 16 }

tmnxMcPeerSyncTable              OBJECT-TYPE
    SYNTAX      SEQUENCE OF TmnxMcPeerSyncEntry
    MAX-ACCESS  not-accessible
    STATUS      current
    DESCRIPTION
        "The tmnxMcPeerSyncTable has an entry for each multi-chassis peer
         synchronization protocol."
    ::= { tmnxMcRedundancyObjs 2 }

tmnxMcPeerSyncEntry              OBJECT-TYPE
    SYNTAX      TmnxMcPeerSyncEntry
    MAX-ACCESS  not-accessible
    STATUS      current
    DESCRIPTION
        "Each row entry represents a particular multi-chassis peer
         synchronization protocol. Entries are create/deleted by the user."
    INDEX       {
        tmnxMcPeerIpType,
        tmnxMcPeerIpAddr
    }
    ::= { tmnxMcPeerSyncTable 1 }

TmnxMcPeerSyncEntry              ::= SEQUENCE
{
    tmnxMcPeerSyncRowStatus          RowStatus,
    tmnxMcPeerSyncIgmp               TruthValue,
    tmnxMcPeerSyncIgmpSnooping       TruthValue,
    tmnxMcPeerSyncSubMgmt            TruthValue,
    tmnxMcPeerSyncSrrp               TruthValue,
    tmnxMcPeerSyncAdminState         TmnxAdminStateOld,
    tmnxMcPeerSyncOperState          TmnxOperState,
    tmnxMcPeerSyncOperFlags          BITS,
    tmnxMcPeerSyncStatus             INTEGER,
    tmnxMcPeerSyncLastSyncTime       TimeStamp,
    tmnxMcPeerSyncNumEntries         Counter32,
    tmnxMcPeerSyncLclDeletedEntries  Counter32,
    tmnxMcPeerSyncAlarmedEntries     Counter32,
    tmnxMcPeerSyncRemNumEntries      Counter32,
    tmnxMcPeerSyncRemLclDelEntries   Counter32,
    tmnxMcPeerSyncRemAlarmedEntries  Counter32,
    tmnxMcPeerSyncMcRing             TruthValue,
    tmnxMcPeerSyncMldSnooping        TruthValue,
    tmnxMcPeerSyncDhcpServer         TruthValue,
    tmnxMcPeerSyncSubHostTrk         TruthValue,
    tmnxMcPeerSyncSubMgmtPppoe       TruthValue,
    tmnxMcPeerSyncIpsec              TruthValue,
    tmnxMcPeerSyncMobile             TruthValue,
    tmnxMcPeerSyncOmcrStandby        Counter32,
    tmnxMcPeerSyncOmcrAlarmed        Counter32,
    tmnxMcPeerSyncOmcrRemStandby     Counter32,
    tmnxMcPeerSyncOmcrRemAlarmed     Counter32,
    tmnxMcPeerSyncMld                TruthValue,
    tmnxMcPeerSyncPythonCache        TruthValue,
    tmnxMcPeerSyncL2tp               TruthValue,
    tmnxMcPeerSyncDiameterProxy      TruthValue,
    tmnxMcPeerSyncPimSnpgSap         TruthValue,
    tmnxMcPeerSyncPimSnpgSdp         TruthValue
}

tmnxMcPeerSyncRowStatus          OBJECT-TYPE
    SYNTAX      RowStatus
    MAX-ACCESS  read-create
    STATUS      current
    DESCRIPTION
        "The value of tmnxMcPeerSyncRowStatus is used for creation and deletion
         of a synchronization protocol with a multi-chassis peer."
    ::= { tmnxMcPeerSyncEntry 1 }

tmnxMcPeerSyncIgmp               OBJECT-TYPE
    SYNTAX      TruthValue
    MAX-ACCESS  read-create
    STATUS      current
    DESCRIPTION
        "The value of tmnxMcPeerSyncIgmp specifies whether IGMP protocol
         information should be synchronized with the multi-chassis peer."
    DEFVAL      { false }
    ::= { tmnxMcPeerSyncEntry 2 }

tmnxMcPeerSyncIgmpSnooping       OBJECT-TYPE
    SYNTAX      TruthValue
    MAX-ACCESS  read-create
    STATUS      current
    DESCRIPTION
        "The value of tmnxMcPeerSyncIgmpSnooping specifies whether
         IGMP-snooping information should be synchronized with the
         multi-chassis peer."
    DEFVAL      { false }
    ::= { tmnxMcPeerSyncEntry 3 }

tmnxMcPeerSyncSubMgmt            OBJECT-TYPE
    SYNTAX      TruthValue
    MAX-ACCESS  read-create
    STATUS      current
    DESCRIPTION
        "The value of tmnxMcPeerSyncSubMgmt specifies whether subscriber
         management IPoE information should be synchronized with the
         multi-chassis peer."
    DEFVAL      { false }
    ::= { tmnxMcPeerSyncEntry 4 }

tmnxMcPeerSyncSrrp               OBJECT-TYPE
    SYNTAX      TruthValue
    MAX-ACCESS  read-create
    STATUS      current
    DESCRIPTION
        "The value of tmnxMcPeerSyncSrrp specifies whether SRRP information
         should be synchronized with the multi-chassis peer."
    DEFVAL      { false }
    ::= { tmnxMcPeerSyncEntry 5 }

tmnxMcPeerSyncAdminState         OBJECT-TYPE
    SYNTAX      TmnxAdminStateOld
    MAX-ACCESS  read-create
    STATUS      current
    DESCRIPTION
        "The value of tmnxMcPeerSyncAdminState specifies the administrative
         status of the synchronization protocol with the multi-chassis peer."
    DEFVAL      { outOfService }
    ::= { tmnxMcPeerSyncEntry 6 }

tmnxMcPeerSyncOperState          OBJECT-TYPE
    SYNTAX      TmnxOperState
    MAX-ACCESS  read-only
    STATUS      current
    DESCRIPTION
        "The value of tmnxMcPeerSyncOperState indicates the operational status
         of the synchronization protocol with the multi-chassis peer."
    ::= { tmnxMcPeerSyncEntry 7 }

tmnxMcPeerSyncOperFlags          OBJECT-TYPE
    SYNTAX      BITS {
        syncAdminDown       (0),
        peerAdminDown       (1),
        connectionDown      (2),
        internalError       (3),
        mcsVersionMismatch  (4),
        platformMismatch    (5),
        appVersionMismatch  (6),
        appSupportMismatch  (7),
        omcrVersionMismatch (8),
        omcrStandbyStandby  (9),
        omcrNumEntriesHigh  (10)
    }
    MAX-ACCESS  read-only
    STATUS      current
    DESCRIPTION
        "The value of tmnxMcPeerSyncOperFlags indicates the reason that the
         synchronization protocol with the multi-chassis peer is down.

         syncAdminDown(0)       Synchronization is administratively down.
                                No recovery needed.

         peerAdminDown(1)       The peering is administratively down.
                                No recovery needed.

         connectionDown(2)      There is a problem with the connection to the
                                multi-chassis peer. The connection will be
                                automatically repaired. No recovery needed

         internalError(3)       There has been an irrecoverable internal error.
                                The synchronization protocol cannot come up
                                again without user intervention. The user must
                                set the tmnxMcPeerSyncAdminState to
                                'outOfService', then 'inService'.

         mcsVersionMismatch(4)  There is a mismatch between the versions of the
                                multi-chassis sync protocol running on each
                                peer.

         platformMismatch(5)    There is a mismatch between the platforms of
                                each peer the multi-chassis sync protocol is
                                running on.

         appVersionMismatch(6)  There is a mismatch between the versions of
                                applications attempting to use the
                                multi-chassis sync protocol on the two peers.

         appSupportMismatch(7)  There is a mismatch between the applications
                                supported by the multi-chassis sync protocol on
                                each peer.

         omcrVersionMismatch(8) There is a mismatch between the version of the
                                Oversubscribed Multi-Chassis Redundancy function
                                on the two peers.

         omcrStandbyStandby(9)  In an Oversubscribed Multi-Chassis Redundancy set-up,
                                both peers are standby.

         omcrNumEntriesHigh (10) In the warm standby node of an Oversubscribed Multi-Chassis Redundancy set-up,
                                the number of entries in the MCS database exceeded the
                                maximum for a particular client application."
    ::= { tmnxMcPeerSyncEntry 8 }

tmnxMcPeerSyncStatus             OBJECT-TYPE
    SYNTAX      INTEGER {
        inSync         (1),
        syncInProgress (2),
        outOfSync      (3)
    }
    MAX-ACCESS  read-only
    STATUS      current
    DESCRIPTION
        "The value of tmnxMcPeerSyncStatus indicates the status of the
         synchronization process."
    ::= { tmnxMcPeerSyncEntry 9 }

tmnxMcPeerSyncLastSyncTime       OBJECT-TYPE
    SYNTAX      TimeStamp
    MAX-ACCESS  read-only
    STATUS      current
    DESCRIPTION
        "The value of tmnxMcPeerSyncLastSyncTime indicates the sysUpTime at the
         time the last synchronization with the peer was successful."
    ::= { tmnxMcPeerSyncEntry 10 }

tmnxMcPeerSyncNumEntries         OBJECT-TYPE
    SYNTAX      Counter32
    MAX-ACCESS  read-only
    STATUS      current
    DESCRIPTION
        "The value of tmnxMcPeerSyncNumEntries indicates the total number of
         entries in the MCS database per multi-chassis peer."
    ::= { tmnxMcPeerSyncEntry 11 }

tmnxMcPeerSyncLclDeletedEntries  OBJECT-TYPE
    SYNTAX      Counter32
    MAX-ACCESS  read-only
    STATUS      current
    DESCRIPTION
        "The value of tmnxMcPeerSyncLclDeletedEntries indicates the number of
         locally deleted entries in the MCS database per multi-chassis peer.
         Locally deleted entries are entries that are not being used by the
         local MCS client application."
    ::= { tmnxMcPeerSyncEntry 12 }

tmnxMcPeerSyncAlarmedEntries     OBJECT-TYPE
    SYNTAX      Counter32
    MAX-ACCESS  read-only
    STATUS      current
    DESCRIPTION
        "The value of tmnxMcPeerSyncAlarmedEntries indicates the number of
         alarmed entries in the MCS database per multi-chassis peer. Entries
         with an alarm are entries that are not being used by the local client
         application due to resource constraints."
    ::= { tmnxMcPeerSyncEntry 13 }

tmnxMcPeerSyncRemNumEntries      OBJECT-TYPE
    SYNTAX      Counter32
    MAX-ACCESS  read-only
    STATUS      current
    DESCRIPTION
        "The value of tmnxMcPeerSyncRemNumEntries indicates the total number of
         entries in the MCS database of the multi-chassis peer."
    ::= { tmnxMcPeerSyncEntry 14 }

tmnxMcPeerSyncRemLclDelEntries   OBJECT-TYPE
    SYNTAX      Counter32
    MAX-ACCESS  read-only
    STATUS      current
    DESCRIPTION
        "The value of tmnxMcPeerSyncRemLclDelEntries indicates the number of
         locally deleted entries in the MCS database of the multi-chassis peer.
         Locally deleted entries are entries that are not being used by the
         remote MCS client application."
    ::= { tmnxMcPeerSyncEntry 15 }

tmnxMcPeerSyncRemAlarmedEntries  OBJECT-TYPE
    SYNTAX      Counter32
    MAX-ACCESS  read-only
    STATUS      current
    DESCRIPTION
        "The value of tmnxMcPeerSyncRemAlarmedEntries indicates the number of
         alarmed entries in the MCS database of the multi-chassis peer. Entries
         with an alarm are entries that are not being used by the remote client
         application due to resource constraints."
    ::= { tmnxMcPeerSyncEntry 16 }

tmnxMcPeerSyncMcRing             OBJECT-TYPE
    SYNTAX      TruthValue
    MAX-ACCESS  read-create
    STATUS      current
    DESCRIPTION
        "The value of tmnxMcPeerSyncMcRing specifies whether mc-ring
         information should be synchronized with the multi-chassis peer.

         Setting this object to 'true(1)' enables the synchronization."
    DEFVAL      { false }
    ::= { tmnxMcPeerSyncEntry 17 }

tmnxMcPeerSyncMldSnooping        OBJECT-TYPE
    SYNTAX      TruthValue
    MAX-ACCESS  read-create
    STATUS      current
    DESCRIPTION
        "The value of tmnxMcPeerSyncMldSnooping specifies whether MLD-snooping
         information should be synchronized with the multi-chassis peer.

         Setting this object to 'true(1)' enables the synchronization."
    DEFVAL      { false }
    ::= { tmnxMcPeerSyncEntry 18 }

tmnxMcPeerSyncDhcpServer         OBJECT-TYPE
    SYNTAX      TruthValue
    MAX-ACCESS  read-create
    STATUS      current
    DESCRIPTION
        "The value of tmnxMcPeerSyncDhcpServer specifies whether DHCP Server
         information should be synchronized with the multi-chassis peer.

         Setting this object to 'true(1)' enables the synchronization."
    DEFVAL      { false }
    ::= { tmnxMcPeerSyncEntry 19 }

tmnxMcPeerSyncSubHostTrk         OBJECT-TYPE
    SYNTAX      TruthValue
    MAX-ACCESS  read-create
    STATUS      current
    DESCRIPTION
        "The value of tmnxMcPeerSyncSubHostTrk specifies whether subscriber
         host tracking information should be synchronized with the
         multi-chassis peer.

         Setting this object to 'true(1)' enables the synchronization."
    DEFVAL      { false }
    ::= { tmnxMcPeerSyncEntry 20 }

tmnxMcPeerSyncSubMgmtPppoe       OBJECT-TYPE
    SYNTAX      TruthValue
    MAX-ACCESS  read-create
    STATUS      current
    DESCRIPTION
        "The value of tmnxMcPeerSyncSubMgmtPppoe specifies whether subscriber
         management PPPoE information should be synchronized with the
         multi-chassis peer."
    DEFVAL      { false }
    ::= { tmnxMcPeerSyncEntry 21 }

tmnxMcPeerSyncIpsec              OBJECT-TYPE
    SYNTAX      TruthValue
    MAX-ACCESS  read-create
    STATUS      current
    DESCRIPTION
        "The value of tmnxMcPeerSyncIpsec specifies whether ipsec information
         is synchronized on this multi-chassis peer."
    DEFVAL      { false }
    ::= { tmnxMcPeerSyncEntry 22 }

tmnxMcPeerSyncMobile             OBJECT-TYPE
    SYNTAX      TruthValue
    MAX-ACCESS  read-create
    STATUS      current
    DESCRIPTION
        "The value of tmnxMcPeerSyncMobile specifies whether the mobile
         management information should be synchronized with the multi-chassis
         peer."
    DEFVAL      { false }
    ::= { tmnxMcPeerSyncEntry 25 }

tmnxMcPeerSyncOmcrStandby        OBJECT-TYPE
    SYNTAX      Counter32
    MAX-ACCESS  read-only
    STATUS      current
    DESCRIPTION
        "The value of tmnxMcPeerSyncOmcrStandby indicates the number of
         Oversubscribed Multi-Chassis Redundancy (OMCR) standby entries in the
         MCS database of this multi-chassis peer."
    ::= { tmnxMcPeerSyncEntry 26 }

tmnxMcPeerSyncOmcrAlarmed        OBJECT-TYPE
    SYNTAX      Counter32
    MAX-ACCESS  read-only
    STATUS      current
    DESCRIPTION
        "The value of tmnxMcPeerSyncOmcrAlarmed indicates the number of
         Oversubscribed Multi-Chassis Redundancy (OMCR) alarmed entries in the
         MCS database of this multi-chassis peer."
    ::= { tmnxMcPeerSyncEntry 27 }

tmnxMcPeerSyncOmcrRemStandby     OBJECT-TYPE
    SYNTAX      Counter32
    MAX-ACCESS  read-only
    STATUS      current
    DESCRIPTION
        "The value of tmnxMcPeerSyncOmcrRemStandby indicates the number of
         Oversubscribed Multi-Chassis Redundancy (OMCR) standby entries
         reported by the remote MCR system."
    ::= { tmnxMcPeerSyncEntry 28 }

tmnxMcPeerSyncOmcrRemAlarmed     OBJECT-TYPE
    SYNTAX      Counter32
    MAX-ACCESS  read-only
    STATUS      current
    DESCRIPTION
        "The value of tmnxMcPeerSyncOmcrRemAlarmed indicates the number of
         Oversubscribed Multi-Chassis Redundancy (OMCR) alarmed entries
         reported by the remote MCR system."
    ::= { tmnxMcPeerSyncEntry 29 }

tmnxMcPeerSyncMld                OBJECT-TYPE
    SYNTAX      TruthValue
    MAX-ACCESS  read-create
    STATUS      current
    DESCRIPTION
        "The value of tmnxMcPeerSyncMld specifies whether MLD protocol
         information should be synchronized with the multi-chassis peer."
    DEFVAL      { false }
    ::= { tmnxMcPeerSyncEntry 30 }

tmnxMcPeerSyncPythonCache        OBJECT-TYPE
    SYNTAX      TruthValue
    MAX-ACCESS  read-create
    STATUS      current
    DESCRIPTION
        "The value of tmnxMcPeerSyncPythonCache specifies if Python cache data
         is synchronized with the multi-chassis peer."
    DEFVAL      { false }
    ::= { tmnxMcPeerSyncEntry 31 }

tmnxMcPeerSyncL2tp               OBJECT-TYPE
    SYNTAX      TruthValue
    MAX-ACCESS  read-create
    STATUS      current
    DESCRIPTION
        "The value of tmnxMcPeerSyncL2tp specifies if Layer Two Tunnel Protocol
         (L2TP) data is synchronized with the multi-chassis peer."
    DEFVAL      { false }
    ::= { tmnxMcPeerSyncEntry 32 }

tmnxMcPeerSyncDiameterProxy      OBJECT-TYPE
    SYNTAX      TruthValue
    MAX-ACCESS  read-create
    STATUS      current
    DESCRIPTION
        "The value of tmnxMcPeerSyncDiameterProxy specifies if Diameter Proxy
         data is synchronized with the multi-chassis peer."
    DEFVAL      { false }
    ::= { tmnxMcPeerSyncEntry 33 }

tmnxMcPeerSyncPimSnpgSap         OBJECT-TYPE
    SYNTAX      TruthValue
    MAX-ACCESS  read-create
    STATUS      current
    DESCRIPTION
        "The value of tmnxMcPeerSyncPimSnpgSap specifies if PIM (Protocol
         Independent Multicast) snooping data is synchronized with the
         multi-chassis peer on sap endpoints."
    DEFVAL      { false }
    ::= { tmnxMcPeerSyncEntry 34 }

tmnxMcPeerSyncPimSnpgSdp         OBJECT-TYPE
    SYNTAX      TruthValue
    MAX-ACCESS  read-create
    STATUS      current
    DESCRIPTION
        "The value of tmnxMcPeerSyncPimSnpgSdp specifies if PIM (Protocol
         Independent Multicast) snooping data is synchronized with the
         multi-chassis peer on sdp endpoints."
    DEFVAL      { false }
    ::= { tmnxMcPeerSyncEntry 35 }

tmnxMcPeerSyncPortTable          OBJECT-TYPE
    SYNTAX      SEQUENCE OF TmnxMcPeerSyncPortEntry
    MAX-ACCESS  not-accessible
    STATUS      current
    DESCRIPTION
        "The tmnxMcPeerSyncPortTable has an entry for each port that is being
         synchronized with a multi-chassis peer."
    ::= { tmnxMcRedundancyObjs 3 }

tmnxMcPeerSyncPortEntry          OBJECT-TYPE
    SYNTAX      TmnxMcPeerSyncPortEntry
    MAX-ACCESS  not-accessible
    STATUS      current
    DESCRIPTION
        "Each row entry represents a port to be synchronized. Entries are
         created/deleted by the user."
    INDEX       {
        tmnxMcPeerIpType,
        tmnxMcPeerIpAddr,
        tmnxMcPeerSyncPortId
    }
    ::= { tmnxMcPeerSyncPortTable 1 }

TmnxMcPeerSyncPortEntry          ::= SEQUENCE
{
    tmnxMcPeerSyncPortId             TmnxPortID,
    tmnxMcPeerSyncPortRowStatus      RowStatus,
    tmnxMcPeerSyncPortSyncTag        TNamedItemOrEmpty
}

tmnxMcPeerSyncPortId             OBJECT-TYPE
    SYNTAX      TmnxPortID
    MAX-ACCESS  not-accessible
    STATUS      current
    DESCRIPTION
        "The value of tmnxMcPeerSyncPortId indicates the port to be
         synchronized with the multi-chassis peer."
    ::= { tmnxMcPeerSyncPortEntry 1 }

tmnxMcPeerSyncPortRowStatus      OBJECT-TYPE
    SYNTAX      RowStatus
    MAX-ACCESS  read-create
    STATUS      current
    DESCRIPTION
        "The value of tmnxMcPeerSyncPortRowStatus is used for creation and
         deletion of ports to be synchronized with the multi-chassis peer."
    ::= { tmnxMcPeerSyncPortEntry 2 }

tmnxMcPeerSyncPortSyncTag        OBJECT-TYPE
    SYNTAX      TNamedItemOrEmpty
    MAX-ACCESS  read-create
    STATUS      current
    DESCRIPTION
        "The value of tmnxMcPeerSyncPortSyncTag specifies a synchronization tag
         to be used while synchronizing this port with the multi-chassis peer."
    DEFVAL      { ''H }
    ::= { tmnxMcPeerSyncPortEntry 3 }

tmnxMcPeerSyncPortEncapRangeTable OBJECT-TYPE
    SYNTAX      SEQUENCE OF TmnxMcPeerSyncPortEncapRangeEntry
    MAX-ACCESS  not-accessible
    STATUS      current
    DESCRIPTION
        "The tmnxMcPeerSyncPortEncapRangeTable has an entry for each port
         encapsulation value range to be synchronized with a multi-chassis
         peer."
    ::= { tmnxMcRedundancyObjs 4 }

tmnxMcPeerSyncPortEncapRangeEntry OBJECT-TYPE
    SYNTAX      TmnxMcPeerSyncPortEncapRangeEntry
    MAX-ACCESS  not-accessible
    STATUS      current
    DESCRIPTION
        "Each row entry represents a range of encapsulation values on a port to
         be synchronized with a multi-chassis peer. Entries are created/deleted
         by the user."
    INDEX       {
        tmnxMcPeerIpType,
        tmnxMcPeerIpAddr,
        tmnxMcPeerSyncPortId,
        tmnxMcPeerSyncPortEncapType,
        tmnxMcPeerSyncPortEncapMin,
        tmnxMcPeerSyncPortEncapMax
    }
    ::= { tmnxMcPeerSyncPortEncapRangeTable 1 }

TmnxMcPeerSyncPortEncapRangeEntry ::= SEQUENCE
{
    tmnxMcPeerSyncPortEncapType      INTEGER,
    tmnxMcPeerSyncPortEncapMin       TmnxEncapVal,
    tmnxMcPeerSyncPortEncapMax       TmnxEncapVal,
    tmnxMcPeerSyncPortEncapRowStatus RowStatus,
    tmnxMcPeerSyncPortEncapSyncTag   TNamedItem
}

tmnxMcPeerSyncPortEncapType      OBJECT-TYPE
    SYNTAX      INTEGER {
        dot1q (1),
        qinq  (2)
    }
    MAX-ACCESS  not-accessible
    STATUS      current
    DESCRIPTION
        "The value of tmnxMcPeerSyncPortEncapType indicates the encapsulation
         type used to interpret tmnxMcPeerSyncPortEncapMin and
         tmnxMcPeerSyncPortEncapMax."
    ::= { tmnxMcPeerSyncPortEncapRangeEntry 1 }

tmnxMcPeerSyncPortEncapMin       OBJECT-TYPE
    SYNTAX      TmnxEncapVal
    MAX-ACCESS  not-accessible
    STATUS      current
    DESCRIPTION
        "The value of tmnxMcPeerSyncPortEncapMin indicates the minimum
         encapsulation value on the port indicated by tmnxMcPeerSyncPortId that
         will be synchronized with the multi-chassis peer."
    ::= { tmnxMcPeerSyncPortEncapRangeEntry 2 }

tmnxMcPeerSyncPortEncapMax       OBJECT-TYPE
    SYNTAX      TmnxEncapVal
    MAX-ACCESS  not-accessible
    STATUS      current
    DESCRIPTION
        "The value of tmnxMcPeerSyncPortEncapMax indicates the maximum
         encapsulation value on the port indicated by tmnxMcPeerSyncPortId that
         will be synchronized with the multi-chassis peer."
    ::= { tmnxMcPeerSyncPortEncapRangeEntry 3 }

tmnxMcPeerSyncPortEncapRowStatus OBJECT-TYPE
    SYNTAX      RowStatus
    MAX-ACCESS  read-create
    STATUS      current
    DESCRIPTION
        "The value of tmnxMcPeerSyncPortEncapRowStatus is used for creation and
         deletion of encapsulation value ranges over a specific port to be
         synchronized with the multi-chassis peer."
    ::= { tmnxMcPeerSyncPortEncapRangeEntry 4 }

tmnxMcPeerSyncPortEncapSyncTag   OBJECT-TYPE
    SYNTAX      TNamedItem
    MAX-ACCESS  read-create
    STATUS      current
    DESCRIPTION
        "The value of tmnxMcPeerSyncPortEncapSyncTag specifies a
         synchronization tag to be used while synchronizing this encapsulation
         value range with the multi-chassis peer. This object MUST be specified
         at row creation time."
    ::= { tmnxMcPeerSyncPortEncapRangeEntry 5 }

tmnxMcLagConfigTableLastChanged  OBJECT-TYPE
    SYNTAX      TimeStamp
    MAX-ACCESS  read-only
    STATUS      current
    DESCRIPTION
        "The value of tmnxMcLagConfigTableLastChanged indicates the sysUpTime
         at the time of the last modification of an entry in the
         tmnxMcLagConfigTable.

         If no changes were made to the table since the last re-initialization
         of the local network management subsystem, then this object contains a
         zero value."
    ::= { tmnxMcRedundancyObjs 5 }

tmnxMcLagConfigTable             OBJECT-TYPE
    SYNTAX      SEQUENCE OF TmnxMcLagConfigEntry
    MAX-ACCESS  not-accessible
    STATUS      current
    DESCRIPTION
        "The tmnxMcLagConfigTable has an entry for each multi-chassis LAG
         configuration for the indicated peer."
    ::= { tmnxMcRedundancyObjs 6 }

tmnxMcLagConfigEntry             OBJECT-TYPE
    SYNTAX      TmnxMcLagConfigEntry
    MAX-ACCESS  not-accessible
    STATUS      current
    DESCRIPTION
        "Each row entry represents configuration data for a multi-chassis LAG
         configuration with a given peer.

         Rows are created or removed automatically by the system, each time a
         row is created or deleted in the tmnxMcPeerTable."
    INDEX       {
        tmnxMcPeerIpType,
        tmnxMcPeerIpAddr
    }
    ::= { tmnxMcLagConfigTable 1 }

TmnxMcLagConfigEntry             ::= SEQUENCE
{
    tmnxMcLagConfigPeerLastChanged   TimeStamp,
    tmnxMcLagConfigPeerAdminstate    TmnxAdminState,
    tmnxMcLagConfigKeepALiveIvl      Unsigned32,
    tmnxMcLagConfigHoldOnNgbrFailure Unsigned32,
    tmnxMcLagConfigOperState         INTEGER,
    tmnxMcLagConfigPeerLastStateChge TimeStamp
}

tmnxMcLagConfigPeerLastChanged   OBJECT-TYPE
    SYNTAX      TimeStamp
    MAX-ACCESS  read-only
    STATUS      current
    DESCRIPTION
        "The value of tmnxMcLagConfigPeerLastChanged indicates the sysUpTime at
         the time of the last modification of this entry.

         If no changes were made to the entry since the last re-initialization
         of the local network management subsystem, then this object contains a
         zero value."
    ::= { tmnxMcLagConfigEntry 1 }

tmnxMcLagConfigPeerAdminstate    OBJECT-TYPE
    SYNTAX      TmnxAdminState
    MAX-ACCESS  read-write
    STATUS      current
    DESCRIPTION
        "The value of tmnxMcLagConfigPeerAdminstate specifies the
         administrative state of the multi-chassis lag with the indicated peer."
    DEFVAL      { outOfService }
    ::= { tmnxMcLagConfigEntry 2 }

tmnxMcLagConfigKeepALiveIvl      OBJECT-TYPE
    SYNTAX      Unsigned32 (5..500)
    UNITS       "deci-seconds"
    MAX-ACCESS  read-write
    STATUS      current
    DESCRIPTION
        "The value of tmnxMcLagConfigKeepALiveIvl specifies the mc-lag
         keepalive timer value in units of 0.1 sec. This defines the interval
         at which keep-alive messages are exchanged between two systems
         participating in mc-lag. These keep-alive messages are used to
         determine remote-node failure."
    DEFVAL      { 10 }
    ::= { tmnxMcLagConfigEntry 3 }

tmnxMcLagConfigHoldOnNgbrFailure OBJECT-TYPE
    SYNTAX      Unsigned32 (2..25)
    MAX-ACCESS  read-write
    STATUS      current
    DESCRIPTION
        "The value of tmnxMcLagConfigHoldOnNgbrFailure specifies how many
         tmnxMcLagConfigKeepALiveIvl intervals the standby node will wait for
         packets from the active node before assuming a redundant-neighbor node
         failure.

         This delay in switch-over operation is required to accommodate for
         different factors influencing node failure detection rate, such as IGP
         convergence, or HA switch-over times and to prevent that the standby
         node takes actions prematurely."
    DEFVAL      { 3 }
    ::= { tmnxMcLagConfigEntry 4 }

tmnxMcLagConfigOperState         OBJECT-TYPE
    SYNTAX      INTEGER {
        inService    (0),
        outOfService (1)
    }
    MAX-ACCESS  read-only
    STATUS      current
    DESCRIPTION
        "The value of tmnxMcLagConfigOperState indicates the operational status
         of this multi-chassis LAG peer."
    ::= { tmnxMcLagConfigEntry 5 }

tmnxMcLagConfigPeerLastStateChge OBJECT-TYPE
    SYNTAX      TimeStamp
    MAX-ACCESS  read-only
    STATUS      current
    DESCRIPTION
        "The value of tmnxMcLagConfigPeerLastStateChge indicates the sysUpTime
         at the time of the last operational state  change for this
         multi-chassis LAG peer.

         If no changes were made since the last re-initialization of the local
         network management subsystem, then this object contains a zero value."
    ::= { tmnxMcLagConfigEntry 6 }

tmnxMcLagConfigLagTableLastChanged OBJECT-TYPE
    SYNTAX      TimeStamp
    MAX-ACCESS  read-only
    STATUS      current
    DESCRIPTION
        "The value of tmnxMcLagConfigLagTableLastChanged indicates the
         sysUpTime at the time of the last modification of an entry in the
         tmnxMcLagConfigLagTable.

         If no changes were made to the table since the last re-initialization
         of the local network management subsystem, then this object contains a
         zero value."
    ::= { tmnxMcRedundancyObjs 7 }

tmnxMcLagConfigLagTable          OBJECT-TYPE
    SYNTAX      SEQUENCE OF TmnxMcLagConfigLagEntry
    MAX-ACCESS  not-accessible
    STATUS      current
    DESCRIPTION
        "The tmnxMcLagConfigLagTable has an entry for each lag that
         participates in a multi-chassis configuration for the indicated peer."
    ::= { tmnxMcRedundancyObjs 8 }

tmnxMcLagConfigLagEntry          OBJECT-TYPE
    SYNTAX      TmnxMcLagConfigLagEntry
    MAX-ACCESS  not-accessible
    STATUS      current
    DESCRIPTION
        "Each row entry represents configuration data for a lag that
         participates in a multi-chassis configuration with a given peer.

         Rows can be created and deleted by the operator."
    INDEX       {
        tmnxMcPeerIpType,
        tmnxMcPeerIpAddr,
        tmnxMcLagConfigLagId
    }
    ::= { tmnxMcLagConfigLagTable 1 }

TmnxMcLagConfigLagEntry          ::= SEQUENCE
{
    tmnxMcLagConfigLagId             LAGInterfaceNumber,
    tmnxMcLagConfigLagLastChanged    TimeStamp,
    tmnxMcLagConfigLagRowStatus      RowStatus,
    tmnxMcLagConfigLaglacpKey        Unsigned32,
    tmnxMcLagConfigLagSystemId       OCTET STRING,
    tmnxMcLagConfigLagSystemPriority Unsigned32,
    tmnxMcLagConfigLagRemoteLagId    LAGInterfaceNumber,
    tmnxMcLagConfigLagSrcBMacLSB     Unsigned32,
    tmnxMcLagConfigLagOperSrcBMacLSB Unsigned32
}

tmnxMcLagConfigLagId             OBJECT-TYPE
    SYNTAX      LAGInterfaceNumber
    MAX-ACCESS  not-accessible
    STATUS      current
    DESCRIPTION
        "The value of tmnxMcLagConfigLagId identifies the Link Aggregation
         Group on this system that is to form a mc-lag configuration with the
         indicated peer."
    ::= { tmnxMcLagConfigLagEntry 1 }

tmnxMcLagConfigLagLastChanged    OBJECT-TYPE
    SYNTAX      TimeStamp
    MAX-ACCESS  read-only
    STATUS      current
    DESCRIPTION
        "The value of tmnxMcLagConfigLagLastChanged indicates the sysUpTime at
         the time of the last modification of this entry.

         If no changes were made to the entry since the last re-initialization
         of the local network management subsystem, then this object contains a
         zero value."
    ::= { tmnxMcLagConfigLagEntry 2 }

tmnxMcLagConfigLagRowStatus      OBJECT-TYPE
    SYNTAX      RowStatus
    MAX-ACCESS  read-create
    STATUS      current
    DESCRIPTION
        "The value of tmnxMcLagConfigLagRowStatus specifies the row status of
         this row."
    ::= { tmnxMcLagConfigLagEntry 3 }

tmnxMcLagConfigLaglacpKey        OBJECT-TYPE
    SYNTAX      Unsigned32 (0..65535)
    MAX-ACCESS  read-create
    STATUS      current
    DESCRIPTION
        "The value of tmnxMcLagConfigLaglacpKey specifies a 16bit key that
         needs to be configured in the same manner on both sides of the mc-lag
         in order for the mc-lag to come up.

         The value of tmnxMcLagConfigLaglacpKey must be 0 when the value of
         tLagStandbySignaling of the corresponding LAG is 'powerOff (2)'.

         The value of tmnxMcLagConfigLaglacpKey cannot be 0 when the value of
         tLagStandbySignaling of the corresponding LAG is 'lacp (1)'."
    ::= { tmnxMcLagConfigLagEntry 4 }

tmnxMcLagConfigLagSystemId       OBJECT-TYPE
    SYNTAX      OCTET STRING (SIZE (6))
    MAX-ACCESS  read-create
    STATUS      current
    DESCRIPTION
        "The value of tmnxMcLagConfigLagSystemId specifies the system-id to be
         used in the context of mc-lag operation. The partner system will
         consider all ports using the same system-id, system priority and
         lacp-key as part of the same lag.

         In order to achieve this in mc-lag operation, both systems have to be
         configured with the same values.

         As long as the system does not have the connection with its redundant
         peer, it will use the locally defined value (chassis MAC address).
         After detecting a redundant node failure, the previously active system
         will keep on using the system-id configured here, while the standby
         system will switch to its locally defined value.

         The value of this object must be all zeroes when the value of
         tLagStandbySignaling of the corresponding LAG is 'powerOff (2)'.

         The value of this object cannot be all zeroes when the value of
         tLagStandbySignaling of the corresponding LAG is 'lacp (1)'."
    ::= { tmnxMcLagConfigLagEntry 5 }

tmnxMcLagConfigLagSystemPriority OBJECT-TYPE
    SYNTAX      Unsigned32 (0..65535)
    MAX-ACCESS  read-create
    STATUS      current
    DESCRIPTION
        "The value of tmnxMcLagConfigLagSystemPriority specifies the system
         priority to be used in the context of mc-lag.  The partner system will
         consider all ports using the same system-id, system priority and
         lacp-key as part of the same lag.

         In order to achieve this in mc-lag operation, both systems have to be
         configured with the same values.

         A low numeric value specifies a high system priority.

         The value of this object must be 0 when the value of
         tLagStandbySignaling of the corresponding LAG is 'powerOff (2)'.

         The value of this object cannot be 0 when the value of
         tLagStandbySignaling of the corresponding LAG is 'lacp (1)'."
    ::= { tmnxMcLagConfigLagEntry 6 }

tmnxMcLagConfigLagRemoteLagId    OBJECT-TYPE
    SYNTAX      LAGInterfaceNumber
    MAX-ACCESS  read-create
    STATUS      current
    DESCRIPTION
        "The value of tmnxMcLagConfigLagRemoteLagId specifies the Lag ID on the
         remote system.

         If not specified, the value of this object will be set to the value of
         tmnxMcLagConfigLagId."
    ::= { tmnxMcLagConfigLagEntry 7 }

tmnxMcLagConfigLagSrcBMacLSB     OBJECT-TYPE
    SYNTAX      Unsigned32 (0 | 1..65535 | 4294967295)
    MAX-ACCESS  read-create
    STATUS      current
    DESCRIPTION
        "The value of tmnxMcLagConfigLagSrcBMacLSB specifies the value of last
         16-bits of the MAC address used for all the traffic ingressing the
         MC-Lag links.

         The value '4294967295' indicates use of the lacp-key as source
         backbone MAC address LSB."
    DEFVAL      { 0 }
    ::= { tmnxMcLagConfigLagEntry 8 }

tmnxMcLagConfigLagOperSrcBMacLSB OBJECT-TYPE
    SYNTAX      Unsigned32
    MAX-ACCESS  read-only
    STATUS      current
    DESCRIPTION
        "The value of tmnxMcLagConfigLagOperSrcBMacLSB indicates the
         operational value of last 16-bits of the MAC address used for all the
         traffic ingressing the MC-Lag links."
    ::= { tmnxMcLagConfigLagEntry 9 }

tmnxSrrpOperTable                OBJECT-TYPE
    SYNTAX      SEQUENCE OF TmnxSrrpOperEntry
    MAX-ACCESS  not-accessible
    STATUS      current
    DESCRIPTION
        "The tmnxSrrpOperTable has an entry for each Subscriber Router
         Redundancy Protocol instance configured on this system."
    ::= { tmnxMcRedundancyObjs 9 }

tmnxSrrpOperEntry                OBJECT-TYPE
    SYNTAX      TmnxSrrpOperEntry
    MAX-ACCESS  not-accessible
    STATUS      current
    DESCRIPTION
        "Each row entry represents a particular SRRP instance tied to a service
         group interface. Entries are created/deleted by the user."
    INDEX       {
        vRtrID,
        vRtrIfIndex,
        tmnxSrrpOperID
    }
    ::= { tmnxSrrpOperTable 1 }

TmnxSrrpOperEntry                ::= SEQUENCE
{
    tmnxSrrpOperID                   Unsigned32,
    tmnxSrrpOperRowStatus            RowStatus,
    tmnxSrrpOperDescription          TItemDescription,
    tmnxSrrpOperGwMac                MacAddress,
    tmnxSrrpOperGwOperMac            MacAddress,
    tmnxSrrpOperPriority             Unsigned32,
    tmnxSrrpOperInUsePriority        Unsigned32,
    tmnxSrrpOperMasterPriority       Unsigned32,
    tmnxSrrpOperKeepAliveInterval    Unsigned32,
    tmnxSrrpOperMsgPathSapPortId     TmnxPortID,
    tmnxSrrpOperMsgPathSapEncapVal   TmnxEncapVal,
    tmnxSrrpOperAdminState           TmnxAdminState,
    tmnxSrrpOperState                INTEGER,
    tmnxSrrpOperMasterSince          TimeStamp,
    tmnxSrrpOperVrrpPolicy1          Unsigned32,
    tmnxSrrpOperVrrpPolicy2          Unsigned32,
    tmnxSrrpOperFlags                BITS,
    tmnxSrrpOperMasterDownInterval   TimeInterval,
    tmnxSrrpOperMasterDownTimer      TimeInterval,
    tmnxSrrpOperSendFibPopulation    INTEGER,
    tmnxSrrpOperPreempt              TruthValue,
    tmnxSrrpOperOneGarpPerSap        TruthValue,
    tmnxSrrpOperMonitorOperGrp       TNamedItemOrEmpty,
    tmnxSrrpOperPriorityStep         TmnxSrrpPriorityStep,
    tmnxSrrpOperDomain               TNamedItemOrEmpty,
    tmnxSrrpOperDomainColor          Unsigned32,
    tmnxSrrpOperDownReason           INTEGER
}

tmnxSrrpOperID                   OBJECT-TYPE
    SYNTAX      Unsigned32
    MAX-ACCESS  not-accessible
    STATUS      current
    DESCRIPTION
        "The value of tmnxSrrpOperID indicates the unique SRRP ID of this SRRP
         instance."
    ::= { tmnxSrrpOperEntry 1 }

tmnxSrrpOperRowStatus            OBJECT-TYPE
    SYNTAX      RowStatus
    MAX-ACCESS  read-create
    STATUS      current
    DESCRIPTION
        "The value of tmnxSrrpOperRowStatus is used for creation/deletion of
         SRRP instances."
    ::= { tmnxSrrpOperEntry 2 }

tmnxSrrpOperDescription          OBJECT-TYPE
    SYNTAX      TItemDescription
    MAX-ACCESS  read-create
    STATUS      current
    DESCRIPTION
        "The value of tmnxSrrpOperDescription specifies the textual description
         of this SRRP instance."
    DEFVAL      { "" }
    ::= { tmnxSrrpOperEntry 3 }

tmnxSrrpOperGwMac                OBJECT-TYPE
    SYNTAX      MacAddress
    MAX-ACCESS  read-create
    STATUS      current
    DESCRIPTION
        "The value of tmnxSrrpOperGwMac specifies the MAC address used to
         override the default SRRP gateway MAC."
    DEFVAL      { '000000000000'H }
    ::= { tmnxSrrpOperEntry 4 }

tmnxSrrpOperGwOperMac            OBJECT-TYPE
    SYNTAX      MacAddress
    MAX-ACCESS  read-only
    STATUS      current
    DESCRIPTION
        "The value of tmnxSrrpOperGwOperMac indicates the operational MAC
         address used by this SRRP instance. When tmnxSrrpOperGwMac is set to
         the default, this address is calculated as the base VRRP MAC address
         with the last octet overridden by the lower 8 bits of tmnxSrrpOperID."
    ::= { tmnxSrrpOperEntry 5 }

tmnxSrrpOperPriority             OBJECT-TYPE
    SYNTAX      Unsigned32 (0..255)
    MAX-ACCESS  read-create
    STATUS      current
    DESCRIPTION
        "The value of tmnxSrrpOperPriority specifies the priority of this SRRP
         instance advertised to the neighbor router. It is compared to the
         neighbor router's priority, and the SRRP instance with the higher
         priority enters the master state and the one with the lower priority
         enters the backup state. If the priorities are identical, the system
         IP addresses are used as a tie-breaker."
    DEFVAL      { 100 }
    ::= { tmnxSrrpOperEntry 6 }

tmnxSrrpOperInUsePriority        OBJECT-TYPE
    SYNTAX      Unsigned32
    MAX-ACCESS  read-only
    STATUS      current
    DESCRIPTION
        "The value of tmnxSrrpOperInUsePriority indicates the the current
         in-use priority of this SRRP instance. This value will be different
         from the base priority set by tmnxSrrpOperPriority when it is changed
         by a VRRP event."
    ::= { tmnxSrrpOperEntry 7 }

tmnxSrrpOperMasterPriority       OBJECT-TYPE
    SYNTAX      Unsigned32
    MAX-ACCESS  read-only
    STATUS      current
    DESCRIPTION
        "The value of tmnxSrrpOperMasterPriority indicates the the current
         priority of the Master for this SRRP instance."
    ::= { tmnxSrrpOperEntry 8 }

tmnxSrrpOperKeepAliveInterval    OBJECT-TYPE
    SYNTAX      Unsigned32 (1..100)
    UNITS       "hundreds of milli-seconds"
    MAX-ACCESS  read-create
    STATUS      current
    DESCRIPTION
        "The value of tmnxSrrpOperKeepAliveInterval specifies the interval
         between SRRP advertisement messages send when operating in the master
         state."
    DEFVAL      { 10 }
    ::= { tmnxSrrpOperEntry 9 }

tmnxSrrpOperMsgPathSapPortId     OBJECT-TYPE
    SYNTAX      TmnxPortID
    MAX-ACCESS  read-create
    STATUS      current
    DESCRIPTION
        "The value of tmnxSrrpOperMsgPathSapPortId specifies the port ID of the
         SAP on which this SRRP instance will send its advertisements. This
         object MUST be set along with tmnxSrrpOperMsgPathSapEncapVal in the
         same SNMP PDU."
    DEFVAL      { 0 }
    ::= { tmnxSrrpOperEntry 10 }

tmnxSrrpOperMsgPathSapEncapVal   OBJECT-TYPE
    SYNTAX      TmnxEncapVal
    MAX-ACCESS  read-create
    STATUS      current
    DESCRIPTION
        "The value of tmnxSrrpOperMsgPathSapEncapVal specifies the
         encapsulation value of the SAP on which this SRRP instance will send
         its advertisements. This object MUST be set along with
         tmnxSrrpOperMsgPathSapPortId in the same SNMP PDU."
    DEFVAL      { 0 }
    ::= { tmnxSrrpOperEntry 11 }

tmnxSrrpOperAdminState           OBJECT-TYPE
    SYNTAX      TmnxAdminState
    MAX-ACCESS  read-create
    STATUS      current
    DESCRIPTION
        "The value of tmnxSrrpOperAdminState specifies the administrative state
         of this SRRP instance."
    DEFVAL      { outOfService }
    ::= { tmnxSrrpOperEntry 12 }

tmnxSrrpOperState                OBJECT-TYPE
    SYNTAX      INTEGER {
        disabled       (0),
        initialize     (1),
        backupRouting  (2),
        backupShunt    (3),
        pendingRouting (4),
        pendingShunt   (5),
        pendingMaster  (6),
        master         (7)
    }
    MAX-ACCESS  read-only
    STATUS      current
    DESCRIPTION
        "The value of tmnxSrrpOperState indicates the operational state of this
         SRRP instance.

         disabled(0)      The SRRP instance is administratively down.
         initialize(1)    The SRRP instance is operationally down or is
                          starting to discover its neighbor.
         backupRouting(2) The SRRP instance is in backup mode, but it is still
                          forwarding traffic. The MAC address used to forward
                          traffic is the native MAC address of the interface
                          SRRP is running on.
         backupShunt(3)   The SRRP instance is in backup mode. Any traffic it
                          receives will be forwarded to the spoke-sdp on the
                          redundant interface tied to the group interface this
                          instance is running on.
         pendingRouting(4)The SRRP instance is in backup mode. A transient
                          state when a master/pending-master is preempted and
                          before it is going to backupRouting state. In this
                          state, traffic destined to the SRRP gateway mac
                          address received from a group interface will still
                          be accepted and forwarded.
         pendingShunt(5)  The SRRP instance is in backup mode. A transient
                          state when a master/pending-master is preempted and
                          before it is going to backupShunt state. In this
                          state, traffic destined to the SRRP gateway mac
                          address received from a group interface will still
                          be accepted and forwarded.
         pendingMaster(6) The SRRP instance is in master mode. All traffic is
                          forwarded using the native MAC address of the interface
                          SRRP is running on.
         master(7)        The SRRP instance is in master mode. All traffic is
                          forwarded using the gateway MAC address of this SRRP
                          instance."
    ::= { tmnxSrrpOperEntry 13 }

tmnxSrrpOperMasterSince          OBJECT-TYPE
    SYNTAX      TimeStamp
    MAX-ACCESS  read-only
    STATUS      current
    DESCRIPTION
        "The value of tmnxSrrpOperMasterSince indicates the sysUpTime when the
         last master was chosen. When this instance is master, it indicates
         when it first became master. When it is backup, it indicates when the
         first SRRP advertisement message from the current SRRP master was
         received."
    ::= { tmnxSrrpOperEntry 14 }

tmnxSrrpOperVrrpPolicy1          OBJECT-TYPE
    SYNTAX      Unsigned32
    MAX-ACCESS  read-create
    STATUS      current
    DESCRIPTION
        "The value of tmnxSrrpOperVrrpPolicy1 specifies the first VRRP control
         policy associated with this SRRP instance."
    DEFVAL      { 0 }
    ::= { tmnxSrrpOperEntry 15 }

tmnxSrrpOperVrrpPolicy2          OBJECT-TYPE
    SYNTAX      Unsigned32
    MAX-ACCESS  read-create
    STATUS      current
    DESCRIPTION
        "The value of tmnxSrrpOperVrrpPolicy2 specifies the second VRRP control
         policy associated with this SRRP instance."
    DEFVAL      { 0 }
    ::= { tmnxSrrpOperEntry 16 }

tmnxSrrpOperFlags                OBJECT-TYPE
    SYNTAX      BITS {
        subnetMismatch (0),
        srrpIdMismatch (1),
        sapMismatch    (2),
        sapTagMismatch (3),
        redIfMismatch  (4),
        dualMaster     (5),
        dupSubIfAddr   (6)
    }
    MAX-ACCESS  read-only
    STATUS      current
    DESCRIPTION
        "The value of tmnxSrrpOperFlags indicates the operational status of
         this SRRP instance.

         subnetMismatch(0)      One the subnets that SRRP is backing up
                                does not have a match with the peer.

         srrpIdMismatch(1)      The peer has a different SRRP instance ID
                                backing the same subnet.

         sapMismatch(2)         The local SRRP instance is backing a different
                                set of SAPs than the peer.

         sapTagMismatch(3)      The local SRRP instance is backing a set of
                                SAPs with different remote and local tags.

         redIfMismatch(4)       The local SRRP instance and remote SRRP
                                instance have mismatching redundant interfaces.

         dualMaster(5)          Both SRRP instances are master at the same time.

         dupSubIfAddr(6)        The IP address for a local subscriber interface
                                conflicts with the IP address for a remote
                                subscriber interface."
    ::= { tmnxSrrpOperEntry 17 }

tmnxSrrpOperMasterDownInterval   OBJECT-TYPE
    SYNTAX      TimeInterval
    UNITS       "milliseconds"
    MAX-ACCESS  read-only
    STATUS      current
    DESCRIPTION
        "The value of tmnxSrrpOperMasterDownInterval indicates the time
         interval for the backup router to declare the master as down.
         It is calculated as
                (3 * Advertisement_Interval) + Skew_time
         where Skew_Time is calculated as
                (256 - Priority) / 256."
    ::= { tmnxSrrpOperEntry 18 }

tmnxSrrpOperMasterDownTimer      OBJECT-TYPE
    SYNTAX      TimeInterval
    UNITS       "milliseconds"
    MAX-ACCESS  read-only
    STATUS      current
    DESCRIPTION
        "The value of tmnxSrrpOperMasterDownTimer indicates the current value
         of the Master Down Timer.

         When a backup router receives an SRRP advertisement from a master, it
         resets this timer to the value of the Master Down Interval and begins
         to count down. If the backup router does not receive an advertisement
         till this timer times out, it will assume that the master is down and
         will declare itself to be the master."
    ::= { tmnxSrrpOperEntry 19 }

tmnxSrrpOperSendFibPopulation    OBJECT-TYPE
    SYNTAX      INTEGER {
        all          (1),
        outerTagOnly (2)
    }
    MAX-ACCESS  read-create
    STATUS      current
    DESCRIPTION
        "The value of tmnxSrrpOperSendFibPopulation specifies the mode used to
         send FIB population packets on this SRRP instance.

         When the value of tmnxSrrpOperSendFibPopulation is set to 'all', FIB
         population packets are sent for every subscriber VLAN.

         When the value of tmnxSrrpOperSendFibPopulation is set to
         'outerTagOnly', FIB population packets are sent only on outer VLANs
         when the group interface SAPs are QinQ encapsulated."
    DEFVAL      { all }
    ::= { tmnxSrrpOperEntry 20 }

tmnxSrrpOperPreempt              OBJECT-TYPE
    SYNTAX      TruthValue
    MAX-ACCESS  read-create
    STATUS      current
    DESCRIPTION
        "The value of tmnxSrrpOperPreempt specifies whether to allow SRRP
         instance to override an existing master."
    DEFVAL      { true }
    ::= { tmnxSrrpOperEntry 21 }

tmnxSrrpOperOneGarpPerSap        OBJECT-TYPE
    SYNTAX      TruthValue
    MAX-ACCESS  read-create
    STATUS      current
    DESCRIPTION
        "The value of tmnxSrrpOperOneGarpPerSap specifies whether to send one
         gratuitous ARP for each SAP."
    DEFVAL      { false }
    ::= { tmnxSrrpOperEntry 22 }

tmnxSrrpOperMonitorOperGrp       OBJECT-TYPE
    SYNTAX      TNamedItemOrEmpty
    MAX-ACCESS  read-create
    STATUS      current
    DESCRIPTION
        "The value of tmnxSrrpOperMonitorOperGrp specifies the name of the
         monitoring operation group."
    DEFVAL      { ''H }
    ::= { tmnxSrrpOperEntry 23 }

tmnxSrrpOperPriorityStep         OBJECT-TYPE
    SYNTAX      TmnxSrrpPriorityStep
    MAX-ACCESS  read-create
    STATUS      current
    DESCRIPTION
        "The value of tmnxSrrpOperPriorityStep specifies the value by which the
         advertisement priority is decremented whenever a member of the
         operational-group monitored goes down.

         An 'inconsistentValue' error is returned if tmnxSrrpOperPriorityStep
         is set to non-default value and tmnxSrrpOperMonitorOperGrp is set to
         its default value."
    DEFVAL      { 0 }
    ::= { tmnxSrrpOperEntry 24 }

tmnxSrrpOperDomain               OBJECT-TYPE
    SYNTAX      TNamedItemOrEmpty
    MAX-ACCESS  read-create
    STATUS      current
    DESCRIPTION
        "The value of tmnxSrrpOperDomain specifies the name of the SRRP
         oversubscription domain.

         A non-empty value must correspond to a row in the
         tmnxMcOmcrDomainTable.

         Non-empty/non-zero values for tmnxSrrpOperDomain and
         tmnxSrrpOperDomainColor must be set together."
    DEFVAL      { ''H }
    ::= { tmnxSrrpOperEntry 25 }

tmnxSrrpOperDomainColor          OBJECT-TYPE
    SYNTAX      Unsigned32 (0..10)
    MAX-ACCESS  read-create
    STATUS      current
    DESCRIPTION
        "The value of tmnxSrrpOperDomainColor specifies the color of the SRRP
         oversubscription domain for this SRRP instance.

         A non-zero value is only allowed while the value of tmnxSrrpOperDomain
         is not empty.

         The value zero specifies 'no color'.

         The color defines a subset of oversubscribed resources; the system
         will try to restore a subset either completely or not at all.

         Non-empty/non-zero values for tmnxSrrpOperDomain and
         tmnxSrrpOperDomainColor must be set together."
    DEFVAL      { 0 }
    ::= { tmnxSrrpOperEntry 26 }

tmnxSrrpOperDownReason           OBJECT-TYPE
    SYNTAX      INTEGER {
        unknown        (0),
        notActive      (1),
        adminDown      (2),
        ifDown         (3),
        invalidMac     (4),
        messageSapDown (5)
    }
    MAX-ACCESS  read-only
    STATUS      current
    DESCRIPTION
        "The value of tmnxSrrpOperDownReason indicates the reason for the
         operational state to be 'down'."
    ::= { tmnxSrrpOperEntry 27 }

tmnxMcLagInfoLagTable            OBJECT-TYPE
    SYNTAX      SEQUENCE OF TmnxMcLagInfoLagEntry
    MAX-ACCESS  not-accessible
    STATUS      current
    DESCRIPTION
        "The tmnxMcLagInfoLagTable has an entry for each lag that participates
         in a multi-chassis configuration for the indicated peer."
    ::= { tmnxMcRedundancyObjs 10 }

tmnxMcLagInfoLagEntry            OBJECT-TYPE
    SYNTAX      TmnxMcLagInfoLagEntry
    MAX-ACCESS  not-accessible
    STATUS      current
    DESCRIPTION
        "Each row entry represents operational data for a lag that participates
         in a multi-chassis configuration with a given peer.

         Rows are created or removed automatically by the system, each time a
         row is created or deleted in the tmnxMcLagConfigLagTable."
    AUGMENTS    { tmnxMcLagConfigLagEntry }
    ::= { tmnxMcLagInfoLagTable 1 }

TmnxMcLagInfoLagEntry            ::= SEQUENCE
{
    tmnxMcLagActiveStandby           TruthValue,
    tmnxMcLagLacpIdInUse             TruthValue,
    tmnxMcLagExtendedTimeOut         TruthValue,
    tmnxMcLagSelectionLogic          DisplayString,
    tmnxMcLagConfigMismatchString    DisplayString,
    tmnxMcLagConfigMismatchFlags     BITS
}

tmnxMcLagActiveStandby           OBJECT-TYPE
    SYNTAX      TruthValue
    MAX-ACCESS  read-only
    STATUS      current
    DESCRIPTION
        "The value of tmnxMcLagActiveStandby indicates whether this mc-lag is
         active or standby.

         If the value of this object is 'true', this mc-lag is active."
    ::= { tmnxMcLagInfoLagEntry 1 }

tmnxMcLagLacpIdInUse             OBJECT-TYPE
    SYNTAX      TruthValue
    MAX-ACCESS  read-only
    STATUS      current
    DESCRIPTION
        "The value of tmnxMcLagLacpIdInUse indicates whether or not the mc-lag
         values (i.e. system-id, system priority and lacp-key) are advertised
         to the Lacp peer.

         If the value of this object is 'true', the mc-lag values are
         advertised. Otherwise the normal lag values are advertised."
    ::= { tmnxMcLagInfoLagEntry 2 }

tmnxMcLagExtendedTimeOut         OBJECT-TYPE
    SYNTAX      TruthValue
    MAX-ACCESS  read-only
    STATUS      current
    DESCRIPTION
        "The value of tmnxMcLagExtendedTimeOut indicates whether or not the
         system is using the value of tmnxMcLagConfigHoldOnNgbrFailure.

         If this is 'true', the system is temporarily using a larger value than
         the value configured in tmnxMcLagConfigHoldOnNgbrFailure."
    ::= { tmnxMcLagInfoLagEntry 3 }

tmnxMcLagSelectionLogic          OBJECT-TYPE
    SYNTAX      DisplayString
    MAX-ACCESS  read-only
    STATUS      current
    DESCRIPTION
        "The value of tmnxMcLagSelectionLogic is a printable character string
         which contains information about the multi-chassis selection logic."
    ::= { tmnxMcLagInfoLagEntry 4 }

tmnxMcLagConfigMismatchString    OBJECT-TYPE
    SYNTAX      DisplayString
    MAX-ACCESS  read-only
    STATUS      current
    DESCRIPTION
        "The value of tmnxMcLagConfigMismatchString is a printable character
         string which contains information about the multi-chassis
         configuration mismatch."
    ::= { tmnxMcLagInfoLagEntry 5 }

tmnxMcLagConfigMismatchFlags     OBJECT-TYPE
    SYNTAX      BITS {
        lagIsNotMultiChassis         (0),
        localRemoteLagIdMismatch     (1),
        lagSelectionCriteriaMismatch (2),
        lagEncapsulationMismatch     (3),
        mcLacpkeyMismatch            (4),
        mcSystemPriorityMismatch     (5),
        mcSystemIdMismatch           (6)
    }
    MAX-ACCESS  read-only
    STATUS      current
    DESCRIPTION
        "The value of tmnxMcLagConfigMismatchFlags indicates the operational
         status of the multi-chassis configuration.

         lagIsNotMultiChassis(0)            The lag is not multi-chassis on
                                            the peer.

         localRemoteLagIdMismatch(1)        Local - remote Lag ID mismatch with
                                            the peer.

         lagSelectionCriteriaMismatch(2)    LAG selection criteria mismatch
                                            with the peer.

         lagEncapsulationMismatch(3)        LAG Encapsulation mismatch with
                                            the peer.

         mcLacpkeyMismatch(4)               MC lacp-key mismatch with the peer.

         mcSystemPriorityMismatch(5)        MC system-priority mismatch with
                                            the peer.

         mcSystemIdMismatch(6)              MC system-id mismatch with the
                                            peer."
    ::= { tmnxMcLagInfoLagEntry 6 }

tmnxMcsClientAppTable            OBJECT-TYPE
    SYNTAX      SEQUENCE OF TmnxMcsClientAppEntry
    MAX-ACCESS  not-accessible
    STATUS      current
    DESCRIPTION
        "The tmnxMcsClientAppTable has an entry for each application using the
         multi-chassis peer synchronization protocol configured on this system."
    ::= { tmnxMcRedundancyObjs 11 }

tmnxMcsClientAppEntry            OBJECT-TYPE
    SYNTAX      TmnxMcsClientAppEntry
    MAX-ACCESS  not-accessible
    STATUS      current
    DESCRIPTION
        "Each row entry represents a particular multi-chassis peer
         synchronization protocol application.

         Entries cannot be created and deleted via SNMP SET operations."
    INDEX       {
        tmnxMcPeerIpType,
        tmnxMcPeerIpAddr,
        tmnxMcsClientApplication
    }
    ::= { tmnxMcsClientAppTable 1 }

TmnxMcsClientAppEntry            ::= SEQUENCE
{
    tmnxMcsClientApplication         TmnxMcsClientApp,
    tmnxMcsClientNumEntries          Counter32,
    tmnxMcsClientLclDeletedEntries   Counter32,
    tmnxMcsClientAlarmedEntries      Counter32,
    tmnxMcsClientRemNumEntries       Counter32,
    tmnxMcsClientRemLclDelEntries    Counter32,
    tmnxMcsClientRemAlarmedEntries   Counter32,
    tmnxMcsClientOmcrStandby         Counter32,
    tmnxMcsClientOmcrAlarmed         Counter32,
    tmnxMcsClientOmcrRemStandby      Counter32,
    tmnxMcsClientOmcrRemAlarmed      Counter32
}

tmnxMcsClientApplication         OBJECT-TYPE
    SYNTAX      TmnxMcsClientApp
    MAX-ACCESS  not-accessible
    STATUS      current
    DESCRIPTION
        "The value of tmnxMcsClientApplication indicates the type of
         application using multi-chassis synchronization."
    ::= { tmnxMcsClientAppEntry 1 }

tmnxMcsClientNumEntries          OBJECT-TYPE
    SYNTAX      Counter32
    MAX-ACCESS  read-only
    STATUS      current
    DESCRIPTION
        "The value of tmnxMcsClientNumEntries indicates the total number of
         entries in the MCS database per multi-chassis peer for a particular
         application."
    ::= { tmnxMcsClientAppEntry 2 }

tmnxMcsClientLclDeletedEntries   OBJECT-TYPE
    SYNTAX      Counter32
    MAX-ACCESS  read-only
    STATUS      current
    DESCRIPTION
        "The value of tmnxMcsClientLclDeletedEntries indicates the number of
         locally deleted entries in the MCS database per multi-chassis peer for
         a particular application. Locally deleted entries are entries that are
         not being used by the local MCS client application."
    ::= { tmnxMcsClientAppEntry 3 }

tmnxMcsClientAlarmedEntries      OBJECT-TYPE
    SYNTAX      Counter32
    MAX-ACCESS  read-only
    STATUS      current
    DESCRIPTION
        "The value of tmnxMcsClientAlarmedEntries indicates the number of
         alarmed entries in the MCS database per multi-chassis peer for a
         particular application. Entries with an alarm are entries that are not
         being used by the local client application due to resource
         constraints."
    ::= { tmnxMcsClientAppEntry 4 }

tmnxMcsClientRemNumEntries       OBJECT-TYPE
    SYNTAX      Counter32
    MAX-ACCESS  read-only
    STATUS      current
    DESCRIPTION
        "The value of tmnxMcsClientRemNumEntries indicates the total number of
         entries in the MCS database on the multi-chassis peer for a particular
         application."
    ::= { tmnxMcsClientAppEntry 5 }

tmnxMcsClientRemLclDelEntries    OBJECT-TYPE
    SYNTAX      Counter32
    MAX-ACCESS  read-only
    STATUS      current
    DESCRIPTION
        "The value of tmnxMcsClientRemLclDelEntries indicates the number of
         locally deleted entries in the MCS database ont he multi-chassis peer
         for a particular application. Locally deleted entries are entries that
         are not being used by the remote MCS client application."
    ::= { tmnxMcsClientAppEntry 6 }

tmnxMcsClientRemAlarmedEntries   OBJECT-TYPE
    SYNTAX      Counter32
    MAX-ACCESS  read-only
    STATUS      current
    DESCRIPTION
        "The value of tmnxMcsClientRemAlarmedEntries indicates the number of
         alarmed entries in the MCS database on the multi-chassis peer for a
         particular application. Entries with an alarm are entries that are not
         being used by the remote client application due to resource
         constraints."
    ::= { tmnxMcsClientAppEntry 7 }

tmnxMcsClientOmcrStandby         OBJECT-TYPE
    SYNTAX      Counter32
    MAX-ACCESS  read-only
    STATUS      current
    DESCRIPTION
        "The value of tmnxMcsClientOmcrStandby indicates the number of
         Oversubscribed Multi-Chassis Redundancy (OMCR) standby entries in the
         MCS database of this multi-chassis peer for this particular
         application."
    ::= { tmnxMcsClientAppEntry 8 }

tmnxMcsClientOmcrAlarmed         OBJECT-TYPE
    SYNTAX      Counter32
    MAX-ACCESS  read-only
    STATUS      current
    DESCRIPTION
        "The value of tmnxMcsClientOmcrAlarmed indicates the number of
         Oversubscribed Multi-Chassis Redundancy (OMCR) alarmed entries in the
         MCS database of this multi-chassis peer for this particular
         application."
    ::= { tmnxMcsClientAppEntry 9 }

tmnxMcsClientOmcrRemStandby      OBJECT-TYPE
    SYNTAX      Counter32
    MAX-ACCESS  read-only
    STATUS      current
    DESCRIPTION
        "The value of tmnxMcsClientOmcrRemStandby indicates the number of
         Oversubscribed Multi-Chassis Redundancy (OMCR) standby entries for
         this particular application reported by the remote MCR system."
    ::= { tmnxMcsClientAppEntry 10 }

tmnxMcsClientOmcrRemAlarmed      OBJECT-TYPE
    SYNTAX      Counter32
    MAX-ACCESS  read-only
    STATUS      current
    DESCRIPTION
        "The value of tmnxMcsClientOmcrRemAlarmed indicates the number of
         Oversubscribed Multi-Chassis Redundancy (OMCR) alarmed entries for
         this particular application reported by the remote MCR system."
    ::= { tmnxMcsClientAppEntry 11 }

tmnxSrrpStatsTable               OBJECT-TYPE
    SYNTAX      SEQUENCE OF TmnxSrrpStatsEntry
    MAX-ACCESS  not-accessible
    STATUS      current
    DESCRIPTION
        "The tmnxSrrpStatsTable has an entry for each Subscriber Router
         Redundancy Protocol instance configured on this system."
    ::= { tmnxMcRedundancyObjs 12 }

tmnxSrrpStatsEntry               OBJECT-TYPE
    SYNTAX      TmnxSrrpStatsEntry
    MAX-ACCESS  not-accessible
    STATUS      current
    DESCRIPTION
        "Each row entry represents the statistics for a particular SRRP
         instance tied to a service group interface. Entries are
         created/deleted in conjunction with entries in the tmnxSrrpOperTable"
    INDEX       {
        vRtrID,
        vRtrIfIndex,
        tmnxSrrpOperID
    }
    ::= { tmnxSrrpStatsTable 1 }

TmnxSrrpStatsEntry               ::= SEQUENCE
{
    tmnxSrrpStatsBecomeMaster        Counter32,
    tmnxSrrpStatsMasterChanges       Counter32,
    tmnxSrrpStatsAdvSent             Counter32,
    tmnxSrrpStatsAdvRcvd             Counter32,
    tmnxSrrpStatsPriZeroPktsRcvd     Counter32,
    tmnxSrrpStatsPriZeroPktsSent     Counter32,
    tmnxSrrpStatsPreemptEvents       Counter32,
    tmnxSrrpStatsPreemptedEvents     Counter32,
    tmnxSrrpStatsAdvIntDiscards      Counter32,
    tmnxSrrpStatsAdvIntErrors        Counter32,
    tmnxSrrpStatsBecomeBackupRouting Counter32,
    tmnxSrrpStatsBecomeBackupShunt   Counter32,
    tmnxSrrpStatsBecomeNonMaster     Counter32
}

tmnxSrrpStatsBecomeMaster        OBJECT-TYPE
    SYNTAX      Counter32
    MAX-ACCESS  read-only
    STATUS      current
    DESCRIPTION
        "The value for tmnxSrrpStatsBecomeMaster indicates the total number of
         times that the virtual router's state has transitioned to master."
    ::= { tmnxSrrpStatsEntry 1 }

tmnxSrrpStatsMasterChanges       OBJECT-TYPE
    SYNTAX      Counter32
    MAX-ACCESS  read-only
    STATUS      current
    DESCRIPTION
        "The value for tmnxSrrpStatsMasterChanges indicates the total number of
         times the virtual router has seen the master virtual router change."
    ::= { tmnxSrrpStatsEntry 2 }

tmnxSrrpStatsAdvSent             OBJECT-TYPE
    SYNTAX      Counter32
    MAX-ACCESS  read-only
    STATUS      current
    DESCRIPTION
        "The value for tmnxSrrpStatsAdvSent indicates the total number of SRRP
         advertisements sent by this virtual router."
    ::= { tmnxSrrpStatsEntry 3 }

tmnxSrrpStatsAdvRcvd             OBJECT-TYPE
    SYNTAX      Counter32
    MAX-ACCESS  read-only
    STATUS      current
    DESCRIPTION
        "The value for tmnxSrrpStatsAdvRcvd indicates the total number of SRRP
         advertisements received by this virtual router."
    ::= { tmnxSrrpStatsEntry 4 }

tmnxSrrpStatsPriZeroPktsRcvd     OBJECT-TYPE
    SYNTAX      Counter32
    MAX-ACCESS  read-only
    STATUS      current
    DESCRIPTION
        "The value for tmnxSrrpStatsPriZeroPktsRcvd indicates the total number
         of SRRP packets received by the virtual router with a priority of '0'."
    ::= { tmnxSrrpStatsEntry 5 }

tmnxSrrpStatsPriZeroPktsSent     OBJECT-TYPE
    SYNTAX      Counter32
    MAX-ACCESS  read-only
    STATUS      current
    DESCRIPTION
        "The value for tmnxSrrpStatsPriZeroPktsSent indicates the total number
         of SRRP packets sent by the virtual router with a priority of '0'."
    ::= { tmnxSrrpStatsEntry 6 }

tmnxSrrpStatsPreemptEvents       OBJECT-TYPE
    SYNTAX      Counter32
    MAX-ACCESS  read-only
    STATUS      current
    DESCRIPTION
        "The value for tmnxSrrpStatsPreemptEvents indicates the total number of
         times the virtual router has preempted another non-owner master with
         lower priority."
    ::= { tmnxSrrpStatsEntry 7 }

tmnxSrrpStatsPreemptedEvents     OBJECT-TYPE
    SYNTAX      Counter32
    MAX-ACCESS  read-only
    STATUS      current
    DESCRIPTION
        "The value for tmnxSrrpStatsPreemptedEvents indicates the total number
         of times the virtual router has been preempted by another non-owner
         master with higher priority."
    ::= { tmnxSrrpStatsEntry 8 }

tmnxSrrpStatsAdvIntDiscards      OBJECT-TYPE
    SYNTAX      Counter32
    MAX-ACCESS  read-only
    STATUS      current
    DESCRIPTION
        "The value for tmnxSrrpStatsAdvIntDiscards indicates the total number
         of SRRP advertisement packets discarded because the advertisement
         interval in the received packet was different than the one configured
         for the local virtual router."
    ::= { tmnxSrrpStatsEntry 9 }

tmnxSrrpStatsAdvIntErrors        OBJECT-TYPE
    SYNTAX      Counter32
    MAX-ACCESS  read-only
    STATUS      current
    DESCRIPTION
        "The value for tmnxSrrpStatsAdvIntErrors indicates the total number of
         SRRP advertisement packets received for which the advertisement
         interval is different than the one configured for the local virtual
         router."
    ::= { tmnxSrrpStatsEntry 10 }

tmnxSrrpStatsBecomeBackupRouting OBJECT-TYPE
    SYNTAX      Counter32
    MAX-ACCESS  read-only
    STATUS      current
    DESCRIPTION
        "The value for tmnxSrrpStatsBecomeBackupRouting indicates the total
         number of times that the virtual router's state has transitioned to
         backup routing state."
    ::= { tmnxSrrpStatsEntry 11 }

tmnxSrrpStatsBecomeBackupShunt   OBJECT-TYPE
    SYNTAX      Counter32
    MAX-ACCESS  read-only
    STATUS      current
    DESCRIPTION
        "The value for tmnxSrrpStatsBecomeBackupShunt indicates the total
         number of times that the virtual router's state has transitioned to
         backup shunt."
    ::= { tmnxSrrpStatsEntry 12 }

tmnxSrrpStatsBecomeNonMaster     OBJECT-TYPE
    SYNTAX      Counter32
    MAX-ACCESS  read-only
    STATUS      current
    DESCRIPTION
        "The value for tmnxSrrpStatsBecomeNonMaster indicates the total number
         times that the virtual router's state has transitioned from master to
         a non-master state."
    ::= { tmnxSrrpStatsEntry 13 }

tmnxMcRingTableLastChanged       OBJECT-TYPE
    SYNTAX      TimeStamp
    MAX-ACCESS  read-only
    STATUS      current
    DESCRIPTION
        "The value of tmnxMcRingTableLastChanged indicates the sysUpTime at the
         time of the last modification of an entry in the tmnxMcRingTable.

         If no changes were made to the table since the last re-initialization
         of the local network management subsystem, then this object contains a
         zero value."
    ::= { tmnxMcRedundancyObjs 13 }

tmnxMcRingTable                  OBJECT-TYPE
    SYNTAX      SEQUENCE OF TmnxMcRingEntry
    MAX-ACCESS  not-accessible
    STATUS      current
    DESCRIPTION
        "The tmnxMcRingTable has an entry for each multi-chassis ring that
         participates in a multi-chassis configuration for the indicated peer."
    ::= { tmnxMcRedundancyObjs 14 }

tmnxMcRingEntry                  OBJECT-TYPE
    SYNTAX      TmnxMcRingEntry
    MAX-ACCESS  not-accessible
    STATUS      current
    DESCRIPTION
        "Each row entry represents configuration data for a ring that
         participates in a multi-chassis configuration with a given peer.

         Rows can be created and deleted by the operator."
    INDEX       {
        tmnxMcPeerIpType,
        tmnxMcPeerIpAddr,
        tmnxMcPeerSyncPortSyncTag
    }
    ::= { tmnxMcRingTable 1 }

TmnxMcRingEntry                  ::= SEQUENCE
{
    tmnxMcRingRowStatus              RowStatus,
    tmnxMcRingLastChanged            TimeStamp,
    tmnxMcRingAdminState             TmnxAdminState,
    tmnxMcRingInbCtrlSvcId           TmnxServId,
    tmnxMcRingInbCtrlIfName          TNamedItemOrEmpty,
    tmnxMcRingInbCtrlDestIpType      InetAddressType,
    tmnxMcRingInbCtrlDestIp          InetAddress,
    tmnxMcRingVlanMap                OCTET STRING,
    tmnxMcRingVlanMapExcl            OCTET STRING,
    tmnxMcRingInbCtrlDbMax           Unsigned32,
    tmnxMcRingInbCtrlDbAdmin         TmnxAdminState,
    tmnxMcRingType                   TmnxMcRingType
}

tmnxMcRingRowStatus              OBJECT-TYPE
    SYNTAX      RowStatus
    MAX-ACCESS  read-create
    STATUS      current
    DESCRIPTION
        "The value of tmnxMcRingRowStatus specifies the row status of this row."
    ::= { tmnxMcRingEntry 1 }

tmnxMcRingLastChanged            OBJECT-TYPE
    SYNTAX      TimeStamp
    MAX-ACCESS  read-only
    STATUS      current
    DESCRIPTION
        "The value of tmnxMcRingLastChanged indicates the sysUpTime at the time
         of the last modification of this entry.

         If no changes were made to the entry since the last re-initialization
         of the local network management subsystem, then this object contains a
         zero value."
    ::= { tmnxMcRingEntry 2 }

tmnxMcRingAdminState             OBJECT-TYPE
    SYNTAX      TmnxAdminState
    MAX-ACCESS  read-create
    STATUS      current
    DESCRIPTION
        "The value of tmnxMcRingAdminState specifies the administrative state
         of the multi-chassis ring."
    DEFVAL      { outOfService }
    ::= { tmnxMcRingEntry 3 }

tmnxMcRingInbCtrlSvcId           OBJECT-TYPE
    SYNTAX      TmnxServId
    MAX-ACCESS  read-create
    STATUS      current
    DESCRIPTION
        "If the interface used for the inband control connection belongs to a
         VPRN service, the value of tmnxMcRingInbCtrlSvcId specifies its
         service ID.

         Otherwise, the value of tmnxMcRingInbCtrlSvcId is zero. In the latter
         case, the interface must belong to the Base router."
    DEFVAL      { 0 }
    ::= { tmnxMcRingEntry 4 }

tmnxMcRingInbCtrlIfName          OBJECT-TYPE
    SYNTAX      TNamedItemOrEmpty
    MAX-ACCESS  read-create
    STATUS      current
    DESCRIPTION
        "The value of tmnxMcRingInbCtrlIfName specifies the name of the IP
         interface used for the inband control connection.

         If the name is not configured, the ring cannot become operational."
    DEFVAL      { "" }
    ::= { tmnxMcRingEntry 5 }

tmnxMcRingInbCtrlDestIpType      OBJECT-TYPE
    SYNTAX      InetAddressType
    MAX-ACCESS  read-create
    STATUS      current
    DESCRIPTION
        "The value of tmnxMcRingInbCtrlDestIpType specifies the type of host
         address stored in tmnxMcRingInbCtrlDestIp."
    DEFVAL      { unknown }
    ::= { tmnxMcRingEntry 6 }

tmnxMcRingInbCtrlDestIp          OBJECT-TYPE
    SYNTAX      InetAddress (SIZE (0|4|16|20))
    MAX-ACCESS  read-create
    STATUS      current
    DESCRIPTION
        "The value of tmnxMcRingInbCtrlDestIp specifies the destination IP
         address used in the inband control connection.

         If the address is not configured, the ring cannot become operational."
    DEFVAL      { ''H }
    ::= { tmnxMcRingEntry 7 }

tmnxMcRingVlanMap                OBJECT-TYPE
    SYNTAX      OCTET STRING (SIZE (0|512))
    MAX-ACCESS  read-create
    STATUS      current
    DESCRIPTION
        "The value of tmnxMcRingVlanMap specifies the set of VLAN ID's
         associated with the SAP's that belong to Path B of this ring.

         A ring connection is sub-divided into 2 'channels', Path A and Path B.

         In normal operating condition, when the value of
         tmnxMcRingInfoOperState is equal to 'connected (5)', one peer system
         controls Path A, the other Path B, according to an arbitrary
         tie-breaker rule based on the peer systems' IP address.

         Otherwise, both peer systems control Path A and Path B.

         The SAP's associated with the excluded range, specified by the value
         of tmnxMcRingVlanMapExcl, are never controlled by either peer system.

         Path A is the complement of Path B.

         In the system that controls Path B, the value of the object
         tmnxMcRingInfoCtrlVlanMap is equal to 'true'.

         The value of tmnxMcRingVlanMap is a bitmap that associates bit i with
         VLAN ID i, with i in [0..4095]. 4095 corresponds to a dot1q default or
         capture SAP.

         In case of QinQ encapsulation, the outermost VLAN ID is referred to.

         Setting the value of tmnxMcRingVlanMap to the empty string is
         equivalent to setting it to 512 zeroes."
    DEFVAL      { ''H }
    ::= { tmnxMcRingEntry 8 }

tmnxMcRingVlanMapExcl            OBJECT-TYPE
    SYNTAX      OCTET STRING (SIZE (0|512))
    MAX-ACCESS  read-create
    STATUS      current
    DESCRIPTION
        "The value of tmnxMcRingVlanMapExcl specifies the set of VLAN ID's
         associated with the SAP's that are to be excluded from control by the
         multi-chassis ring. It is a bitmap that associates bit i with VLAN ID
         i, with i in [0..4094]. 4095 corresponds to a dot1q default or capture
         SAP.

         In case of QinQ encapsulation, the outermost VLAN ID is referred to.

         Setting the value of tmnxMcRingVlanMapExcl to the empty string is
         equivalent to setting it to 512 zeroes."
    DEFVAL      { ''H }
    ::= { tmnxMcRingEntry 9 }

tmnxMcRingInbCtrlDbMax           OBJECT-TYPE
    SYNTAX      Unsigned32 (5..200)
    UNITS       "seconds"
    MAX-ACCESS  read-create
    STATUS      current
    DESCRIPTION
        "The value of tmnxMcRingInbCtrlDbMax specifies the maximum debounce
         time on the transition of the operational state of the inband control
         connection from 'connected (2)' to 'broken (3)'."
    DEFVAL      { 10 }
    ::= { tmnxMcRingEntry 20 }

tmnxMcRingInbCtrlDbAdmin         OBJECT-TYPE
    SYNTAX      TmnxAdminState
    MAX-ACCESS  read-create
    STATUS      current
    DESCRIPTION
        "The value of tmnxMcRingInbCtrlDbAdmin specifies the administrative
         state of the debounce mechanism on the transition of the operational
         state of the inband control connection from 'connected (2)' to 'broken
         (3)'."
    DEFVAL      { inService }
    ::= { tmnxMcRingEntry 21 }

tmnxMcRingType                   OBJECT-TYPE
    SYNTAX      TmnxMcRingType
    MAX-ACCESS  read-create
    STATUS      current
    DESCRIPTION
        "The value of tmnxMcRingType specifies the type of multi-chassis ring."
    DEFVAL      { layer2 }
    ::= { tmnxMcRingEntry 22 }

tmnxMcRingInfoTableLastChanged   OBJECT-TYPE
    SYNTAX      TimeStamp
    MAX-ACCESS  read-only
    STATUS      current
    DESCRIPTION
        "The value of tmnxMcRingInfoTableLastChanged indicates the sysUpTime at
         the time of the last change of an entry in the tmnxMcRingInfoTable.

         If no changes occurred since the last re-initialization of the local
         network management subsystem, then this object contains a zero value."
    ::= { tmnxMcRedundancyObjs 15 }

tmnxMcRingInfoTable              OBJECT-TYPE
    SYNTAX      SEQUENCE OF TmnxMcRingInfoEntry
    MAX-ACCESS  not-accessible
    STATUS      current
    DESCRIPTION
        "The tmnxMcRingInfoTable has an entry for each multi-chassis ring that
         participates in a multi-chassis configuration for the indicated peer."
    ::= { tmnxMcRedundancyObjs 16 }

tmnxMcRingInfoEntry              OBJECT-TYPE
    SYNTAX      TmnxMcRingInfoEntry
    MAX-ACCESS  not-accessible
    STATUS      current
    DESCRIPTION
        "Each row entry in the tmnxMcRingInfoTable represents additional
         columns of operational data for a ring that participates in a
         multi-chassis operation with a given peer."
    AUGMENTS    { tmnxMcRingEntry }
    ::= { tmnxMcRingInfoTable 1 }

TmnxMcRingInfoEntry              ::= SEQUENCE
{
    tmnxMcRingInfoLastChanged        TimeStamp,
    tmnxMcRingInfoOperState          TmnxMcRingOperState,
    tmnxMcRingInfoFailureReason      DisplayString,
    tmnxMcRingInfoInbCtrlOperState   TmnxMcRingInbCtrlOperState,
    tmnxMcRingInfoInbCtrlSrcIpType   InetAddressType,
    tmnxMcRingInfoInbCtrlSrcIp       InetAddress,
    tmnxMcRingInfoInbCtrlDbStart     TimeStamp,
    tmnxMcRingInfoInbCtrlDbTime      TimeInterval,
    tmnxMcRingInfoPortId             TmnxPortID,
    tmnxMcRingInfoVlanMap            OCTET STRING,
    tmnxMcRingInfoVlanMapExcl        OCTET STRING,
    tmnxMcRingInfoCtrlVlanMap        TruthValue,
    tmnxMcRingInfoInbCtrlDbGuard     Unsigned32
}

tmnxMcRingInfoLastChanged        OBJECT-TYPE
    SYNTAX      TimeStamp
    MAX-ACCESS  read-only
    STATUS      current
    DESCRIPTION
        "The value of tmnxMcRingInfoLastChanged indicates the sysUpTime at the
         time of the last change of this entry.

         If no changes occurred since the last re-initialization of the local
         network management subsystem, then this object contains a zero value."
    ::= { tmnxMcRingInfoEntry 1 }

tmnxMcRingInfoOperState          OBJECT-TYPE
    SYNTAX      TmnxMcRingOperState
    MAX-ACCESS  read-only
    STATUS      current
    DESCRIPTION
        "The value of tmnxMcRingInfoOperState indicates the operational state
         of the multi-chassis ring."
    ::= { tmnxMcRingInfoEntry 2 }

tmnxMcRingInfoFailureReason      OBJECT-TYPE
    SYNTAX      DisplayString (SIZE (0..80))
    MAX-ACCESS  read-only
    STATUS      current
    DESCRIPTION
        "The value of the object tmnxMcRingInfoFailureReason is a printable
         character string that explains the reason why the
         tmnxMcRingInfoOperState is in one of the failed states."
    ::= { tmnxMcRingInfoEntry 3 }

tmnxMcRingInfoInbCtrlOperState   OBJECT-TYPE
    SYNTAX      TmnxMcRingInbCtrlOperState
    MAX-ACCESS  read-only
    STATUS      current
    DESCRIPTION
        "The value of tmnxMcRingInfoInbCtrlOperState indicates the operational
         state of the inband control connection."
    ::= { tmnxMcRingInfoEntry 4 }

tmnxMcRingInfoInbCtrlSrcIpType   OBJECT-TYPE
    SYNTAX      InetAddressType
    MAX-ACCESS  read-only
    STATUS      current
    DESCRIPTION
        "The value of tmnxMcRingInfoInbCtrlSrcIpType indicates the type of host
         address stored in tmnxMcRingInfoInbCtrlSrcIp."
    ::= { tmnxMcRingInfoEntry 5 }

tmnxMcRingInfoInbCtrlSrcIp       OBJECT-TYPE
    SYNTAX      InetAddress (SIZE (0|4|16|20))
    MAX-ACCESS  read-only
    STATUS      current
    DESCRIPTION
        "The value of tmnxMcRingInfoInbCtrlSrcIp indicates the source IP
         address used in the inband control connection."
    ::= { tmnxMcRingInfoEntry 6 }

tmnxMcRingInfoInbCtrlDbStart     OBJECT-TYPE
    SYNTAX      TimeStamp
    MAX-ACCESS  read-only
    STATUS      current
    DESCRIPTION
        "The value of tmnxMcRingInfoInbCtrlDbStart indicates the sysUpTime the
         last time that the debounce timer was started on the transition of the
         operational state of the inband control connection from 'connected
         (2)' to 'broken (3)'.

         If the debounce timer was never started, this object contains a zero
         value."
    ::= { tmnxMcRingInfoEntry 7 }

tmnxMcRingInfoInbCtrlDbTime      OBJECT-TYPE
    SYNTAX      TimeInterval
    MAX-ACCESS  read-only
    STATUS      current
    DESCRIPTION
        "The value of tmnxMcRingInfoInbCtrlDbTime indicates the value of the
         debounce timer at the time indicated by the value of
         tmnxMcRingInfoInbCtrlDbStart.

         Data traffic may have been dropped starting from the time indicated by
         tmnxMcRingInfoInbCtrlDbStart during the interval indicated by
         tmnxMcRingInfoInbCtrlDbTime."
    ::= { tmnxMcRingInfoEntry 8 }

tmnxMcRingInfoPortId             OBJECT-TYPE
    SYNTAX      TmnxPortID
    MAX-ACCESS  read-only
    STATUS      current
    DESCRIPTION
        "The value of tmnxMcRingInfoPortId indicates the port ID of the port
         associated with this ring."
    ::= { tmnxMcRingInfoEntry 9 }

tmnxMcRingInfoVlanMap            OBJECT-TYPE
    SYNTAX      OCTET STRING (SIZE (0|512))
    MAX-ACCESS  read-only
    STATUS      current
    DESCRIPTION
        "The value of tmnxMcRingInfoVlanMap indicates the actual set of VLAN
         ID's associated with the SAP's that are controlled by the slave peer.
         It is a bitmap that associates bit i with VLAN ID i, with i in
         [0..4094].

         An empty string is equivalent to 512 zeroes."
    ::= { tmnxMcRingInfoEntry 10 }

tmnxMcRingInfoVlanMapExcl        OBJECT-TYPE
    SYNTAX      OCTET STRING (SIZE (0|512))
    MAX-ACCESS  read-only
    STATUS      current
    DESCRIPTION
        "The value of tmnxMcRingInfoVlanMapExcl indicates the actual set of
         VLAN ID's associated with the SAP's that are excluded from control by
         the multi-chassis ring. It is a bitmap that associates bit i with VLAN
         ID i, with i in [0..4094].

         An empty string is equivalent to 512 zeroes."
    ::= { tmnxMcRingInfoEntry 11 }

tmnxMcRingInfoCtrlVlanMap        OBJECT-TYPE
    SYNTAX      TruthValue
    MAX-ACCESS  read-only
    STATUS      current
    DESCRIPTION
        "The value of tmnxMcRingInfoCtrlVlanMap indicates if this system is
         currently controlling the SAP's indicated by tmnxMcRingInfoVlanMap."
    ::= { tmnxMcRingInfoEntry 12 }

tmnxMcRingInfoInbCtrlDbGuard     OBJECT-TYPE
    SYNTAX      Unsigned32
    UNITS       "seconds"
    MAX-ACCESS  read-only
    STATUS      current
    DESCRIPTION
        "The value of tmnxMcRingInfoInbCtrlDbGuard indicates the value of the
         debounce guard time.

         The debounce guard time serves to reset the debounce mechanism on the
         transitions of the tmnxMcRingInfoInbCtrlOperState.

         If no such transitions occur during the debounce guard time, the
         debounce mechanism is reset."
    ::= { tmnxMcRingInfoEntry 13 }

tmnxMcRingNodeTableLastChanged   OBJECT-TYPE
    SYNTAX      TimeStamp
    MAX-ACCESS  read-only
    STATUS      current
    DESCRIPTION
        "The value of tmnxMcRingNodeTableLastChanged indicates the sysUpTime at
         the time of the last modification of an entry in the
         tmnxMcRingNodeTable.

         If no changes were made to the table since the last re-initialization
         of the local network management subsystem, then this object contains a
         zero value."
    ::= { tmnxMcRedundancyObjs 17 }

tmnxMcRingNodeTable              OBJECT-TYPE
    SYNTAX      SEQUENCE OF TmnxMcRingNodeEntry
    MAX-ACCESS  not-accessible
    STATUS      current
    DESCRIPTION
        "The tmnxMcRingNodeTable has an entry for each access node that
         participates in a multi-chassis ring configuration for the indicated
         peer."
    ::= { tmnxMcRedundancyObjs 18 }

tmnxMcRingNodeEntry              OBJECT-TYPE
    SYNTAX      TmnxMcRingNodeEntry
    MAX-ACCESS  not-accessible
    STATUS      current
    DESCRIPTION
        "Each row entry represents configuration data related to an access node
         that participates in a multi-chassis ring configuration with a given
         peer.

         Rows can be created and deleted by the operator."
    INDEX       {
        tmnxMcPeerIpType,
        tmnxMcPeerIpAddr,
        tmnxMcPeerSyncPortSyncTag,
        tmnxMcRingNodeName
    }
    ::= { tmnxMcRingNodeTable 1 }

TmnxMcRingNodeEntry              ::= SEQUENCE
{
    tmnxMcRingNodeName               TNamedItem,
    tmnxMcRingNodeRowStatus          RowStatus,
    tmnxMcRingNodeLastChanged        TimeStamp,
    tmnxMcRingNodeRncvAdminState     TmnxAdminState,
    tmnxMcRingNodeRncvSvcId          TmnxServId,
    tmnxMcRingNodeRncvEncapValue     TmnxEncapVal,
    tmnxMcRingNodeRncvSrcIpType      InetAddressType,
    tmnxMcRingNodeRncvSrcIp          InetAddress,
    tmnxMcRingNodeRncvDestIpType     InetAddressType,
    tmnxMcRingNodeRncvDestIp         InetAddress,
    tmnxMcRingNodeRncvInterval       Unsigned32,
    tmnxMcRingNodeRncvSrcMac         MacAddress
}

tmnxMcRingNodeName               OBJECT-TYPE
    SYNTAX      TNamedItem
    MAX-ACCESS  not-accessible
    STATUS      current
    DESCRIPTION
        "The value of tmnxMcRingNodeName specifies the unique name of a
         multi-chassis ring access node."
    ::= { tmnxMcRingNodeEntry 1 }

tmnxMcRingNodeRowStatus          OBJECT-TYPE
    SYNTAX      RowStatus
    MAX-ACCESS  read-create
    STATUS      current
    DESCRIPTION
        "The value of tmnxMcRingNodeRowStatus specifies the row status of this
         row."
    ::= { tmnxMcRingNodeEntry 2 }

tmnxMcRingNodeLastChanged        OBJECT-TYPE
    SYNTAX      TimeStamp
    MAX-ACCESS  read-only
    STATUS      current
    DESCRIPTION
        "The value of tmnxMcRingNodeLastChanged indicates the sysUpTime at the
         time of the last modification of this entry.

         If no changes were made to the entry since the last re-initialization
         of the local network management subsystem, then this object contains a
         zero value."
    ::= { tmnxMcRingNodeEntry 3 }

tmnxMcRingNodeRncvAdminState     OBJECT-TYPE
    SYNTAX      TmnxAdminState
    MAX-ACCESS  read-create
    STATUS      current
    DESCRIPTION
        "The value of tmnxMcRingNodeRncvAdminState specifies the administrative
         state of the Ring-Node Connectivity Verification of this ring node.

         When the value of tmnxMcRingInfoOperState in the corresponding
         tmnxMcRingInfoEntry is  equal to 'broken',
         the Ring-Node Connectivity Verification operates automatically,
         regardless of the value of tmnxMcRingNodeRncvAdminState. This
         automatic operation uses the parameter values configured in this entry,
         except tmnxMcRingNodeRncvInterval."
    DEFVAL      { outOfService }
    ::= { tmnxMcRingNodeEntry 4 }

tmnxMcRingNodeRncvSvcId          OBJECT-TYPE
    SYNTAX      TmnxServId
    MAX-ACCESS  read-create
    STATUS      current
    DESCRIPTION
        "The value of tmnxMcRingNodeRncvSvcId specifies the service ID of the
         SAP used for the Ring-Node Connectivity Verification of this ring
         node."
    DEFVAL      { 0 }
    ::= { tmnxMcRingNodeEntry 5 }

tmnxMcRingNodeRncvEncapValue     OBJECT-TYPE
    SYNTAX      TmnxEncapVal
    MAX-ACCESS  read-create
    STATUS      current
    DESCRIPTION
        "The value of tmnxMcRingNodeRncvEncapValue specifies the encapsulation
         value of the SAP used for the Ring-Node Connectivity Verification of
         this ring node.

         It is only meaningful if the value of tmnxMcRingNodeRncvSvcId is not
         zero.

         The value zero means that the SAP used for the Ring-Node Connectivity
         Verification of this ring node uses NULL encapsulation."
    DEFVAL      { 0 }
    ::= { tmnxMcRingNodeEntry 6 }

tmnxMcRingNodeRncvSrcIpType      OBJECT-TYPE
    SYNTAX      InetAddressType
    MAX-ACCESS  read-create
    STATUS      current
    DESCRIPTION
        "The value of tmnxMcRingNodeRncvSrcIpType specifies the type of host
         address stored in tmnxMcRingNodeRncvSrcIp."
    DEFVAL      { unknown }
    ::= { tmnxMcRingNodeEntry 7 }

tmnxMcRingNodeRncvSrcIp          OBJECT-TYPE
    SYNTAX      InetAddress (SIZE (0|4|16|20))
    MAX-ACCESS  read-create
    STATUS      current
    DESCRIPTION
        "The value of tmnxMcRingNodeRncvSrcIp specifies the source IP address
         used in the Ring-Node Connectivity Verification of this ring node."
    DEFVAL      { ''H }
    ::= { tmnxMcRingNodeEntry 8 }

tmnxMcRingNodeRncvDestIpType     OBJECT-TYPE
    SYNTAX      InetAddressType
    MAX-ACCESS  read-create
    STATUS      current
    DESCRIPTION
        "The value of tmnxMcRingNodeRncvDestIpType specifies the type of host
         address stored in tmnxMcRingNodeRncvDestIp."
    DEFVAL      { unknown }
    ::= { tmnxMcRingNodeEntry 9 }

tmnxMcRingNodeRncvDestIp         OBJECT-TYPE
    SYNTAX      InetAddress (SIZE (0|4|16|20))
    MAX-ACCESS  read-create
    STATUS      current
    DESCRIPTION
        "The value of tmnxMcRingNodeRncvDestIp specifies the destination IP
         address used in the Ring-Node Connectivity Verification of this ring
         node."
    DEFVAL      { ''H }
    ::= { tmnxMcRingNodeEntry 10 }

tmnxMcRingNodeRncvInterval       OBJECT-TYPE
    SYNTAX      Unsigned32 (1..6000)
    UNITS       "minutes"
    MAX-ACCESS  read-create
    STATUS      current
    DESCRIPTION
        "The value of tmnxMcRingNodeRncvInterval specifies the polling interval
         of the Ring-Node Connectivity Verification of this ring node."
    DEFVAL      { 5 }
    ::= { tmnxMcRingNodeEntry 11 }

tmnxMcRingNodeRncvSrcMac         OBJECT-TYPE
    SYNTAX      MacAddress
    MAX-ACCESS  read-create
    STATUS      current
    DESCRIPTION
        "The value of tmnxMcRingNodeRncvSrcMac specifies the source MAC address
         used for the Ring-Node Connectivity Verification of this ring node.

         The value 'all zeroes' specifies that the MAC address of the system
         management processor (CPM) is used."
    DEFVAL      { '000000000000'H }
    ::= { tmnxMcRingNodeEntry 12 }

tmnxMcRingNodeInfoTableLastChgd  OBJECT-TYPE
    SYNTAX      TimeStamp
    MAX-ACCESS  read-only
    STATUS      current
    DESCRIPTION
        "The value of tmnxMcRingNodeInfoTableLastChgd indicates the sysUpTime
         at the time of the last change of an entry in the
         tmnxMcRingNodeInfoTable.

         If no changes occurred since the last re-initialization of the local
         network management subsystem, then this object contains a zero value."
    ::= { tmnxMcRedundancyObjs 19 }

tmnxMcRingNodeInfoTable          OBJECT-TYPE
    SYNTAX      SEQUENCE OF TmnxMcRingNodeInfoEntry
    MAX-ACCESS  not-accessible
    STATUS      current
    DESCRIPTION
        "The tmnxMcRingNodeInfoTable has an entry for each access node that
         participates in a multi-chassis ring configuration for the indicated
         peer."
    ::= { tmnxMcRedundancyObjs 20 }

tmnxMcRingNodeInfoEntry          OBJECT-TYPE
    SYNTAX      TmnxMcRingNodeInfoEntry
    MAX-ACCESS  not-accessible
    STATUS      current
    DESCRIPTION
        "Each row entry represents operational data related to an access node
         that participates in a multi-chassis ring configuration with a given
         peer.

         Rows are created or removed automatically by the system."
    INDEX       {
        tmnxMcPeerIpType,
        tmnxMcPeerIpAddr,
        tmnxMcPeerSyncPortSyncTag,
        tmnxMcRingNodeName
    }
    ::= { tmnxMcRingNodeInfoTable 1 }

TmnxMcRingNodeInfoEntry          ::= SEQUENCE
{
    tmnxMcRingNodeInfoLastChanged    TimeStamp,
    tmnxMcRingNodeInfoLocOperState   TmnxMcRingNodeOperState,
    tmnxMcRingNodeInfoRemOperState   TmnxMcRingNodeOperState,
    tmnxMcRingNodeInfoInUse          TruthValue,
    tmnxMcRingNodeInfoFailureReason  DisplayString
}

tmnxMcRingNodeInfoLastChanged    OBJECT-TYPE
    SYNTAX      TimeStamp
    MAX-ACCESS  read-only
    STATUS      current
    DESCRIPTION
        "The value of tmnxMcRingNodeInfoLastChanged indicates the sysUpTime at
         the time of the last change of this entry.

         If no changes occurred since the last re-initialization of the local
         network management subsystem, then this object contains a zero value."
    ::= { tmnxMcRingNodeInfoEntry 1 }

tmnxMcRingNodeInfoLocOperState   OBJECT-TYPE
    SYNTAX      TmnxMcRingNodeOperState
    MAX-ACCESS  read-only
    STATUS      current
    DESCRIPTION
        "The value of tmnxMcRingNodeInfoLocOperState indicates the operational
         state of the ring node as monitored by the local chassis."
    ::= { tmnxMcRingNodeInfoEntry 2 }

tmnxMcRingNodeInfoRemOperState   OBJECT-TYPE
    SYNTAX      TmnxMcRingNodeOperState
    MAX-ACCESS  read-only
    STATUS      current
    DESCRIPTION
        "The value of tmnxMcRingNodeInfoRemOperState indicates the operational
         state of the ring node as monitored by the remote chassis."
    ::= { tmnxMcRingNodeInfoEntry 3 }

tmnxMcRingNodeInfoInUse          OBJECT-TYPE
    SYNTAX      TruthValue
    MAX-ACCESS  read-only
    STATUS      current
    DESCRIPTION
        "The value of tmnxMcRingNodeInfoInUse indicates if this ring node is
         currently used by any subscriber or configured as ring-node on any
         SAP."
    ::= { tmnxMcRingNodeInfoEntry 4 }

tmnxMcRingNodeInfoFailureReason  OBJECT-TYPE
    SYNTAX      DisplayString (SIZE (0..80))
    MAX-ACCESS  read-only
    STATUS      current
    DESCRIPTION
        "The value of the object tmnxMcRingNodeInfoFailureReason is a printable
         character string that explains the reason why the
         tmnxMcRingNodeInfoLocOperState is in one of the failed states."
    ::= { tmnxMcRingNodeInfoEntry 5 }

tmnxMcTlsCfgTableLastChanged     OBJECT-TYPE
    SYNTAX      TimeStamp
    MAX-ACCESS  read-only
    STATUS      current
    DESCRIPTION
        "The value of tmnxMcTlsCfgTableLastChanged indicates the sysUpTime at
         the time of the last change of an entry in the tmnxMcTlsCfgTable.

         If no changes occurred since the last re-initialization of the local
         network management subsystem, then this object contains a zero value."
    ::= { tmnxMcRedundancyObjs 21 }

tmnxMcTlsCfgTable                OBJECT-TYPE
    SYNTAX      SEQUENCE OF TmnxMcTlsCfgEntry
    MAX-ACCESS  not-accessible
    STATUS      current
    DESCRIPTION
        "The tmnxMcTlsCfgTable has an entry for each TLS Service."
    ::= { tmnxMcRedundancyObjs 22 }

tmnxMcTlsCfgEntry                OBJECT-TYPE
    SYNTAX      TmnxMcTlsCfgEntry
    MAX-ACCESS  not-accessible
    STATUS      current
    DESCRIPTION
        "Each row entry in the tmnxMcTlsCfgTable represents additional columns
         in the TIMETRA-SERV-MIB::svcTlsInfoTable for attributes needed in a
         multi-chassis operation."
    AUGMENTS    { svcTlsInfoEntry }
    ::= { tmnxMcTlsCfgTable 1 }

TmnxMcTlsCfgEntry                ::= SEQUENCE
{
    tmnxMcTlsCfgLastChanged          TimeStamp,
    tmnxMcTlsCfgDefGwIpType          InetAddressType,
    tmnxMcTlsCfgDefGwIp              InetAddress,
    tmnxMcTlsCfgDefGwMac             MacAddress
}

tmnxMcTlsCfgLastChanged          OBJECT-TYPE
    SYNTAX      TimeStamp
    MAX-ACCESS  read-only
    STATUS      current
    DESCRIPTION
        "The value of tmnxMcTlsCfgLastChanged indicates the sysUpTime at the
         time of the last change of this entry.

         If no changes occurred since the last re-initialization of the local
         network management subsystem, then this object contains a zero value."
    ::= { tmnxMcTlsCfgEntry 1 }

tmnxMcTlsCfgDefGwIpType          OBJECT-TYPE
    SYNTAX      InetAddressType
    MAX-ACCESS  read-write
    STATUS      current
    DESCRIPTION
        "The value of tmnxMcTlsCfgDefGwIpType specifies the type of host
         address stored in tmnxMcTlsCfgDefGwIp."
    DEFVAL      { unknown }
    ::= { tmnxMcTlsCfgEntry 2 }

tmnxMcTlsCfgDefGwIp              OBJECT-TYPE
    SYNTAX      InetAddress (SIZE (0|4|16|20))
    MAX-ACCESS  read-write
    STATUS      current
    DESCRIPTION
        "The value of tmnxMcTlsCfgDefGwIp specifies the default gateway IP
         address used in multi-chassis operation associated with this TLS
         service."
    DEFVAL      { ''H }
    ::= { tmnxMcTlsCfgEntry 3 }

tmnxMcTlsCfgDefGwMac             OBJECT-TYPE
    SYNTAX      MacAddress
    MAX-ACCESS  read-write
    STATUS      current
    DESCRIPTION
        "The value of tmnxMcTlsCfgDefGwMac specifies the default gateway MAC
         address used in multi-chassis operation associated with this TLS
         service."
    DEFVAL      { '000000000000'H }
    ::= { tmnxMcTlsCfgEntry 4 }

tmnxMcEpipeSapTableLastChanged   OBJECT-TYPE
    SYNTAX      TimeStamp
    MAX-ACCESS  read-only
    STATUS      current
    DESCRIPTION
        "The value of tmnxMcEpipeSapTableLastChanged indicates the sysUpTime at
         the time of the last change of an entry in the tmnxMcEpipeSapTable.

         If no changes occurred since the last re-initialization of the local
         network management subsystem, then this object contains a zero value."
    ::= { tmnxMcRedundancyObjs 23 }

tmnxMcEpipeSapTable              OBJECT-TYPE
    SYNTAX      SEQUENCE OF TmnxMcEpipeSapEntry
    MAX-ACCESS  not-accessible
    STATUS      current
    DESCRIPTION
        "A table that contains multi-chassis ring information for epipe SAP's."
    ::= { tmnxMcRedundancyObjs 24 }

tmnxMcEpipeSapEntry              OBJECT-TYPE
    SYNTAX      TmnxMcEpipeSapEntry
    MAX-ACCESS  not-accessible
    STATUS      current
    DESCRIPTION
        "Multi-chassis ring information about a specific epipe SAP."
    INDEX       {
        svcId,
        sapPortId,
        sapEncapValue
    }
    ::= { tmnxMcEpipeSapTable 1 }

TmnxMcEpipeSapEntry              ::= SEQUENCE
{
    tmnxMcEpipeSapRowStatus          RowStatus,
    tmnxMcEpipeSapLastChanged        TimeStamp,
    tmnxMcEpipeSapRingNodeName       TNamedItemOrEmpty
}

tmnxMcEpipeSapRowStatus          OBJECT-TYPE
    SYNTAX      RowStatus
    MAX-ACCESS  read-create
    STATUS      current
    DESCRIPTION
        "The value of tmnxMcEpipeSapRowStatus specifies the row status of this
         row."
    ::= { tmnxMcEpipeSapEntry 1 }

tmnxMcEpipeSapLastChanged        OBJECT-TYPE
    SYNTAX      TimeStamp
    MAX-ACCESS  read-only
    STATUS      current
    DESCRIPTION
        "The value of tmnxMcEpipeSapLastChanged indicates the sysUpTime at the
         time of the last change of this entry.

         If no changes occurred since the last re-initialization of the local
         network management subsystem, then this object contains a zero value."
    ::= { tmnxMcEpipeSapEntry 2 }

tmnxMcEpipeSapRingNodeName       OBJECT-TYPE
    SYNTAX      TNamedItemOrEmpty
    MAX-ACCESS  read-create
    STATUS      current
    DESCRIPTION
        "The value of tmnxMcEpipeSapRingNodeName specifies the unique name of a
         multi-chassis ring access node.

         It is used to identify the multi-chassis ring node associated with
         this entry."
    DEFVAL      { ''H }
    ::= { tmnxMcEpipeSapEntry 3 }

tmnxMcsDhcpsObjs                 OBJECT IDENTIFIER ::= { tmnxMcRedundancyObjs 25 }

tmnxMcsDhcpsTableLastChgd        OBJECT-TYPE
    SYNTAX      TimeStamp
    MAX-ACCESS  read-only
    STATUS      current
    DESCRIPTION
        "The value of tmnxMcsDhcpsTableLastChgd indicates the sysUpTime at the
         time of the last modification of an entry in the tmnxMcsDhcpsTable.

         If no changes were made to the table since the last re-initialization
         of the local network management subsystem, then this object contains a
         zero value."
    ::= { tmnxMcsDhcpsObjs 1 }

tmnxMcsDhcpsTable                OBJECT-TYPE
    SYNTAX      SEQUENCE OF TmnxMcsDhcpsEntry
    MAX-ACCESS  not-accessible
    STATUS      current
    DESCRIPTION
        "The tmnxMcsDhcpsTable has an entry for each DHCP Server that is being
         synchronized with a multi-chassis peer.

         Before creating an entry in this table, the entry in the
         tmnxMcPeerSyncTable that corresponds to this peer, must be created."
    ::= { tmnxMcsDhcpsObjs 2 }

tmnxMcsDhcpsEntry                OBJECT-TYPE
    SYNTAX      TmnxMcsDhcpsEntry
    MAX-ACCESS  not-accessible
    STATUS      current
    DESCRIPTION
        "Each row entry represents a DHCP Server to be synchronized. Entries
         are created/deleted by the user."
    INDEX       {
        tmnxMcsDhcpsRtrID,
        tmnxMcsDhcpsServerName
    }
    ::= { tmnxMcsDhcpsTable 1 }

TmnxMcsDhcpsEntry                ::= SEQUENCE
{
    tmnxMcsDhcpsRtrID                TmnxVRtrID,
    tmnxMcsDhcpsServerName           TNamedItem,
    tmnxMcsDhcpsRowStatus            RowStatus,
    tmnxMcsDhcpsPeerIpType           InetAddressType,
    tmnxMcsDhcpsPeerIpAddr           InetAddress,
    tmnxMcsDhcpsSyncTag              TNamedItem
}

tmnxMcsDhcpsRtrID                OBJECT-TYPE
    SYNTAX      TmnxVRtrID
    MAX-ACCESS  not-accessible
    STATUS      current
    DESCRIPTION
        "The value of tmnxMcsDhcpsRtrID specifies the virtual router instance
         of the DHCP Server to be synchronized with the multi-chassis peer.

         The value '1' specifies that the DHCP Server belongs to the Base
         router. For a DHCP Server in the context of a VPRN service, the
         virtual router ID is indicated in the svcVRouterId of the
         svcBaseInfoTable."
    ::= { tmnxMcsDhcpsEntry 1 }

tmnxMcsDhcpsServerName           OBJECT-TYPE
    SYNTAX      TNamedItem
    MAX-ACCESS  not-accessible
    STATUS      current
    DESCRIPTION
        "The value of tmnxMcsDhcpsServerName specifies the DHCP Server to be
         synchronized with the multi-chassis peer."
    ::= { tmnxMcsDhcpsEntry 2 }

tmnxMcsDhcpsRowStatus            OBJECT-TYPE
    SYNTAX      RowStatus
    MAX-ACCESS  read-create
    STATUS      current
    DESCRIPTION
        "This object allows entries to be created and deleted in the
         tmnxMcsDhcpsTable.

         The object tmnxMcsDhcpsSyncTag must be set when creating a new row."
    REFERENCE
        "See definition of RowStatus in RFC 2579, 'Textual Conventions for SMIv2'."
    ::= { tmnxMcsDhcpsEntry 3 }

tmnxMcsDhcpsPeerIpType           OBJECT-TYPE
    SYNTAX      InetAddressType
    MAX-ACCESS  read-create
    STATUS      current
    DESCRIPTION
        "The value of tmnxMcsDhcpsPeerIpType specifies the address type of
         tmnxMcsDhcpsPeerIpAddr.

         The value of tmnxMcsDhcpsPeerIpType must be set simultaneously with
         the value of tmnxMcsDhcpsPeerIpAddr and the value of
         tmnxMcsDhcpsSyncTag.

         When the value of tmnxMcsDhcpsRowStatus is set to 'createAndGo', the
         value of tmnxMcsDhcpsPeerIpType must be set, too.

         Modifying the value of tmnxMcsDhcpsPeerIpType while the value of
         tmnxMcsDhcpsRowStatus is equal to 'active', is only allowed while the
         value of TIMETRA-DHCP-SERVER-MIB::tmnxDhcpsFoState for this DHCP
         Server is equal to 'partnerDown (5)'."
    DEFVAL      { unknown }
    ::= { tmnxMcsDhcpsEntry 4 }

tmnxMcsDhcpsPeerIpAddr           OBJECT-TYPE
    SYNTAX      InetAddress (SIZE (0|4|16|20))
    MAX-ACCESS  read-create
    STATUS      current
    DESCRIPTION
        "The value of tmnxMcsDhcpsPeerIpAddr specifies the address of the
         multi-chassis peer. Its type is specified by tmnxMcsDhcpsPeerIpType.

         It must be a valid unicast address.

         The value of tmnxMcsDhcpsPeerIpAddr must be set simultaneously with
         the value of tmnxMcsDhcpsPeerIpType and the value of
         tmnxMcsDhcpsSyncTag.

         When the value of tmnxMcsDhcpsRowStatus is set to 'createAndGo', the
         value of tmnxMcsDhcpsPeerIpAddr must be set, too.

         Modifying the value of tmnxMcsDhcpsPeerIpAddr while the value of
         tmnxMcsDhcpsRowStatus is equal to 'active', is only allowed while the
         value of TIMETRA-DHCP-SERVER-MIB::tmnxDhcpsFoState for this DHCP
         Server is equal to 'partnerDown (5)'."
    DEFVAL      { ''H }
    ::= { tmnxMcsDhcpsEntry 5 }

tmnxMcsDhcpsSyncTag              OBJECT-TYPE
    SYNTAX      TNamedItem
    MAX-ACCESS  read-create
    STATUS      current
    DESCRIPTION
        "The value of tmnxMcsDhcpsSyncTag specifies a synchronization tag to be
         used while synchronizing this DHCP Server with the multi-chassis peer.

         The value of tmnxMcsDhcpsSyncTag must be set simultaneously with the
         value of tmnxMcsDhcpsPeerIpAddr and the value of
         tmnxMcsDhcpsPeerIpType.

         When the value of tmnxMcsDhcpsRowStatus is set to 'createAndGo', the
         value of tmnxMcsDhcpsSyncTag must be set, too.

         Modifying the value of tmnxMcsDhcpsSyncTag while the value of
         tmnxMcsDhcpsRowStatus is equal to 'active', is only allowed while the
         value of TIMETRA-DHCP-SERVER-MIB::tmnxDhcpsFoState for this DHCP
         Server is equal to 'partnerDown (5)'."
    ::= { tmnxMcsDhcpsEntry 6 }

tmnxMcsDhcpsPoolTableLastChgd    OBJECT-TYPE
    SYNTAX      TimeStamp
    MAX-ACCESS  read-only
    STATUS      current
    DESCRIPTION
        "The value of tmnxMcsDhcpsPoolTableLastChgd indicates the sysUpTime at
         the time of the last modification of an entry in the
         tmnxMcsDhcpsPoolTable.

         If no changes were made to the table since the last re-initialization
         of the local network management subsystem, then this object contains a
         zero value."
    ::= { tmnxMcsDhcpsObjs 3 }

tmnxMcsDhcpsPoolTable            OBJECT-TYPE
    SYNTAX      SEQUENCE OF TmnxMcsDhcpsPoolEntry
    MAX-ACCESS  not-accessible
    STATUS      current
    DESCRIPTION
        "The tmnxMcsDhcpsPoolTable has an entry for each DHCP Server Pool that
         is being synchronized with a multi-chassis peer.

         Before creating an entry in this table, the entry in the
         tmnxMcPeerSyncTable that corresponds to this peer, must be created."
    ::= { tmnxMcsDhcpsObjs 4 }

tmnxMcsDhcpsPoolEntry            OBJECT-TYPE
    SYNTAX      TmnxMcsDhcpsPoolEntry
    MAX-ACCESS  not-accessible
    STATUS      current
    DESCRIPTION
        "Each row entry represents a DHCP Server Pool to be synchronized.
         Entries are created/deleted by the user."
    INDEX       {
        tmnxMcsDhcpsRtrID,
        tmnxMcsDhcpsServerName,
        tmnxMcsDhcpsPoolName
    }
    ::= { tmnxMcsDhcpsPoolTable 1 }

TmnxMcsDhcpsPoolEntry            ::= SEQUENCE
{
    tmnxMcsDhcpsPoolName             TNamedItem,
    tmnxMcsDhcpsPoolRowStatus        RowStatus,
    tmnxMcsDhcpsPoolPeerIpType       InetAddressType,
    tmnxMcsDhcpsPoolPeerIpAddr       InetAddress,
    tmnxMcsDhcpsPoolSyncTag          TNamedItem
}

tmnxMcsDhcpsPoolName             OBJECT-TYPE
    SYNTAX      TNamedItem
    MAX-ACCESS  not-accessible
    STATUS      current
    DESCRIPTION
        "The value of tmnxMcsDhcpsPoolName specifies the DHCP Server Pool to be
         synchronized with the multi-chassis peer."
    ::= { tmnxMcsDhcpsPoolEntry 1 }

tmnxMcsDhcpsPoolRowStatus        OBJECT-TYPE
    SYNTAX      RowStatus
    MAX-ACCESS  read-create
    STATUS      current
    DESCRIPTION
        "This object allows entries to be created and deleted in the
         tmnxMcsDhcpsPoolTable.

         The object tmnxMcsDhcpsPoolSyncTag must be set when creating a new
         row."
    REFERENCE
        "See definition of RowStatus in RFC 2579, 'Textual Conventions for SMIv2'."
    ::= { tmnxMcsDhcpsPoolEntry 2 }

tmnxMcsDhcpsPoolPeerIpType       OBJECT-TYPE
    SYNTAX      InetAddressType
    MAX-ACCESS  read-create
    STATUS      current
    DESCRIPTION
        "The value of tmnxMcsDhcpsPoolPeerIpType specifies the address type of
         tmnxMcsDhcpsPeerIpAddr.

         The value of tmnxMcsDhcpsPoolPeerIpType must be set simultaneously
         with the value of tmnxMcsDhcpsPoolPeerIpAddr and the value of
         tmnxMcsDhcpsPoolSyncTag.

         When the value of tmnxMcsDhcpsPoolRowStatus is set to 'createAndGo',
         the value of tmnxMcsDhcpsPoolPeerIpType must be set, too.

         Modifying the value of tmnxMcsDhcpsPoolPeerIpType while the value of
         tmnxMcsDhcpsPoolRowStatus is equal to 'active', is only allowed while
         the value of TIMETRA-DHCP-SERVER-MIB::tmnxDhcpsFoState for this DHCP
         Server Pool is equal to 'partnerDown (5)'."
    DEFVAL      { unknown }
    ::= { tmnxMcsDhcpsPoolEntry 3 }

tmnxMcsDhcpsPoolPeerIpAddr       OBJECT-TYPE
    SYNTAX      InetAddress (SIZE (0|4|16|20))
    MAX-ACCESS  read-create
    STATUS      current
    DESCRIPTION
        "The value of tmnxMcsDhcpsPoolPeerIpAddr specifies the address of the
         multi-chassis peer. Its type is specified by
         tmnxMcsDhcpsPoolPeerIpType.

         It must be a valid unicast address.

         The value of tmnxMcsDhcpsPoolPeerIpAddr must be set simultaneously
         with the value of tmnxMcsDhcpsPoolPeerIpType and the value of
         tmnxMcsDhcpsPoolSyncTag.

         When the value of tmnxMcsDhcpsPoolRowStatus is set to 'createAndGo',
         the value of tmnxMcsDhcpsPoolPeerIpAddr must be set, too.

         Modifying the value of tmnxMcsDhcpsPoolPeerIpAddr while the value of
         tmnxMcsDhcpsPoolRowStatus is equal to 'active', is only allowed while
         the value of TIMETRA-DHCP-SERVER-MIB::tmnxDhcpsFoState for this DHCP
         Server Pool is equal to 'partnerDown (5)'."
    DEFVAL      { ''H }
    ::= { tmnxMcsDhcpsPoolEntry 4 }

tmnxMcsDhcpsPoolSyncTag          OBJECT-TYPE
    SYNTAX      TNamedItem
    MAX-ACCESS  read-create
    STATUS      current
    DESCRIPTION
        "The value of tmnxMcsDhcpsPoolSyncTag specifies a synchronization tag
         to be used while synchronizing this DHCP Server with the multi-chassis
         peer.

         The value of tmnxMcsDhcpsPoolSyncTag must be set simultaneously with
         the value of tmnxMcsDhcpsPoolPeerIpAddr and the value of
         tmnxMcsDhcpsPoolPeerIpType.

         When the value of tmnxMcsDhcpsPoolRowStatus is set to 'createAndGo',
         the value of tmnxMcsDhcpsPoolSyncTag must be set, too.

         Modifying the value of tmnxMcsDhcpsPoolSyncTag while the value of
         tmnxMcsDhcpsPoolRowStatus is equal to 'active', is only allowed while
         the value of TIMETRA-DHCP-SERVER-MIB::tmnxDhcpsFoState for this DHCP
         Server Pool is equal to 'partnerDown (5)'."
    ::= { tmnxMcsDhcpsPoolEntry 5 }

tmnxSrrpAssoBfdIntfTblLastChgd   OBJECT-TYPE
    SYNTAX      TimeStamp
    MAX-ACCESS  read-only
    STATUS      current
    DESCRIPTION
        "Timestamp of the last change to the tmnxSrrpAssoBfdIntfTable either
         from adding a row or removing a row."
    ::= { tmnxMcRedundancyObjs 26 }

tmnxSrrpAssoBfdIntfTable         OBJECT-TYPE
    SYNTAX      SEQUENCE OF TmnxSrrpAssoBfdIntfEntry
    MAX-ACCESS  not-accessible
    STATUS      current
    DESCRIPTION
        "The tmnxSrrpAssoBfdIntfTable is a read-only table which provides a
         list of the BFD interfaces associated with the corresponding SRRP
         instance.

         The BFD interface provides a fast mechanism for changing the state of
         an SRRP instance riding on the same subnet."
    ::= { tmnxMcRedundancyObjs 27 }

tmnxSrrpAssoBfdIntfEntry         OBJECT-TYPE
    SYNTAX      TmnxSrrpAssoBfdIntfEntry
    MAX-ACCESS  not-accessible
    STATUS      current
    DESCRIPTION
        "Each row entry in the tmnxSrrpAssoBfdIntfTable represents the BFD
         interface associated with SRRP instance tied to a service group
         interface."
    INDEX       {
        vRtrID,
        vRtrIfIndex,
        tmnxSrrpOperID,
        tmnxSrrpAssoBfdIntfSvcId,
        tmnxSrrpAssoBfdIntfIfName,
        tmnxSrrpAssoBfdIntfDestIpType,
        tmnxSrrpAssoBfdIntfDestIp
    }
    ::= { tmnxSrrpAssoBfdIntfTable 1 }

TmnxSrrpAssoBfdIntfEntry         ::= SEQUENCE
{
    tmnxSrrpAssoBfdIntfSvcId         TmnxServId,
    tmnxSrrpAssoBfdIntfIfName        TNamedItem,
    tmnxSrrpAssoBfdIntfDestIpType    InetAddressType,
    tmnxSrrpAssoBfdIntfDestIp        InetAddress,
    tmnxSrrpAssoBfdIntfRowStatus     RowStatus,
    tmnxSrrpAssoBfdIntfLastChanged   TimeStamp,
    tmnxSrrpAssoBfdIntfSrcIpType     InetAddressType,
    tmnxSrrpAssoBfdIntfSrcIp         InetAddress,
    tmnxSrrpAssoBfdIntfSessOperState TmnxSrrpAssoBfdIntfSessOperState
}

tmnxSrrpAssoBfdIntfSvcId         OBJECT-TYPE
    SYNTAX      TmnxServId
    MAX-ACCESS  not-accessible
    STATUS      current
    DESCRIPTION
        "The value of tmnxSrrpAssoBfdIntfSvcId specifies the service ID of the
         interface running BFD."
    ::= { tmnxSrrpAssoBfdIntfEntry 1 }

tmnxSrrpAssoBfdIntfIfName        OBJECT-TYPE
    SYNTAX      TNamedItem
    MAX-ACCESS  not-accessible
    STATUS      current
    DESCRIPTION
        "The value of tmnxSrrpAssoBfdIntfIfName specifies the name of the
         interface running BFD."
    ::= { tmnxSrrpAssoBfdIntfEntry 2 }

tmnxSrrpAssoBfdIntfDestIpType    OBJECT-TYPE
    SYNTAX      InetAddressType
    MAX-ACCESS  not-accessible
    STATUS      current
    DESCRIPTION
        "The value of tmnxSrrpAssoBfdIntfDestIpType specifies the address type
         of tmnxSrrpAssoBfdIntfDestIp object."
    ::= { tmnxSrrpAssoBfdIntfEntry 3 }

tmnxSrrpAssoBfdIntfDestIp        OBJECT-TYPE
    SYNTAX      InetAddress (SIZE (0|4|16|20))
    MAX-ACCESS  not-accessible
    STATUS      current
    DESCRIPTION
        "The value of tmnxSrrpAssoBfdIntfDestIp specifies the destination IP
         address on the interface running BFD."
    ::= { tmnxSrrpAssoBfdIntfEntry 4 }

tmnxSrrpAssoBfdIntfRowStatus     OBJECT-TYPE
    SYNTAX      RowStatus
    MAX-ACCESS  read-create
    STATUS      current
    DESCRIPTION
        "This object tmnxSrrpAssoBfdIntfRowStatus is used for creation or
         deletion of entries in the tmnxSrrpAssoBfdIntfEntry. Deletion of an
         entry in this table will not succeed if it is currently associated
         with any SRRP instance."
    ::= { tmnxSrrpAssoBfdIntfEntry 5 }

tmnxSrrpAssoBfdIntfLastChanged   OBJECT-TYPE
    SYNTAX      TimeStamp
    MAX-ACCESS  read-only
    STATUS      current
    DESCRIPTION
        "The value of tmnxSrrpAssoBfdIntfLastChanged indicates the time stamp
         of the last change to this row of this table."
    ::= { tmnxSrrpAssoBfdIntfEntry 6 }

tmnxSrrpAssoBfdIntfSrcIpType     OBJECT-TYPE
    SYNTAX      InetAddressType
    MAX-ACCESS  read-only
    STATUS      current
    DESCRIPTION
        "The value of tmnxSrrpAssoBfdIntfSrcIpType indicates the address type
         of tmnxSrrpAssoBfdIntfSrcIp object."
    ::= { tmnxSrrpAssoBfdIntfEntry 7 }

tmnxSrrpAssoBfdIntfSrcIp         OBJECT-TYPE
    SYNTAX      InetAddress (SIZE (0|4|16|20))
    MAX-ACCESS  read-only
    STATUS      current
    DESCRIPTION
        "The value of tmnxSrrpAssoBfdIntfSrcIp indicates the source IP address
         on the interface running BFD."
    ::= { tmnxSrrpAssoBfdIntfEntry 8 }

tmnxSrrpAssoBfdIntfSessOperState OBJECT-TYPE
    SYNTAX      TmnxSrrpAssoBfdIntfSessOperState
    MAX-ACCESS  read-only
    STATUS      current
    DESCRIPTION
        "The value of tmnxSrrpAssoBfdIntfSessOperState indicates the
         operational state of the BFD session the SRRP instance is relying upon
         for its fast triggering mechanism."
    ::= { tmnxSrrpAssoBfdIntfEntry 9 }

tmnxMcRingDbTableLastChanged     OBJECT-TYPE
    SYNTAX      TimeStamp
    MAX-ACCESS  read-only
    STATUS      current
    DESCRIPTION
        "The value of tmnxMcRingDbTableLastChanged indicates the sysUpTime at
         the time of the last modification of an entry in the
         tmnxMcRingDbTable.

         If no changes were made to the table since the last re-initialization
         of the local network management subsystem, then this object contains a
         zero value."
    ::= { tmnxMcRedundancyObjs 28 }

tmnxMcRingDbTableSize            OBJECT-TYPE
    SYNTAX      Unsigned32
    MAX-ACCESS  read-only
    STATUS      current
    DESCRIPTION
        "The value of tmnxMcRingDbTableSize indicates the maximum number of
         entries that the tmnxMcRingDbTable can contain."
    ::= { tmnxMcRedundancyObjs 29 }

tmnxMcRingDbTable                OBJECT-TYPE
    SYNTAX      SEQUENCE OF TmnxMcRingDbEntry
    MAX-ACCESS  not-accessible
    STATUS      current
    DESCRIPTION
        "The tmnxMcRingDbTable has an entry for each time a multi-chassis
         ring's operational state change was debounced.

         Only up to the last n occurrences are available, where n is equal to
         the value of tmnxMcRingDbTableSize."
    ::= { tmnxMcRedundancyObjs 30 }

tmnxMcRingDbEntry                OBJECT-TYPE
    SYNTAX      TmnxMcRingDbEntry
    MAX-ACCESS  not-accessible
    STATUS      current
    DESCRIPTION
        "Each row entry represents information about a debounce event.

         Rows are created automatically by the system."
    INDEX       {
        tmnxMcPeerIpType,
        tmnxMcPeerIpAddr,
        tmnxMcPeerSyncPortSyncTag,
        tmnxMcRingDbStart
    }
    ::= { tmnxMcRingDbTable 1 }

TmnxMcRingDbEntry                ::= SEQUENCE
{
    tmnxMcRingDbStart                TimeStamp,
    tmnxMcRingDbTime                 TimeInterval,
    tmnxMcRingDbOperState            TmnxMcRingInbCtrlOperState
}

tmnxMcRingDbStart                OBJECT-TYPE
    SYNTAX      TimeStamp
    MAX-ACCESS  not-accessible
    STATUS      current
    DESCRIPTION
        "The value of tmnxMcRingDbStart indicates the sysUpTime when the
         debounce timer was started on the transition of the operational state
         of the inband control connection from 'connected (2)' to 'broken (3)'."
    ::= { tmnxMcRingDbEntry 1 }

tmnxMcRingDbTime                 OBJECT-TYPE
    SYNTAX      TimeInterval
    MAX-ACCESS  read-only
    STATUS      current
    DESCRIPTION
        "The value of tmnxMcRingDbTime indicates the value of the debounce
         timer at the time indicated by the value of tmnxMcRingDbStart.

         Data traffic may have been dropped starting from the time indicated by
         tmnxMcRingDbStart during the interval indicated by tmnxMcRingDbTime."
    ::= { tmnxMcRingDbEntry 2 }

tmnxMcRingDbOperState            OBJECT-TYPE
    SYNTAX      TmnxMcRingInbCtrlOperState
    MAX-ACCESS  read-only
    STATUS      current
    DESCRIPTION
        "The value of tmnxMcRingDbOperState indicates the operational state of
         the inband control connection after debouncing."
    ::= { tmnxMcRingDbEntry 3 }

tmnxMcL3RingSrrpTableLastChanged OBJECT-TYPE
    SYNTAX      TimeStamp
    MAX-ACCESS  read-only
    STATUS      current
    DESCRIPTION
        "The value of tmnxMcL3RingSrrpTableLastChanged indicates the sysUpTime
         at the time of the last modification of an entry in the
         tmnxMcL3RingSrrpTable.

         If no changes were made to the table since the last re-initialization
         of the local network management subsystem, then this object contains a
         zero value."
    ::= { tmnxMcRedundancyObjs 31 }

tmnxMcL3RingSrrpTable            OBJECT-TYPE
    SYNTAX      SEQUENCE OF TmnxMcL3RingSrrpEntry
    MAX-ACCESS  not-accessible
    STATUS      current
    DESCRIPTION
        "The tmnxMcL3RingSrrpTable has an entry for each multi-chassis layer-3
         ring that participates in a multi-chassis configuration for the
         indicated peer with the indicated SRRP instance."
    ::= { tmnxMcRedundancyObjs 32 }

tmnxMcL3RingSrrpEntry            OBJECT-TYPE
    SYNTAX      TmnxMcL3RingSrrpEntry
    MAX-ACCESS  not-accessible
    STATUS      current
    DESCRIPTION
        "Each row entry represents configuration data for a layer 3 ring that
         participates in a multi-chassis configuration with a given peer of a
         given SRRP instance.

         Rows can be created and deleted by the operator."
    INDEX       {
        tmnxMcPeerIpType,
        tmnxMcPeerIpAddr,
        tmnxMcPeerSyncPortSyncTag,
        tmnxSrrpOperID
    }
    ::= { tmnxMcL3RingSrrpTable 1 }

TmnxMcL3RingSrrpEntry            ::= SEQUENCE
{
    tmnxMcL3RingSrrpRowStatus        RowStatus,
    tmnxMcL3RingSrrpLastChanged      TimeStamp
}

tmnxMcL3RingSrrpRowStatus        OBJECT-TYPE
    SYNTAX      RowStatus
    MAX-ACCESS  read-create
    STATUS      current
    DESCRIPTION
        "The value of tmnxMcL3RingSrrpRowStatus specifies the row status of
         this row."
    ::= { tmnxMcL3RingSrrpEntry 1 }

tmnxMcL3RingSrrpLastChanged      OBJECT-TYPE
    SYNTAX      TimeStamp
    MAX-ACCESS  read-only
    STATUS      current
    DESCRIPTION
        "The value of tmnxMcL3RingSrrpLastChanged indicates the sysUpTime at
         the time of the last modification of this entry.

         If no changes were made to the entry since the last re-initialization
         of the local network management subsystem, then this object contains a
         zero value."
    ::= { tmnxMcL3RingSrrpEntry 2 }

tmnxMcPeerEPTableLastChanged     OBJECT-TYPE
    SYNTAX      TimeStamp
    MAX-ACCESS  read-only
    STATUS      current
    DESCRIPTION
        "The value of tmnxMcPeerEPTableLastChanged indicates the sysUpTime at
         the time of the last modification of an entry in the
         tmnxMcPeerEPTable.

         If no changes were made to the table since the last re-initialization
         of the local network management subsystem, then this object contains a
         zero value."
    ::= { tmnxMcRedundancyObjs 33 }

tmnxMcPeerEPTable                OBJECT-TYPE
    SYNTAX      SEQUENCE OF TmnxMcPeerEPEntry
    MAX-ACCESS  not-accessible
    STATUS      current
    DESCRIPTION
        "The tmnxMcPeerEPTable has an entry for each multi-chassis peer
         end-point configured on this system."
    ::= { tmnxMcRedundancyObjs 34 }

tmnxMcPeerEPEntry                OBJECT-TYPE
    SYNTAX      TmnxMcPeerEPEntry
    MAX-ACCESS  not-accessible
    STATUS      current
    DESCRIPTION
        "Each row entry represents a particular multi-chassis peer end-point.
         Entries are create/deleted by the user."
    INDEX       {
        tmnxMcPeerIpType,
        tmnxMcPeerIpAddr
    }
    ::= { tmnxMcPeerEPTable 1 }

TmnxMcPeerEPEntry                ::= SEQUENCE
{
    tmnxMcPeerEPRowStatus            RowStatus,
    tmnxMcPeerEPLastChanged          TimeStamp,
    tmnxMcPeerEPAdminState           TmnxAdminState,
    tmnxMcPeerEPSysPriority          Unsigned32,
    tmnxMcPeerEPKeepAliveIntvl       Unsigned32,
    tmnxMcPeerEPHoldOnNbrFail        Unsigned32,
    tmnxMcPeerEPBootTimer            Unsigned32,
    tmnxMcPeerEPPassiveMode          TmnxEnabledDisabled,
    tmnxMcPeerEPBfd                  TmnxEnabledDisabled,
    tmnxMcPeerEPOperState            INTEGER,
    tmnxMcPeerEPPeerLastStateChge    TimeStamp,
    tmnxMcPeerEPPassiveModeOper      TruthValue,
    tmnxMcPeerEPRefCount             Unsigned32
}

tmnxMcPeerEPRowStatus            OBJECT-TYPE
    SYNTAX      RowStatus
    MAX-ACCESS  read-create
    STATUS      current
    DESCRIPTION
        "The value of tmnxMcPeerEPRowStatus is used for creation/deletion of
         multi-chassis peer end-points."
    ::= { tmnxMcPeerEPEntry 1 }

tmnxMcPeerEPLastChanged          OBJECT-TYPE
    SYNTAX      TimeStamp
    MAX-ACCESS  read-only
    STATUS      current
    DESCRIPTION
        "The value of tmnxMcPeerEPLastChanged indicates the sysUpTime at the
         time of the last modification of this entry.

         If no changes were made to the entry since the last re-initialization
         of the local network management subsystem, then this object contains a
         zero value."
    ::= { tmnxMcPeerEPEntry 2 }

tmnxMcPeerEPAdminState           OBJECT-TYPE
    SYNTAX      TmnxAdminState
    MAX-ACCESS  read-create
    STATUS      current
    DESCRIPTION
        "The value of tmnxMcPeerEPAdminState specifies the administrative state
         of this multi-chassis peer end-point."
    DEFVAL      { outOfService }
    ::= { tmnxMcPeerEPEntry 3 }

tmnxMcPeerEPSysPriority          OBJECT-TYPE
    SYNTAX      Unsigned32 (0..255)
    MAX-ACCESS  read-create
    STATUS      current
    DESCRIPTION
        "The value of tmnxMcPeerEPSysPriority specifies the system priority of
         this multi-chassis peer end-point."
    DEFVAL      { 0 }
    ::= { tmnxMcPeerEPEntry 4 }

tmnxMcPeerEPKeepAliveIntvl       OBJECT-TYPE
    SYNTAX      Unsigned32 (5..500)
    UNITS       "deci-seconds"
    MAX-ACCESS  read-create
    STATUS      current
    DESCRIPTION
        "The value of tmnxMcPeerEPKeepAliveIntvl specifies the interval at
         which keep-alive messages are exchanged between two peers
         participating in a multi-chassis end-point tunnel (MC-EP).

         These keep-alive messages are used to determine remote-node failures."
    DEFVAL      { 10 }
    ::= { tmnxMcPeerEPEntry 5 }

tmnxMcPeerEPHoldOnNbrFail        OBJECT-TYPE
    SYNTAX      Unsigned32 (2..25)
    MAX-ACCESS  read-create
    STATUS      current
    DESCRIPTION
        "The value of tmnxMcPeerEPHoldOnNbrFail specifies the number of
         keep-alive intervals that the local peer will wait for packets from
         the multi-chassis end-point peer before assuming failure."
    DEFVAL      { 3 }
    ::= { tmnxMcPeerEPEntry 6 }

tmnxMcPeerEPBootTimer            OBJECT-TYPE
    SYNTAX      Unsigned32 (1..600)
    UNITS       "seconds"
    MAX-ACCESS  read-create
    STATUS      current
    DESCRIPTION
        "The value of tmnxMcPeerEPBootTimer specifies the time the
         multi-chassis end-point protocol keeps trying the establish a
         connection before assuming a failure of the remote-peer.

         This object is used at the boot-time only."
    DEFVAL      { 300 }
    ::= { tmnxMcPeerEPEntry 7 }

tmnxMcPeerEPPassiveMode          OBJECT-TYPE
    SYNTAX      TmnxEnabledDisabled
    MAX-ACCESS  read-create
    STATUS      current
    DESCRIPTION
        "The value of tmnxMcPeerEPPassiveMode specifies whether passive-mode
         behavior is configured for the multi-chassis end-point tunnel."
    DEFVAL      { disabled }
    ::= { tmnxMcPeerEPEntry 8 }

tmnxMcPeerEPBfd                  OBJECT-TYPE
    SYNTAX      TmnxEnabledDisabled
    MAX-ACCESS  read-create
    STATUS      current
    DESCRIPTION
        "The value of tmnxMcPeerEPBfd specifies whether bi-directional
         forwarding detection (BFD) is configured for this multi-chassis
         end-point peering tunnel."
    DEFVAL      { disabled }
    ::= { tmnxMcPeerEPEntry 9 }

tmnxMcPeerEPOperState            OBJECT-TYPE
    SYNTAX      INTEGER {
        inService    (0),
        outOfService (1)
    }
    MAX-ACCESS  read-only
    STATUS      current
    DESCRIPTION
        "The value of tmnxMcPeerEPOperState indicates the operational status of
         this multi-chassis end-point peer."
    ::= { tmnxMcPeerEPEntry 10 }

tmnxMcPeerEPPeerLastStateChge    OBJECT-TYPE
    SYNTAX      TimeStamp
    MAX-ACCESS  read-only
    STATUS      current
    DESCRIPTION
        "The value of tmnxMcPeerEPPeerLastStateChge indicates the sysUpTime
         at the time of the last operational state  change for this
         multi-chassis end-point peer.

         If no changes were made since the last re-initialization of the local
         network management subsystem, then this object contains a zero value."
    ::= { tmnxMcPeerEPEntry 11 }

tmnxMcPeerEPPassiveModeOper      OBJECT-TYPE
    SYNTAX      TruthValue
    MAX-ACCESS  read-only
    STATUS      current
    DESCRIPTION
        "The value of tmnxMcPeerEPPassiveModeOper indicates whether
         passive-mode behavior is operationally enabled on this multi-chassis
         end-point tunnel.

         This behavior can be operationally enabled if one of the end-point of
         the tunnel has tmnxMcPeerEPPassiveMode set to 'enabled'."
    ::= { tmnxMcPeerEPEntry 12 }

tmnxMcPeerEPRefCount             OBJECT-TYPE
    SYNTAX      Unsigned32
    MAX-ACCESS  read-only
    STATUS      current
    DESCRIPTION
        "The value of tmnxMcPeerEPRefCount indicates how many service
         end-points are referencing this multi-chassis end-point."
    ::= { tmnxMcPeerEPEntry 13 }

tmnxMcRedBgpMultiHomeObjs        OBJECT IDENTIFIER ::= { tmnxMcRedundancyObjs 35 }

tmnxMcRedBgpMultiHomeBootTimer   OBJECT-TYPE
    SYNTAX      Integer32 (0 | 1..600)
    MAX-ACCESS  read-write
    STATUS      current
    DESCRIPTION
        "The value of tmnxMcRedBgpMultiHomeBootTimer specifies how long the
         system waits after a node reboot before running the DF (designated-
         forwarder) election algorithm."
    DEFVAL      { 10 }
    ::= { tmnxMcRedBgpMultiHomeObjs 1 }

tmnxMcRedBgpMultiHomeSiteTimer   OBJECT-TYPE
    SYNTAX      Integer32 (0..100)
    MAX-ACCESS  read-write
    STATUS      current
    DESCRIPTION
        "The value of tmnxMcRedBgpMultiHomeSiteTimer specifies the time-period
         the system keeps the local sites in standby status, waiting for BGP
         updates from remote PEs before running the DF (designated-forwarder)
         election algorithm to decide whether the site should be unblocked."
    DEFVAL      { 2 }
    ::= { tmnxMcRedBgpMultiHomeObjs 2 }

tmnxMcRedBgpMHSiteMinDnTimer     OBJECT-TYPE
    SYNTAX      Integer32 (0..100)
    UNITS       "seconds"
    MAX-ACCESS  read-write
    STATUS      current
    DESCRIPTION
        "The value of tmnxMcRedBgpMHSiteMinDnTimer specifies the minimum
         time-period the system keeps the site down when a site goes down."
    DEFVAL      { 0 }
    ::= { tmnxMcRedBgpMultiHomeObjs 3 }

tmnxMcTlsSapTableLastChanged     OBJECT-TYPE
    SYNTAX      TimeStamp
    MAX-ACCESS  read-only
    STATUS      current
    DESCRIPTION
        "The value of tmnxMcTlsSapTableLastChanged indicates the sysUpTime at
         the time of the last change of an entry in the tmnxMcTlsSapTable.

         If no changes occurred since the last re-initialization of the local
         network management subsystem, then this object contains a zero value."
    ::= { tmnxMcRedundancyObjs 36 }

tmnxMcTlsSapTable                OBJECT-TYPE
    SYNTAX      SEQUENCE OF TmnxMcTlsSapEntry
    MAX-ACCESS  not-accessible
    STATUS      current
    DESCRIPTION
        "A table that contains multi-chassis ring information for vpls SAP's."
    ::= { tmnxMcRedundancyObjs 37 }

tmnxMcTlsSapEntry                OBJECT-TYPE
    SYNTAX      TmnxMcTlsSapEntry
    MAX-ACCESS  not-accessible
    STATUS      current
    DESCRIPTION
        "Multi-chassis ring information about a specific vpls SAP."
    INDEX       {
        svcId,
        sapPortId,
        sapEncapValue
    }
    ::= { tmnxMcTlsSapTable 1 }

TmnxMcTlsSapEntry                ::= SEQUENCE
{
    tmnxMcTlsSapRowStatus            RowStatus,
    tmnxMcTlsSapLastChanged          TimeStamp,
    tmnxMcTlsSapRingNodeName         TNamedItemOrEmpty
}

tmnxMcTlsSapRowStatus            OBJECT-TYPE
    SYNTAX      RowStatus
    MAX-ACCESS  read-create
    STATUS      current
    DESCRIPTION
        "The value of tmnxMcTlsSapRowStatus specifies the row status of this
         row."
    ::= { tmnxMcTlsSapEntry 1 }

tmnxMcTlsSapLastChanged          OBJECT-TYPE
    SYNTAX      TimeStamp
    MAX-ACCESS  read-only
    STATUS      current
    DESCRIPTION
        "The value of tmnxMcTlsSapLastChanged indicates the sysUpTime at the
         time of the last change of this entry.

         If no changes occurred since the last re-initialization of the local
         network management subsystem, then this object contains a zero value."
    ::= { tmnxMcTlsSapEntry 2 }

tmnxMcTlsSapRingNodeName         OBJECT-TYPE
    SYNTAX      TNamedItemOrEmpty
    MAX-ACCESS  read-create
    STATUS      current
    DESCRIPTION
        "The value of tmnxMcTlsSapRingNodeName specifies the unique name of a
         multi-chassis ring access node.

         It is used to identify the multi-chassis ring node associated with
         this entry."
    DEFVAL      { ''H }
    ::= { tmnxMcTlsSapEntry 3 }

tMcPeerIPsecTblLastChgd          OBJECT-TYPE
    SYNTAX      TimeStamp
    MAX-ACCESS  read-only
    STATUS      current
    DESCRIPTION
        "The value of tMcPeerIPsecTblLastChgd indicates the sysUpTime at the
         time of the last change of an entry in the tMcPeerIPsecTable.

         If no changes occurred since the last re-initialization of the local
         network management subsystem, then this object contains a zero value."
    ::= { tmnxMcRedundancyObjs 38 }

tMcPeerIPsecTable                OBJECT-TYPE
    SYNTAX      SEQUENCE OF TMcPeerIPsecEntry
    MAX-ACCESS  not-accessible
    STATUS      current
    DESCRIPTION
        "The tMcPeerIPsecTable has an entry for ipsec specific objects per
         multi-chassis peer configured on this system."
    ::= { tmnxMcRedundancyObjs 39 }

tMcPeerIPsecEntry                OBJECT-TYPE
    SYNTAX      TMcPeerIPsecEntry
    MAX-ACCESS  not-accessible
    STATUS      current
    DESCRIPTION
        "Each row entry represents ipsec specific objects in a particular
         multi-chassis peer. Entries are create/deleted by the user."
    INDEX       {
        tmnxMcPeerIpType,
        tmnxMcPeerIpAddr
    }
    ::= { tMcPeerIPsecTable 1 }

TMcPeerIPsecEntry                ::= SEQUENCE
{
    tMcPeerIPsecRowStatus            RowStatus,
    tMcPeerIPsecLastChgd             TimeStamp,
    tMcPeerIPsecKeepAliveIntvl       Unsigned32,
    tMcPeerIPsecHoldOnNgbrFail       Unsigned32,
    tMcPeerIPsecBfdEnableSvc         TmnxServId,
    tMcPeerIPsecBfdIntfIfName        TNamedItemOrEmpty,
    tMcPeerIPsecBfdIntfDestIpType    InetAddressType,
    tMcPeerIPsecBfdIntfDestIp        InetAddress,
    tMcPeerIPsecDiscoveryIntvl       Unsigned32,
    tMcPeerIPsecDiscoveryIntvlBoot   Unsigned32,
    tMcPeerIPsecBfdEnable            TruthValue
}

tMcPeerIPsecRowStatus            OBJECT-TYPE
    SYNTAX      RowStatus
    MAX-ACCESS  read-create
    STATUS      current
    DESCRIPTION
        "The value of tMcPeerIPsecRowStatus specifies the row status of this
         row."
    ::= { tMcPeerIPsecEntry 1 }

tMcPeerIPsecLastChgd             OBJECT-TYPE
    SYNTAX      TimeStamp
    MAX-ACCESS  read-only
    STATUS      current
    DESCRIPTION
        "The value of tMcPeerIPsecLastChgd indicates the sysUpTime at the time
         of the last modification of this entry.

         If no changes were made to the entry since the last re-initialization
         of the local network management subsystem, then this object contains a
         zero value."
    ::= { tMcPeerIPsecEntry 2 }

tMcPeerIPsecKeepAliveIntvl       OBJECT-TYPE
    SYNTAX      Unsigned32 (5..500)
    UNITS       "deci-seconds"
    MAX-ACCESS  read-create
    STATUS      current
    DESCRIPTION
        "The value of tMcPeerIPsecKeepAliveIntvl specifies the ipsec specific
         keepalive timer value in units of 0.1 sec. This defines the interval
         at which keep-alive messages are exchanged between two systems
         participating in multi-chassis ipsec tunnels. These keep-alive
         messages are used to determine remote-node failure."
    DEFVAL      { 10 }
    ::= { tMcPeerIPsecEntry 3 }

tMcPeerIPsecHoldOnNgbrFail       OBJECT-TYPE
    SYNTAX      Unsigned32 (2..25)
    MAX-ACCESS  read-create
    STATUS      current
    DESCRIPTION
        "The value of tMcPeerIPsecHoldOnNgbrFail specifies how many
         tMcPeerIPsecKeepAliveIntvl intervals the standby node will wait for
         packets from the active node before assuming a redundant-neighbor node
         failure.

         This delay in switch-over operation is required to accommodate for
         different factors influencing node failure detection rate, such as IGP
         convergence, or HA switch-over times and to prevent that the standby
         node takes actions prematurely."
    DEFVAL      { 3 }
    ::= { tMcPeerIPsecEntry 4 }

tMcPeerIPsecBfdEnableSvc         OBJECT-TYPE
    SYNTAX      TmnxServId
    MAX-ACCESS  read-create
    STATUS      current
    DESCRIPTION
        "The value of tMcPeerIPsecBfdEnableSvc specifies the service ID of the
         interface running BFD."
    DEFVAL      { 0 }
    ::= { tMcPeerIPsecEntry 5 }

tMcPeerIPsecBfdIntfIfName        OBJECT-TYPE
    SYNTAX      TNamedItemOrEmpty
    MAX-ACCESS  read-create
    STATUS      current
    DESCRIPTION
        "The value of tMcPeerIPsecBfdIntfIfName specifies the name of the
         interface running BFD."
    DEFVAL      { ''H }
    ::= { tMcPeerIPsecEntry 6 }

tMcPeerIPsecBfdIntfDestIpType    OBJECT-TYPE
    SYNTAX      InetAddressType
    MAX-ACCESS  read-create
    STATUS      current
    DESCRIPTION
        "The value of tMcPeerIPsecBfdIntfDestIpType specifies the address type
         of tMcPeerIPsecBfdIntfDestIp object."
    DEFVAL      { unknown }
    ::= { tMcPeerIPsecEntry 7 }

tMcPeerIPsecBfdIntfDestIp        OBJECT-TYPE
    SYNTAX      InetAddress (SIZE (0|4|16))
    MAX-ACCESS  read-create
    STATUS      current
    DESCRIPTION
        "The value of tMcPeerIPsecBfdIntfDestIp specifies the destination IP
         address on the interface running BFD."
    DEFVAL      { ''H }
    ::= { tMcPeerIPsecEntry 8 }

tMcPeerIPsecDiscoveryIntvl       OBJECT-TYPE
    SYNTAX      Unsigned32 (1..1800)
    UNITS       "seconds"
    MAX-ACCESS  read-create
    STATUS      current
    DESCRIPTION
        "The value of tMcPeerIPsecDiscoveryIntvl specifies the maximum duration
         of the discovery interval during which a newly activated multi-chassis
         IPsec tunnel-group will remain dormant while trying to contact its
         redundant peer. Groups held dormant in this manner will neither pass
         traffic nor negotiate security keys.  This interval ends when either
         the redundant peer is contacted and a master election occurs, or when
         the maximum duration expires."
    DEFVAL      { 300 }
    ::= { tMcPeerIPsecEntry 9 }

tMcPeerIPsecDiscoveryIntvlBoot   OBJECT-TYPE
    SYNTAX      Unsigned32 (1..1800)
    UNITS       "seconds"
    MAX-ACCESS  read-create
    STATUS      current
    DESCRIPTION
        "The value of tMcPeerIPsecDiscoveryIntvlBoot specifies the maximum
         duration of an interval immediately following system boot up.  When the
         normal discovery interval for a group would expire while the post-boot
         discovery interval is still active, then the group's discovery interval
         is extended until the post-boot discovery interval expires.  This
         allows an extension to the normal discovery stage of groups following
         a chassis reboot, to account for the larger variance in routing
         convergence time."
    DEFVAL      { 300 }
    ::= { tMcPeerIPsecEntry 10 }

tMcPeerIPsecBfdEnable            OBJECT-TYPE
    SYNTAX      TruthValue
    MAX-ACCESS  read-create
    STATUS      current
    DESCRIPTION
        "The value of tMcPeerIPsecBfdEnableSvc specifies whether BFD is enabled
         on the interface.

         The 'inconsistentValue' error is returned if this object is set to
         non-default value and any of tMcPeerIPsecBfdEnableSvc,
         tMcPeerIPsecBfdIntfIfName, tMcPeerIPsecBfdIntfDestIpType,
         tMcPeerIPsecBfdIntfDestIp are set to non-default value."
    DEFVAL      { false }
    ::= { tMcPeerIPsecEntry 11 }

tMcPeerIPsecTnlGrpTblLastChgd    OBJECT-TYPE
    SYNTAX      TimeStamp
    MAX-ACCESS  read-only
    STATUS      current
    DESCRIPTION
        "The value of tMcPeerIPsecTnlGrpTblLastChgd indicates the sysUpTime at
         the time of the last change of an entry in the
         tMcPeerIPsecTnlGrpTable.

         If no changes occurred since the last re-initialization of the local
         network management subsystem, then this object contains a zero value."
    ::= { tmnxMcRedundancyObjs 40 }

tMcPeerIPsecTnlGrpTable          OBJECT-TYPE
    SYNTAX      SEQUENCE OF TMcPeerIPsecTnlGrpEntry
    MAX-ACCESS  not-accessible
    STATUS      current
    DESCRIPTION
        "The tMcPeerIPsecTnlGrpTable has an entry for each ipsec tunnel group
         specific to multi-chassis peer configured on this system."
    ::= { tmnxMcRedundancyObjs 41 }

tMcPeerIPsecTnlGrpEntry          OBJECT-TYPE
    SYNTAX      TMcPeerIPsecTnlGrpEntry
    MAX-ACCESS  not-accessible
    STATUS      current
    DESCRIPTION
        "Each row entry represents a particular ipsec tunnel group of
         multi-chassis peer. Entries are create/deleted by the user."
    INDEX       {
        tmnxMcPeerIpType,
        tmnxMcPeerIpAddr,
        tMcPeerIPsecTnlGrpId
    }
    ::= { tMcPeerIPsecTnlGrpTable 1 }

TMcPeerIPsecTnlGrpEntry          ::= SEQUENCE
{
    tMcPeerIPsecTnlGrpId             TmnxTunnelGroupId,
    tMcPeerIPsecTnlGrpRowStatus      RowStatus,
    tMcPeerIPsecTnlGrpLastChgd       TimeStamp,
    tMcPeerIPsecTnlGrpPeerGrpId      TmnxTunnelGroupIdOrZero,
    tMcPeerIPsecTnlGrpPriority       Unsigned32,
    tMcPeerIPsecTnlGrpPreempt        TruthValue,
    tMcPeerIPsecTnlGrpAdminState     TmnxAdminState,
    tMcPeerIPsecTnlGrpOperState      TmnxOperState,
    tMcPeerIPsecTnlGrpMasterState    TMcPeerIPsecTnlGrpMasterState,
    tMcPeerIPsecTnlGrpReason         DisplayString,
    tMcPeerIPsecTnlGrpForceSwitch    TmnxActionType,
    tMcPeerIPsecTnlGrpProtectStatus  TMcPeerIPsecTnlGrpProtectionStatus,
    tMcPeerIPsecTnlGrpForceSwitchTo  INTEGER
}

tMcPeerIPsecTnlGrpId             OBJECT-TYPE
    SYNTAX      TmnxTunnelGroupId
    MAX-ACCESS  not-accessible
    STATUS      current
    DESCRIPTION
        "The value of tMcPeerIPsecTnlGrpId specifies the tunnel-group
         identifier for this row."
    ::= { tMcPeerIPsecTnlGrpEntry 1 }

tMcPeerIPsecTnlGrpRowStatus      OBJECT-TYPE
    SYNTAX      RowStatus
    MAX-ACCESS  read-create
    STATUS      current
    DESCRIPTION
        "The value of tMcPeerIPsecTnlGrpRowStatus specifies the row status of
         this row."
    ::= { tMcPeerIPsecTnlGrpEntry 2 }

tMcPeerIPsecTnlGrpLastChgd       OBJECT-TYPE
    SYNTAX      TimeStamp
    MAX-ACCESS  read-only
    STATUS      current
    DESCRIPTION
        "The value of tMcPeerIPsecTnlGrpLastChgd indicates the sysUpTime at the
         time of the last modification of this entry.

         If no changes were made to the entry since the last re-initialization
         of the local network management subsystem, then this object contains a
         zero value."
    ::= { tMcPeerIPsecTnlGrpEntry 3 }

tMcPeerIPsecTnlGrpPeerGrpId      OBJECT-TYPE
    SYNTAX      TmnxTunnelGroupIdOrZero
    MAX-ACCESS  read-create
    STATUS      current
    DESCRIPTION
        "The value of tMcPeerIPsecTnlGrpPeerGrpId specifies the tunnel-group
         identifier of the peer for this tunnel-group.

         A value of zero indicates that peer-group is not specified."
    DEFVAL      { 0 }
    ::= { tMcPeerIPsecTnlGrpEntry 4 }

tMcPeerIPsecTnlGrpPriority       OBJECT-TYPE
    SYNTAX      Unsigned32 (0..255)
    MAX-ACCESS  read-create
    STATUS      current
    DESCRIPTION
        "The value of tMcPeerIPsecTnlGrpPriority specifies the priority of this
         tunnel-group."
    DEFVAL      { 100 }
    ::= { tMcPeerIPsecTnlGrpEntry 5 }

tMcPeerIPsecTnlGrpPreempt        OBJECT-TYPE
    SYNTAX      TruthValue
    MAX-ACCESS  read-create
    STATUS      current
    DESCRIPTION
        "The value of tMcPeerIPsecTnlGrpPreempt specifies whether to allow
         mastership preemption by this tunnel group."
    DEFVAL      { false }
    ::= { tMcPeerIPsecTnlGrpEntry 6 }

tMcPeerIPsecTnlGrpAdminState     OBJECT-TYPE
    SYNTAX      TmnxAdminState
    MAX-ACCESS  read-create
    STATUS      current
    DESCRIPTION
        "The value of tMcPeerIPsecTnlGrpAdminState specifies the admin state of
         this tunnel-group."
    DEFVAL      { outOfService }
    ::= { tMcPeerIPsecTnlGrpEntry 7 }

tMcPeerIPsecTnlGrpOperState      OBJECT-TYPE
    SYNTAX      TmnxOperState
    MAX-ACCESS  read-only
    STATUS      current
    DESCRIPTION
        "The value of tMcPeerIPsecTnlGrpOperState indicates the operational
         state of this tunnel-group communicating with the peer tunnel-group."
    ::= { tMcPeerIPsecTnlGrpEntry 8 }

tMcPeerIPsecTnlGrpMasterState    OBJECT-TYPE
    SYNTAX      TMcPeerIPsecTnlGrpMasterState
    MAX-ACCESS  read-only
    STATUS      current
    DESCRIPTION
        "The value of tMcPeerIPsecTnlGrpMasterState indicates the result of the
         mastership election between this tunnel group entity and its peer."
    ::= { tMcPeerIPsecTnlGrpEntry 9 }

tMcPeerIPsecTnlGrpReason         OBJECT-TYPE
    SYNTAX      DisplayString (SIZE (0..80))
    MAX-ACCESS  read-only
    STATUS      current
    DESCRIPTION
        "The value of tMcPeerIPsecTnlGrpReason indicates the reason why
         tMcPeerIPsecTnlGrpOperState is out of service."
    ::= { tMcPeerIPsecTnlGrpEntry 10 }

tMcPeerIPsecTnlGrpForceSwitch    OBJECT-TYPE
    SYNTAX      TmnxActionType
    MAX-ACCESS  read-create
    STATUS      current
    DESCRIPTION
        "The tMcPeerIPsecTnlGrpForceSwitch specifies to perform manual
         mastership switch between this tunnel-group and its redundant peer."
    DEFVAL      { notApplicable }
    ::= { tMcPeerIPsecTnlGrpEntry 11 }

tMcPeerIPsecTnlGrpProtectStatus  OBJECT-TYPE
    SYNTAX      TMcPeerIPsecTnlGrpProtectionStatus
    MAX-ACCESS  read-only
    STATUS      current
    DESCRIPTION
        "The tMcPeerIPsecTnlGrpProtectStatus value indicates the readiness of
         the tunnel group to perform a forced switchover of mastership from the
         current master chassis to the standby chassis.

         Note that even nominal protection status is not a guarantee that
         traffic will not be impacted."
    ::= { tMcPeerIPsecTnlGrpEntry 12 }

tMcPeerIPsecTnlGrpForceSwitchTo  OBJECT-TYPE
    SYNTAX      INTEGER {
        notSpecified (0),
        toMaster     (1),
        toStandby    (2)
    }
    MAX-ACCESS  read-create
    STATUS      current
    DESCRIPTION
        "The tMcPeerIPsecTnlGrpForceSwitchTo specifies the desired mastership
         state to be achieved following a forced switch between this tunnel
         group and its redundant peer.  If the target state matches the
         current state when the switch is attempted, then no switch will
         occur.  The default value of 'notSpecified' will cause the switch
         to be performed regardless of the current state."
    DEFVAL      { notSpecified }
    ::= { tMcPeerIPsecTnlGrpEntry 13 }

tmnxMcsTnlGrpTblLastChgd         OBJECT-TYPE
    SYNTAX      TimeStamp
    MAX-ACCESS  read-only
    STATUS      current
    DESCRIPTION
        "The value of tmnxMcsTnlGrpTblLastChgd indicates the sysUpTime at the
         time of the last change of an entry in the tmnxMcsTnlGrpTable.

         If no changes occurred since the last re-initialization of the local
         network management subsystem, then this object contains a zero value."
    ::= { tmnxMcRedundancyObjs 42 }

tmnxMcsTnlGrpTable               OBJECT-TYPE
    SYNTAX      SEQUENCE OF TmnxMcsTnlGrpEntry
    MAX-ACCESS  not-accessible
    STATUS      current
    DESCRIPTION
        "The tmnxMcsTnlGrpTable has an entry for each ipsec tunnel group
         specific to multi-chassis peer configured on this system."
    ::= { tmnxMcRedundancyObjs 43 }

tmnxMcsTnlGrpEntry               OBJECT-TYPE
    SYNTAX      TmnxMcsTnlGrpEntry
    MAX-ACCESS  not-accessible
    STATUS      current
    DESCRIPTION
        "Each row entry represents a particular ipsec tunnel group of
         multi-chassis peer to be synchronized.

         Entries are create/deleted by the user."
    INDEX       {
        tmnxMcPeerIpType,
        tmnxMcPeerIpAddr,
        tMcPeerIPsecTnlGrpId
    }
    ::= { tmnxMcsTnlGrpTable 1 }

TmnxMcsTnlGrpEntry               ::= SEQUENCE
{
    tmnxMcsTnlGrpRowStatus           RowStatus,
    tmnxMcsTnlGrpSyncTag             TNamedItem
}

tmnxMcsTnlGrpRowStatus           OBJECT-TYPE
    SYNTAX      RowStatus
    MAX-ACCESS  read-create
    STATUS      current
    DESCRIPTION
        "The value of tmnxMcsTnlGrpRowStatus specifies the row status of this
         row."
    ::= { tmnxMcsTnlGrpEntry 1 }

tmnxMcsTnlGrpSyncTag             OBJECT-TYPE
    SYNTAX      TNamedItem
    MAX-ACCESS  read-create
    STATUS      current
    DESCRIPTION
        "The value of tmnxMcsTnlGrpSyncTag specifies the synchronization tag
         assigned to this tunnel-group to be synchronized on this multi-chassis
         peer.

         Value of this object must be set at the time of creation of the entry."
    ::= { tmnxMcsTnlGrpEntry 2 }

tMcPeerTnlGrpStatTable           OBJECT-TYPE
    SYNTAX      SEQUENCE OF TMcPeerTnlGrpStatEntry
    MAX-ACCESS  not-accessible
    STATUS      current
    DESCRIPTION
        "The tMcPeerTnlGrpStatTable has statistics entry for each ipsec tunnel
         group specific to multi-chassis peer configured on this system."
    ::= { tmnxMcRedundancyObjs 44 }

tMcPeerTnlGrpStatEntry           OBJECT-TYPE
    SYNTAX      TMcPeerTnlGrpStatEntry
    MAX-ACCESS  not-accessible
    STATUS      current
    DESCRIPTION
        "Each row entry represents a particular ipsec tunnel statistics group
         of multi-chassis peer."
    AUGMENTS    { tMcPeerIPsecTnlGrpEntry }
    ::= { tMcPeerTnlGrpStatTable 1 }

TMcPeerTnlGrpStatEntry           ::= SEQUENCE
{
    tMcPeerTnlGrpStatDynInstalled    Unsigned32,
    tMcPeerTnlGrpStatDynInstalling   Unsigned32,
    tMcPeerTnlGrpStatDynAwaitConf    Unsigned32,
    tMcPeerTnlGrpStatDynFailed       Unsigned32,
    tMcPeerTnlGrpStatInstalled       Unsigned32,
    tMcPeerTnlGrpStatInstalling      Unsigned32,
    tMcPeerTnlGrpStatAwaitConf       Unsigned32,
    tMcPeerTnlGrpStatFailed          Unsigned32
}

tMcPeerTnlGrpStatDynInstalled    OBJECT-TYPE
    SYNTAX      Unsigned32
    MAX-ACCESS  read-only
    STATUS      current
    DESCRIPTION
        "The value of tMcPeerTnlGrpStatDynInstalled indicates the number of
         dynamic multi-chassis tunnel installed on this tunnel-group to be
         synchronized on this multi-chassis peer."
    ::= { tMcPeerTnlGrpStatEntry 1 }

tMcPeerTnlGrpStatDynInstalling   OBJECT-TYPE
    SYNTAX      Unsigned32
    MAX-ACCESS  read-only
    STATUS      current
    DESCRIPTION
        "The value of tMcPeerTnlGrpStatDynInstalling indicates the number of
         dynamic multi-chassis tunnel being installed on this tunnel-group to
         be synchronized on this multi-chassis peer."
    ::= { tMcPeerTnlGrpStatEntry 2 }

tMcPeerTnlGrpStatDynAwaitConf    OBJECT-TYPE
    SYNTAX      Unsigned32
    MAX-ACCESS  read-only
    STATUS      current
    DESCRIPTION
        "The value of tMcPeerTnlGrpStatDynAwaitConf indicates the number of
         dynamic multi-chassis tunnel awaiting configuration on this
         tunnel-group to be synchronized on this multi-chassis peer."
    ::= { tMcPeerTnlGrpStatEntry 3 }

tMcPeerTnlGrpStatDynFailed       OBJECT-TYPE
    SYNTAX      Unsigned32
    MAX-ACCESS  read-only
    STATUS      current
    DESCRIPTION
        "The value of tMcPeerTnlGrpStatDynFailed indicates the number of
         dynamic multi-chassis tunnel failed to install on this tunnel-group to
         be synchronized on this multi-chassis peer."
    ::= { tMcPeerTnlGrpStatEntry 4 }

tMcPeerTnlGrpStatInstalled       OBJECT-TYPE
    SYNTAX      Unsigned32
    MAX-ACCESS  read-only
    STATUS      current
    DESCRIPTION
        "The value of tMcPeerTnlGrpStatInstalled indicates the number of static
         multi-chassis tunnel installed on this tunnel-group to be synchronized
         on this multi-chassis peer."
    ::= { tMcPeerTnlGrpStatEntry 5 }

tMcPeerTnlGrpStatInstalling      OBJECT-TYPE
    SYNTAX      Unsigned32
    MAX-ACCESS  read-only
    STATUS      current
    DESCRIPTION
        "The value of tMcPeerTnlGrpStatInstalling indicates the number of
         static multi-chassis tunnel being installed on this tunnel-group to be
         synchronized on this multi-chassis peer."
    ::= { tMcPeerTnlGrpStatEntry 6 }

tMcPeerTnlGrpStatAwaitConf       OBJECT-TYPE
    SYNTAX      Unsigned32
    MAX-ACCESS  read-only
    STATUS      current
    DESCRIPTION
        "The value of tMcPeerTnlGrpStatAwaitConf indicates the number of static
         multi-chassis tunnel awaiting configuration on this tunnel-group to be
         synchronized on this multi-chassis peer."
    ::= { tMcPeerTnlGrpStatEntry 7 }

tMcPeerTnlGrpStatFailed          OBJECT-TYPE
    SYNTAX      Unsigned32
    MAX-ACCESS  read-only
    STATUS      current
    DESCRIPTION
        "The value of tMcPeerTnlGrpStatFailed indicates the number of static
         multi-chassis tunnel failed to install on this tunnel-group to be
         synchronized on this multi-chassis peer."
    ::= { tMcPeerTnlGrpStatEntry 8 }

tmnxMcOmcrObjs                   OBJECT IDENTIFIER ::= { tmnxMcRedundancyObjs 45 }

tmnxMcOmcrDomainTable            OBJECT-TYPE
    SYNTAX      SEQUENCE OF TmnxMcOmcrDomainEntry
    MAX-ACCESS  not-accessible
    STATUS      current
    DESCRIPTION
        "The tmnxMcOmcrDomainTable contains objects to configure the OMCR
         oversubscription domains of this system."
    ::= { tmnxMcOmcrObjs 1 }

tmnxMcOmcrDomainEntry            OBJECT-TYPE
    SYNTAX      TmnxMcOmcrDomainEntry
    MAX-ACCESS  not-accessible
    STATUS      current
    DESCRIPTION
        "Each conceptual row represents information about a particular OMCR
         oversubscription domain.

         Entries in this table can be created or deleted via SNMP operations."
    INDEX       { IMPLIED tmnxMcOmcrDomainName }
    ::= { tmnxMcOmcrDomainTable 1 }

TmnxMcOmcrDomainEntry            ::= SEQUENCE
{
    tmnxMcOmcrDomainName             TNamedItem,
    tmnxMcOmcrDomainLastMgmtChange   TimeStamp,
    tmnxMcOmcrDomainRowStatus        RowStatus,
    tmnxMcOmcrDomainDescription      TItemDescription,
    tmnxMcOmcrDomainHoldDownTime     Unsigned32,
    tmnxMcOmcrDomainState            INTEGER
}

tmnxMcOmcrDomainName             OBJECT-TYPE
    SYNTAX      TNamedItem
    MAX-ACCESS  not-accessible
    STATUS      current
    DESCRIPTION
        "The value of tmnxMcOmcrDomainName specifies the name of this OMCR
         oversubscription domain."
    ::= { tmnxMcOmcrDomainEntry 1 }

tmnxMcOmcrDomainLastMgmtChange   OBJECT-TYPE
    SYNTAX      TimeStamp
    MAX-ACCESS  read-only
    STATUS      current
    DESCRIPTION
        "The value of tmnxMcOmcrDomainLastMgmtChange indicates the sysUpTime at
         the time of the most recent management-initiated change to this table
         row."
    ::= { tmnxMcOmcrDomainEntry 2 }

tmnxMcOmcrDomainRowStatus        OBJECT-TYPE
    SYNTAX      RowStatus
    MAX-ACCESS  read-create
    STATUS      current
    DESCRIPTION
        "The value of tmnxMcOmcrDomainRowStatus specifies the row status of
         this row."
    ::= { tmnxMcOmcrDomainEntry 3 }

tmnxMcOmcrDomainDescription      OBJECT-TYPE
    SYNTAX      TItemDescription
    MAX-ACCESS  read-create
    STATUS      current
    DESCRIPTION
        "The value of tmnxMcOmcrDomainDescription specifies the description of
         this OMCR oversubscription domain."
    DEFVAL      { "" }
    ::= { tmnxMcOmcrDomainEntry 4 }

tmnxMcOmcrDomainHoldDownTime     OBJECT-TYPE
    SYNTAX      Unsigned32 (0..10)
    UNITS       "seconds"
    MAX-ACCESS  read-create
    STATUS      current
    DESCRIPTION
        "The value of tmnxMcOmcrDomainHoldDownTime specifies the hold down time
         of this OMCR oversubscription domain.

         The hold down time starts when an access failure is detected; before
         the hold down time is expired, no redundant resources are taken into
         use.

         The value zero specifies that the system immediately proceeds after an
         access failure is detected."
    DEFVAL      { 0 }
    ::= { tmnxMcOmcrDomainEntry 5 }

tmnxMcOmcrDomainState            OBJECT-TYPE
    SYNTAX      INTEGER {
        empty    (0),
        inUse    (1),
        heldDown (2)
    }
    MAX-ACCESS  read-only
    STATUS      current
    DESCRIPTION
        "The value of tmnxMcOmcrDomainState indicates the status of this OMCR
         oversubscription domain."
    ::= { tmnxMcOmcrDomainEntry 6 }

tmnxMcOmcrStatTable              OBJECT-TYPE
    SYNTAX      SEQUENCE OF TmnxMcOmcrStatEntry
    MAX-ACCESS  not-accessible
    STATUS      current
    DESCRIPTION
        "The tmnxMcOmcrStatTable contains objects to monitor the status of the
         access protection of OMCR clients."
    ::= { tmnxMcOmcrObjs 2 }

tmnxMcOmcrStatEntry              OBJECT-TYPE
    SYNTAX      TmnxMcOmcrStatEntry
    MAX-ACCESS  not-accessible
    STATUS      current
    DESCRIPTION
        "Each conceptual row represents information about a particular OMCR
         client protection instance.

         Entries in this table are created and destroyed automatically by the
         system."
    INDEX       {
        tmnxMcOmcrStatClientApplication,
        tmnxMcOmcrStatAccessProtection,
        tmnxMcOmcrStatIndex
    }
    ::= { tmnxMcOmcrStatTable 1 }

TmnxMcOmcrStatEntry              ::= SEQUENCE
{
    tmnxMcOmcrStatClientApplication  TmnxMcsClientApp,
    tmnxMcOmcrStatAccessProtection   TmnxMcsAccessProtection,
    tmnxMcOmcrStatIndex              Unsigned32,
    tmnxMcOmcrStatFailed             INTEGER,
    tmnxMcOmcrStatFailure            DisplayString,
    tmnxMcOmcrStatNumFailedEntries   Gauge32
}

tmnxMcOmcrStatClientApplication  OBJECT-TYPE
    SYNTAX      TmnxMcsClientApp
    MAX-ACCESS  not-accessible
    STATUS      current
    DESCRIPTION
        "The value of tmnxMcOmcrStatClientApplication indicates the OMCR client
         application."
    ::= { tmnxMcOmcrStatEntry 1 }

tmnxMcOmcrStatAccessProtection   OBJECT-TYPE
    SYNTAX      TmnxMcsAccessProtection
    MAX-ACCESS  not-accessible
    STATUS      current
    DESCRIPTION
        "The value of tmnxMcOmcrStatAccessProtection indicates the OMCR client
         application's access protection.

         The value of tmnxMcOmcrStatAccessProtection indicates the
         interpretation of the value of tmnxMcOmcrStatIndex.

         For example: in a row where the value of
         tmnxMcOmcrStatAccessProtection is equal to 'srrp', the value of
         tmnxMcOmcrStatIndex is an SRRP ID and refers to a conceptual row in
         the tmnxSrrpOperTable."
    ::= { tmnxMcOmcrStatEntry 2 }

tmnxMcOmcrStatIndex              OBJECT-TYPE
    SYNTAX      Unsigned32
    MAX-ACCESS  not-accessible
    STATUS      current
    DESCRIPTION
        "The value of tmnxMcOmcrStatIndex indicates the OMCR client
         application's access protection instance index.

         The interpretation of the value of tmnxMcOmcrStatIndex is indicated
         by. the value of tmnxMcOmcrStatAccessProtection indicates.

         For example: in a row where the value of
         tmnxMcOmcrStatAccessProtection is equal to 'srrp', the value of
         tmnxMcOmcrStatIndex is an SRRP ID and refers to a conceptual row in
         the tmnxSrrpOperTable."
    ::= { tmnxMcOmcrStatEntry 3 }

tmnxMcOmcrStatFailed             OBJECT-TYPE
    SYNTAX      INTEGER {
        notAct (0),
        yes    (1),
        no     (2)
    }
    MAX-ACCESS  read-only
    STATUS      current
    DESCRIPTION
        "The value of tmnxMcOmcrStatFailed indicates if the system failed to
         protect the OMCR client application's access protection instance.

         The value may be not applicable, depending on the master state of the
         access protection instance."
    ::= { tmnxMcOmcrStatEntry 4 }

tmnxMcOmcrStatFailure            OBJECT-TYPE
    SYNTAX      DisplayString (SIZE (0..80))
    MAX-ACCESS  read-only
    STATUS      current
    DESCRIPTION
        "The value of tmnxMcOmcrStatFailure indicates why the value of
         tmnxMcOmcrStatFailed is 'yes'."
    ::= { tmnxMcOmcrStatEntry 5 }

tmnxMcOmcrStatNumFailedEntries   OBJECT-TYPE
    SYNTAX      Gauge32
    MAX-ACCESS  read-only
    STATUS      current
    DESCRIPTION
        "The value of tmnxMcOmcrStatNumFailedEntries indicates the number of
         entries that could not be protected for this client application's
         access protection instance.

         For example, in a row where the value of
         tmnxMcOmcrStatClientApplication is equal to 'subMgmtIpoe', and the
         value of tmnxMcOmcrStatAccessProtection is equal to 'srrp', the value
         of tmnxMcOmcrStatNumFailedEntries indicates the number of IPOE
         subscriber hosts that could not be protected for the SRRP instance
         with SRRP ID equal to the value of tmnxMcOmcrStatIndex."
    ::= { tmnxMcOmcrStatEntry 6 }

tmnxMcOmcrDomainTableLastCh      OBJECT-TYPE
    SYNTAX      TimeStamp
    MAX-ACCESS  read-only
    STATUS      current
    DESCRIPTION
        "The value of the object tmnxMcOmcrDomainTableLastCh indicates the
         value of sysUpTime at the time of the last modification of an entry in
         the tmnxMcOmcrDomainTable."
    ::= { tmnxMcRedundancyObjs 46 }

tmnxMcsPythonObjs                OBJECT IDENTIFIER ::= { tmnxMcRedundancyObjs 47 }

tmnxMcsPyPlcyTableLastChgd       OBJECT-TYPE
    SYNTAX      TimeStamp
    MAX-ACCESS  read-only
    STATUS      current
    DESCRIPTION
        "The value of tmnxMcsPyPlcyTableLastChgd indicates the sysUpTime at the
         time of the last modification of an entry in the tmnxMcsPyPlcyTable.

         If no changes were made to the table since the last re-initialization
         of the local network management subsystem, then this object contains a
         zero value."
    ::= { tmnxMcsPythonObjs 1 }

tmnxMcsPyPlcyTable               OBJECT-TYPE
    SYNTAX      SEQUENCE OF TmnxMcsPyPlcyEntry
    MAX-ACCESS  not-accessible
    STATUS      current
    DESCRIPTION
        "The tmnxMcsPyPlcyTable has an entry for each Python policy cache that
         is synchronized between this system and one of its Multi Chassis
         Redundancy peers.

         Before creating an entry in this table, the entry in the
         tmnxMcPeerSyncTable that corresponds to this peer, must be created."
    ::= { tmnxMcsPythonObjs 2 }

tmnxMcsPyPlcyEntry               OBJECT-TYPE
    SYNTAX      TmnxMcsPyPlcyEntry
    MAX-ACCESS  not-accessible
    STATUS      current
    DESCRIPTION
        "Each row represents a Python policy cache that is synchronized between
         this system and one of its Multi Chassis Redundancy peers.

         Entries in this table can be created or deleted via SNMP operations."
    INDEX       { tmnxMcsPyPlcyName }
    ::= { tmnxMcsPyPlcyTable 1 }

TmnxMcsPyPlcyEntry               ::= SEQUENCE
{
    tmnxMcsPyPlcyName                TNamedItem,
    tmnxMcsPyPlcyRowStatus           RowStatus,
    tmnxMcsPyPlcyPeerIpAddrType      InetAddressType,
    tmnxMcsPyPlcyPeerIpAddr          InetAddress,
    tmnxMcsPyPlcyMcsSyncTag          TNamedItem
}

tmnxMcsPyPlcyName                OBJECT-TYPE
    SYNTAX      TNamedItem
    MAX-ACCESS  not-accessible
    STATUS      current
    DESCRIPTION
        "The value of tmnxMcsPyPlcyName specifies the name of the Python policy
         cache.

         A row with the same name must exist in the
         TIMETRA-PYTON-MIB::tmnxPythonPolicyCacheTable."
    ::= { tmnxMcsPyPlcyEntry 1 }

tmnxMcsPyPlcyRowStatus           OBJECT-TYPE
    SYNTAX      RowStatus
    MAX-ACCESS  read-create
    STATUS      current
    DESCRIPTION
        "The value of tmnxMcsPyPlcyRowStatus controls the creation and deletion
         of rows in the table."
    ::= { tmnxMcsPyPlcyEntry 2 }

tmnxMcsPyPlcyPeerIpAddrType      OBJECT-TYPE
    SYNTAX      InetAddressType
    MAX-ACCESS  read-create
    STATUS      current
    DESCRIPTION
        "The value of tmnxMcsPyPlcyPeerIpAddrType specifies the address type of
         tmnxMcsPyPlcyPeerIpAddr."
    DEFVAL      { unknown }
    ::= { tmnxMcsPyPlcyEntry 3 }

tmnxMcsPyPlcyPeerIpAddr          OBJECT-TYPE
    SYNTAX      InetAddress (SIZE (0|4|16))
    MAX-ACCESS  read-create
    STATUS      current
    DESCRIPTION
        "The value of tmnxMcsPyPlcyPeerIpAddr specifies the IP address of the
         Multi-Chassis Redundancy Synchronization (MCS) peer.

         A conceptual row with this IP address must exist in the
         tmnxMcPeerTable."
    DEFVAL      { ''H }
    ::= { tmnxMcsPyPlcyEntry 4 }

tmnxMcsPyPlcyMcsSyncTag          OBJECT-TYPE
    SYNTAX      TNamedItem
    MAX-ACCESS  read-create
    STATUS      current
    DESCRIPTION
        "The value of tmnxMcsPyPlcyMcsSyncTag specifies a tag that uniquely
         identifies this Python policy cache within the scope of the MCS peer.

          The value of this object must be set simultaneously with the value of
          tmnxMcsPyPlcyPeerIpAddr and the value of tmnxMcsPyPlcyPeerIpAddrType.

          When the value of tmnxMcsPyPlcyRowStatus is set to 'createAndGo', the
          value of this object must be set, too.

          Changing the value of this object is only allowed while also specifying
          the values of tmnxMcsPyPlcyPeerIpAddrType and tmnxMcsPyPlcyPeerIpAddr."
    ::= { tmnxMcsPyPlcyEntry 5 }

tmnxMcsPyPlcyTableLastChanged    OBJECT-TYPE
    SYNTAX      TimeStamp
    MAX-ACCESS  read-only
    STATUS      current
    DESCRIPTION
        "The value of the object tmnxMcsPyPlcyTableLastChanged indicates the
         value of sysUpTime at the time of the last modification of an entry in
         the tmnxMcsPyPlcyTable."
    ::= { tmnxMcRedundancyObjs 48 }

tmnxMcL2tpTable                  OBJECT-TYPE
    SYNTAX      SEQUENCE OF TmnxMcL2tpEntry
    MAX-ACCESS  not-accessible
    STATUS      current
    DESCRIPTION
        "The tmnxMcL2tpTable has an entry for each Layer Two Tunnel Protocol
         (L2TP) instance and SRRP instance that is synchronized between this
         system and one of its Multi Chassis Redundancy peers.

         Before creating an entry in this table, the entry in the
         tmnxMcPeerSyncTable that corresponds to this peer, must be created."
    ::= { tmnxMcRedundancyObjs 49 }

tmnxMcL2tpEntry                  OBJECT-TYPE
    SYNTAX      TmnxMcL2tpEntry
    MAX-ACCESS  not-accessible
    STATUS      current
    DESCRIPTION
        "Each row represents a combination of a particular L2TP instance and
         SRRP instance that is synchronized between this system and one of its
         Multi Chassis Redundancy peers.

         Entries in this table can be created or deleted via SNMP operations."
    INDEX       {
        vRtrID,
        tmnxSrrpOperID
    }
    ::= { tmnxMcL2tpTable 1 }

TmnxMcL2tpEntry                  ::= SEQUENCE
{
    tmnxMcL2tpRowStatus              RowStatus,
    tmnxMcL2tpLastChanged            TimeStamp,
    tmnxMcL2tpPeerIpAddrType         InetAddressType,
    tmnxMcL2tpPeerIpAddr             InetAddress,
    tmnxMcL2tpSyncTag                TNamedItem
}

tmnxMcL2tpRowStatus              OBJECT-TYPE
    SYNTAX      RowStatus
    MAX-ACCESS  read-create
    STATUS      current
    DESCRIPTION
        "The value of tmnxMcL2tpRowStatus controls the creation and deletion of
         rows in the table."
    ::= { tmnxMcL2tpEntry 2 }

tmnxMcL2tpLastChanged            OBJECT-TYPE
    SYNTAX      TimeStamp
    MAX-ACCESS  read-only
    STATUS      current
    DESCRIPTION
        "The value tmnxMcL2tpLastChanged indicates the sysUpTime at the time of
         the most recent management-initiated change to the cache of this
         conceptual row."
    ::= { tmnxMcL2tpEntry 3 }

tmnxMcL2tpPeerIpAddrType         OBJECT-TYPE
    SYNTAX      InetAddressType
    MAX-ACCESS  read-create
    STATUS      current
    DESCRIPTION
        "The value of tmnxMcL2tpPeerIpAddrType specifies the address type of
         tmnxMcL2tpPeerIpAddr.

         A non-zero value for this object must be specified while creating a
         conceptual row."
    ::= { tmnxMcL2tpEntry 4 }

tmnxMcL2tpPeerIpAddr             OBJECT-TYPE
    SYNTAX      InetAddress (SIZE (0|4))
    MAX-ACCESS  read-create
    STATUS      current
    DESCRIPTION
        "The value of tmnxMcL2tpPeerIpAddr specifies the IP address of the
         Multi-Chassis Redundancy Synchronization (MCS) peer.

         A conceptual row with this IP address must exist in the
         tmnxMcPeerTable.

         A non-empty value must be specified while creating a conceptual row."
    ::= { tmnxMcL2tpEntry 5 }

tmnxMcL2tpSyncTag                OBJECT-TYPE
    SYNTAX      TNamedItem
    MAX-ACCESS  read-create
    STATUS      current
    DESCRIPTION
        "The value of tmnxMcL2tpSyncTag specifies a tag that uniquely
         identifies this combination of L2TP instance and SRRP instance within
         the scope of the MCS peer.

         Changing the value of this object is only allowed while also
         specifying the values of tmnxMcL2tpPeerIpAddrType and
         tmnxMcL2tpPeerIpAddr.

         A non-empty value must be specified while creating a conceptual row."
    ::= { tmnxMcL2tpEntry 6 }

tmnxMcL2tpTableLastChanged       OBJECT-TYPE
    SYNTAX      TimeStamp
    MAX-ACCESS  read-only
    STATUS      current
    DESCRIPTION
        "The value of the object tmnxMcL2tpTableLastChanged indicates the value
         of sysUpTime at the time of the last modification of an entry in the
         tmnxMcL2tpTable."
    ::= { tmnxMcRedundancyObjs 50 }

tmnxMcTrkSrrpTable               OBJECT-TYPE
    SYNTAX      SEQUENCE OF TmnxMcTrkSrrpEntry
    MAX-ACCESS  not-accessible
    STATUS      current
    DESCRIPTION
        "The tmnxMcTrkSrrpTable contains failover information organized per
         Multi-Chassis peer and per tracked Simple Router Redundancy Protocol
         (SRRP) instance."
    ::= { tmnxMcRedundancyObjs 51 }

tmnxMcTrkSrrpEntry               OBJECT-TYPE
    SYNTAX      TmnxMcTrkSrrpEntry
    MAX-ACCESS  not-accessible
    STATUS      current
    DESCRIPTION
        "Each row entry contains L2TP failover information associated with a
         given MCS peer and SRRP instance.

         Rows are created or removed by SNMP operations on the rowstatus
         object."
    INDEX       {
        tmnxMcTrkSrrpPeerAddrType,
        tmnxMcTrkSrrpPeerAddr,
        tmnxMcTrkSrrpId
    }
    ::= { tmnxMcTrkSrrpTable 1 }

TmnxMcTrkSrrpEntry               ::= SEQUENCE
{
    tmnxMcTrkSrrpPeerAddrType        InetAddressType,
    tmnxMcTrkSrrpPeerAddr            InetAddress,
    tmnxMcTrkSrrpId                  Unsigned32,
    tmnxMcTrkSrrpRowStatus           RowStatus,
    tmnxMcTrkSrrpLastCh              TimeStamp,
    tmnxMcTrkSrrpL2tpTuStart         Unsigned32,
    tmnxMcTrkSrrpL2tpTuEnd           Unsigned32
}

tmnxMcTrkSrrpPeerAddrType        OBJECT-TYPE
    SYNTAX      InetAddressType
    MAX-ACCESS  not-accessible
    STATUS      current
    DESCRIPTION
        "The value of tmnxMcTrkSrrpPeerAddrType specifies the address type of
         tmnxMcTrkSrrpPeerAddr."
    ::= { tmnxMcTrkSrrpEntry 1 }

tmnxMcTrkSrrpPeerAddr            OBJECT-TYPE
    SYNTAX      InetAddress (SIZE (4|16))
    MAX-ACCESS  not-accessible
    STATUS      current
    DESCRIPTION
        "The value of tmnxMcTrkSrrpPeerAddr specifies the IP address of the MCS
         peer.

         A row with the same address must exist in the tmnxMcPeerTable."
    ::= { tmnxMcTrkSrrpEntry 2 }

tmnxMcTrkSrrpId                  OBJECT-TYPE
    SYNTAX      Unsigned32
    MAX-ACCESS  not-accessible
    STATUS      current
    DESCRIPTION
        "The value of tmnxMcTrkSrrpId indicates the unique identifier of the
         tracked SRRP instance.

         An conceptual row with this ID must exist in the tmnxSrrpOperTable."
    ::= { tmnxMcTrkSrrpEntry 3 }

tmnxMcTrkSrrpRowStatus           OBJECT-TYPE
    SYNTAX      RowStatus
    MAX-ACCESS  read-create
    STATUS      current
    DESCRIPTION
        "The value of tmnxMcTrkSrrpRowStatus controls the creation and
         destruction of conceptual rows in this table."
    ::= { tmnxMcTrkSrrpEntry 4 }

tmnxMcTrkSrrpLastCh              OBJECT-TYPE
    SYNTAX      TimeStamp
    MAX-ACCESS  read-only
    STATUS      current
    DESCRIPTION
        "The value of tmnxMcTrkSrrpLastCh indicates the value of sysUpTime at
         the time of the last modification of this conceptual row."
    ::= { tmnxMcTrkSrrpEntry 5 }

tmnxMcTrkSrrpL2tpTuStart         OBJECT-TYPE
    SYNTAX      Unsigned32 (0..16383)
    MAX-ACCESS  read-create
    STATUS      current
    DESCRIPTION
        "The value of tmnxMcTrkSrrpL2tpTuStart specifies the start of the range
         of Layer Two Tunnel Protocol (L2TP) tunnel identifiers that can be
         allocated by L2TP on this system, and synchronized with this MCS peer
         and SRRP instance."
    DEFVAL      { 0 }
    ::= { tmnxMcTrkSrrpEntry 6 }

tmnxMcTrkSrrpL2tpTuEnd           OBJECT-TYPE
    SYNTAX      Unsigned32 (0..16383)
    MAX-ACCESS  read-create
    STATUS      current
    DESCRIPTION
        "The value of tmnxMcTrkSrrpL2tpTuEnd specifies the end of the range of
         tunnel identifiers that can be allocated by L2TP on this system, and
         synchronized with this MCS peer and SRRP instance."
    DEFVAL      { 0 }
    ::= { tmnxMcTrkSrrpEntry 7 }

tmnxMcTrkSrrpTableLastChanged    OBJECT-TYPE
    SYNTAX      TimeStamp
    MAX-ACCESS  read-only
    STATUS      current
    DESCRIPTION
        "The value of the object tmnxMcTrkSrrpTableLastChanged indicates the
         value of sysUpTime at the time of the last modification of an entry in
         the tmnxMcTrkSrrpTable."
    ::= { tmnxMcRedundancyObjs 52 }

tmnxMcDiamPrxTable               OBJECT-TYPE
    SYNTAX      SEQUENCE OF TmnxMcDiamPrxEntry
    MAX-ACCESS  not-accessible
    STATUS      current
    DESCRIPTION
        "The tmnxMcDiamPrxTable has an entry for each Diameter Proxy peer
         policy instance that is synchronized between this system and one of
         its Multi Chassis Redundancy peers.

         Before creating an entry in this table, the entry in the
         tmnxMcPeerSyncTable that corresponds to this peer, must be created."
    ::= { tmnxMcRedundancyObjs 54 }

tmnxMcDiamPrxEntry               OBJECT-TYPE
    SYNTAX      TmnxMcDiamPrxEntry
    MAX-ACCESS  not-accessible
    STATUS      current
    DESCRIPTION
        "Each row represents a particular Diameter Proxy peer policy instance
         that is synchronized between this system and one of its Multi Chassis
         Redundancy peers.

         Entries in this table can be created or deleted via SNMP operations."
    INDEX       { tmnxDiamPlcyName }
    ::= { tmnxMcDiamPrxTable 1 }

TmnxMcDiamPrxEntry               ::= SEQUENCE
{
    tmnxMcDiamPrxRowStatus           RowStatus,
    tmnxMcDiamPrxLastChanged         TimeStamp,
    tmnxMcDiamPrxPeerIpAddrType      InetAddressType,
    tmnxMcDiamPrxPeerIpAddr          InetAddress,
    tmnxMcDiamPrxSyncTag             TNamedItemOrEmpty
}

tmnxMcDiamPrxRowStatus           OBJECT-TYPE
    SYNTAX      RowStatus
    MAX-ACCESS  read-create
    STATUS      current
    DESCRIPTION
        "The value of tmnxMcDiamPrxRowStatus controls the creation and deletion
         of rows in the table."
    ::= { tmnxMcDiamPrxEntry 2 }

tmnxMcDiamPrxLastChanged         OBJECT-TYPE
    SYNTAX      TimeStamp
    MAX-ACCESS  read-only
    STATUS      current
    DESCRIPTION
        "The value tmnxMcDiamPrxLastChanged indicates the sysUpTime at the time
         of the most recent management-initiated change to the cache of this
         conceptual row."
    ::= { tmnxMcDiamPrxEntry 3 }

tmnxMcDiamPrxPeerIpAddrType      OBJECT-TYPE
    SYNTAX      InetAddressType
    MAX-ACCESS  read-create
    STATUS      current
    DESCRIPTION
        "The value of tmnxMcDiamPrxPeerIpAddrType specifies the address type of
         tmnxMcDiamPrxPeerIpAddr."
    DEFVAL      { unknown }
    ::= { tmnxMcDiamPrxEntry 4 }

tmnxMcDiamPrxPeerIpAddr          OBJECT-TYPE
    SYNTAX      InetAddress (SIZE (0|4|16))
    MAX-ACCESS  read-create
    STATUS      current
    DESCRIPTION
        "The value of tmnxMcDiamPrxPeerIpAddr specifies the IP address of the
         Multi-Chassis Redundancy Synchronization (MCS) peer.

         A conceptual row with this IP address must exist in the
         tmnxMcPeerTable."
    DEFVAL      { ''H }
    ::= { tmnxMcDiamPrxEntry 5 }

tmnxMcDiamPrxSyncTag             OBJECT-TYPE
    SYNTAX      TNamedItemOrEmpty
    MAX-ACCESS  read-create
    STATUS      current
    DESCRIPTION
        "The value of tmnxMcDiamPrxSyncTag specifies a tag that uniquely
         identifies this Diameter Proxy peer policy within the scope of the MCS
         peer.

         Changing the value of this object is only allowed while also
         specifying the values of tmnxMcDiamPrxPeerIpAddrType and
         tmnxMcDiamPrxPeerIpAddr."
    DEFVAL      { ''H }
    ::= { tmnxMcDiamPrxEntry 6 }

tmnxMcDiamPrxTableLastChanged    OBJECT-TYPE
    SYNTAX      TimeStamp
    MAX-ACCESS  read-only
    STATUS      current
    DESCRIPTION
        "The value of the object tmnxMcDiamPrxTableLastChanged indicates the
         value of sysUpTime at the time of the last modification of an entry in
         the tmnxMcDiamPrxTable."
    ::= { tmnxMcRedundancyObjs 55 }

tmnxMcRedBgpEvpnMHObjs           OBJECT IDENTIFIER ::= { tmnxMcRedundancyObjs 56 }

tmnxMcRedBgpEvpnMHBootTimer      OBJECT-TYPE
    SYNTAX      Integer32 (0 | 1..600)
    UNITS       "seconds"
    MAX-ACCESS  read-write
    STATUS      current
    DESCRIPTION
        "The value of tmnxMcRedBgpEvpnMHBootTimer specifies how long the system
         waits after a node reboot before running the BGP EVPN multi-homing DF
         (designated-forwarder) election algorithm for BGP EVPN services."
    DEFVAL      { 10 }
    ::= { tmnxMcRedBgpEvpnMHObjs 1 }

tmnxMcRedBgpEvpnMHEsActTimer     OBJECT-TYPE
    SYNTAX      Integer32 (0..100)
    UNITS       "seconds"
    MAX-ACCESS  read-write
    STATUS      current
    DESCRIPTION
        "The value of tmnxMcRedBgpEvpnMHEsActTimer specifies the time-period
         the system keeps the local ethernet-segment in standby status, waiting
         for BGP EVPN updates from remote PEs before running the BGP EVPN
         multi-homing DF (designated-forwarder) election algorithm to decide
         whether the ethernet segment should be unblocked."
    DEFVAL      { 3 }
    ::= { tmnxMcRedBgpEvpnMHObjs 2 }

tmnxMcRedBgpEvpnMHBootTimerRem   OBJECT-TYPE
    SYNTAX      Integer32
    UNITS       "seconds"
    MAX-ACCESS  read-only
    STATUS      current
    DESCRIPTION
        "The value of tmnxMcRedBgpEvpnMHBootTimerRem indicates the time
         remaining for the system to wait after a node reboot before running
         the BGP EVPN multi-homing DF (designated-forwarder) election algorithm
         for BGP EVPN services."
    ::= { tmnxMcRedBgpEvpnMHObjs 3 }

tmnxMcPeerSyncSdpTable           OBJECT-TYPE
    SYNTAX      SEQUENCE OF TmnxMcPeerSyncSdpEntry
    MAX-ACCESS  not-accessible
    STATUS      current
    DESCRIPTION
        "The tmnxMcPeerSyncSdpTable has an entry for each SDP that is being
         synchronized with a multi-chassis peer."
    ::= { tmnxMcRedundancyObjs 57 }

tmnxMcPeerSyncSdpEntry           OBJECT-TYPE
    SYNTAX      TmnxMcPeerSyncSdpEntry
    MAX-ACCESS  not-accessible
    STATUS      current
    DESCRIPTION
        "Each row entry represents an SDP to be synchronized. Entries are
         created/deleted by the user."
    INDEX       {
        tmnxMcPeerIpType,
        tmnxMcPeerIpAddr,
        tmnxMcPeerSyncSdpId
    }
    ::= { tmnxMcPeerSyncSdpTable 1 }

TmnxMcPeerSyncSdpEntry           ::= SEQUENCE
{
    tmnxMcPeerSyncSdpId              SdpId,
    tmnxMcPeerSyncSdpRowStatus       RowStatus,
    tmnxMcPeerSyncSdpSyncTag         TNamedItemOrEmpty
}

tmnxMcPeerSyncSdpId              OBJECT-TYPE
    SYNTAX      SdpId
    MAX-ACCESS  not-accessible
    STATUS      current
    DESCRIPTION
        "The value of tmnxMcPeerSyncSdpId indicates the SDP to be synchronized
         with the multi-chassis peer."
    ::= { tmnxMcPeerSyncSdpEntry 1 }

tmnxMcPeerSyncSdpRowStatus       OBJECT-TYPE
    SYNTAX      RowStatus
    MAX-ACCESS  read-create
    STATUS      current
    DESCRIPTION
        "The value of tmnxMcPeerSyncSdpRowStatus is used for creation and
         deletion of SDPs to be synchronized with the multi-chassis peer."
    ::= { tmnxMcPeerSyncSdpEntry 2 }

tmnxMcPeerSyncSdpSyncTag         OBJECT-TYPE
    SYNTAX      TNamedItemOrEmpty
    MAX-ACCESS  read-create
    STATUS      current
    DESCRIPTION
        "The value of tmnxMcPeerSyncSdpSyncTag specifies a synchronization tag
         to be used while synchronizing this SDP with the multi-chassis peer."
    DEFVAL      { ''H }
    ::= { tmnxMcPeerSyncSdpEntry 3 }

tmnxMcPeerSyncSdpVcIdRangeTable  OBJECT-TYPE
    SYNTAX      SEQUENCE OF TmnxMcPeerSyncSdpVcIdRangeEntry
    MAX-ACCESS  not-accessible
    STATUS      current
    DESCRIPTION
        "The tmnxMcPeerSyncSdpVcIdRangeTable has an entry for each vc-id value
         range on an SDP to be synchronized with a multi-chassis peer."
    ::= { tmnxMcRedundancyObjs 58 }

tmnxMcPeerSyncSdpVcIdRangeEntry  OBJECT-TYPE
    SYNTAX      TmnxMcPeerSyncSdpVcIdRangeEntry
    MAX-ACCESS  not-accessible
    STATUS      current
    DESCRIPTION
        "Each row entry represents a range of vc-id values on an SDP to be
         synchronized with a multi-chassis peer. Entries are created/deleted by
         the user."
    INDEX       {
        tmnxMcPeerIpType,
        tmnxMcPeerIpAddr,
        tmnxMcPeerSyncSdpId,
        tmnxMcPeerSyncSdpVcIdMin,
        tmnxMcPeerSyncSdpVcIdMax
    }
    ::= { tmnxMcPeerSyncSdpVcIdRangeTable 1 }

TmnxMcPeerSyncSdpVcIdRangeEntry  ::= SEQUENCE
{
    tmnxMcPeerSyncSdpVcIdMin         Unsigned32,
    tmnxMcPeerSyncSdpVcIdMax         Unsigned32,
    tmnxMcPeerSyncSdpVcIdRowStatus   RowStatus,
    tmnxMcPeerSyncSdpVcIdSyncTag     TNamedItem
}

tmnxMcPeerSyncSdpVcIdMin         OBJECT-TYPE
    SYNTAX      Unsigned32
    MAX-ACCESS  not-accessible
    STATUS      current
    DESCRIPTION
        "The value of tmnxMcPeerSyncSdpVcIdMin indicates the minimum vc-id
         value on the SDP indicated by tmnxMcPeerSyncSdpId that will be
         synchronized with the multi-chassis peer."
    ::= { tmnxMcPeerSyncSdpVcIdRangeEntry 1 }

tmnxMcPeerSyncSdpVcIdMax         OBJECT-TYPE
    SYNTAX      Unsigned32
    MAX-ACCESS  not-accessible
    STATUS      current
    DESCRIPTION
        "The value of tmnxMcPeerSyncSdpVcIdMax indicates the maximum vc-id
         value on the SDP indicated by tmnxMcPeerSyncSdpId that will be
         synchronized with the multi-chassis peer."
    ::= { tmnxMcPeerSyncSdpVcIdRangeEntry 2 }

tmnxMcPeerSyncSdpVcIdRowStatus   OBJECT-TYPE
    SYNTAX      RowStatus
    MAX-ACCESS  read-create
    STATUS      current
    DESCRIPTION
        "The value of tmnxMcPeerSyncSdpVcIdRowStatus is used for creation and
         deletion of vc-id value ranges for a specific SDP to be synchronized
         with the multi-chassis peer."
    ::= { tmnxMcPeerSyncSdpVcIdRangeEntry 3 }

tmnxMcPeerSyncSdpVcIdSyncTag     OBJECT-TYPE
    SYNTAX      TNamedItem
    MAX-ACCESS  read-create
    STATUS      current
    DESCRIPTION
        "The value of tmnxMcPeerSyncSdpVcIdSyncTag specifies a synchronization
         tag to be used while synchronizing this vc-id value range with the
         multi-chassis peer. This object MUST be specified at row creation."
    ::= { tmnxMcPeerSyncSdpVcIdRangeEntry 4 }

tmnxMcRedundancyStatsObjs        OBJECT IDENTIFIER ::= { tmnxMcRedundancy 2 }

tmnxMcLagStatsPktsRx             OBJECT-TYPE
    SYNTAX      Counter32
    MAX-ACCESS  read-only
    STATUS      current
    DESCRIPTION
        "The value of tmnxMcLagStatsPktsRx indicates how many MC-Lag control
         packets with valid authentication were received on this system."
    ::= { tmnxMcRedundancyStatsObjs 1 }

tmnxMcLagStatsPktsRxKeepalive    OBJECT-TYPE
    SYNTAX      Counter32
    MAX-ACCESS  read-only
    STATUS      current
    DESCRIPTION
        "The value of tmnxMcLagStatsPktsRxKeepalive indicates how many valid
         MC-Lag control packets of type keepalive were received on this system."
    ::= { tmnxMcRedundancyStatsObjs 2 }

tmnxMcLagStatsPktsRxConfig       OBJECT-TYPE
    SYNTAX      Counter32
    MAX-ACCESS  read-only
    STATUS      current
    DESCRIPTION
        "The value of tmnxMcLagStatsPktsRxConfig indicates how many valid
         MC-Lag control packets indicating the lag configuration were received
         on this system."
    ::= { tmnxMcRedundancyStatsObjs 3 }

tmnxMcLagStatsPktsRxPeerConfig   OBJECT-TYPE
    SYNTAX      Counter32
    MAX-ACCESS  read-only
    STATUS      current
    DESCRIPTION
        "The value of tmnxMcLagStatsPktsRxPeerConfig indicates how many valid
         MC-Lag control packets indicating the peer configuration were received
         on this system."
    ::= { tmnxMcRedundancyStatsObjs 4 }

tmnxMcLagStatsPktsRxState        OBJECT-TYPE
    SYNTAX      Counter32
    MAX-ACCESS  read-only
    STATUS      current
    DESCRIPTION
        "The value of tmnxMcLagStatsPktsRxState indicates how many valid MC-Lag
         control packets indicating the lag state were received on this system."
    ::= { tmnxMcRedundancyStatsObjs 5 }

tmnxMcLagStatsDropPktKpaliveTask OBJECT-TYPE
    SYNTAX      Counter32
    MAX-ACCESS  read-only
    STATUS      current
    DESCRIPTION
        "The value of tmnxMcLagStatsDropPktKpaliveTask indicates how many
         MC-Lag control packets were dropped on this system because of invalid
         size, authentication or unknown peer."
    ::= { tmnxMcRedundancyStatsObjs 6 }

tmnxMcLagStatsDropPktTooShort    OBJECT-TYPE
    SYNTAX      Counter32
    MAX-ACCESS  read-only
    STATUS      current
    DESCRIPTION
        "The value of tmnxMcLagStatsDropPktTooShort indicates how many MC-Lag
         control packets were dropped on this system because the packet was too
         small."
    ::= { tmnxMcRedundancyStatsObjs 7 }

tmnxMcLagStatsDropPktVerifyFaild OBJECT-TYPE
    SYNTAX      Counter32
    MAX-ACCESS  read-only
    STATUS      current
    DESCRIPTION
        "The value of tmnxMcLagStatsDropPktVerifyFaild indicates how many
         MC-Lag control packets were dropped on this system because of invalid
         formatting."
    ::= { tmnxMcRedundancyStatsObjs 8 }

tmnxMcLagStatsDropTlvInvalidSize OBJECT-TYPE
    SYNTAX      Counter32
    MAX-ACCESS  read-only
    STATUS      current
    DESCRIPTION
        "The value of tmnxMcLagStatsDropTlvInvalidSize indicates how many
         MC-Lag control packets were dropped on this system because of invalid
         size."
    ::= { tmnxMcRedundancyStatsObjs 9 }

tmnxMcLagStatsDropOutOfSeq       OBJECT-TYPE
    SYNTAX      Counter32
    MAX-ACCESS  read-only
    STATUS      current
    DESCRIPTION
        "The value of tmnxMcLagStatsDropOutOfSeq indicates how many MC-Lag
         control packets were dropped on this system because they were out of
         sequence."
    ::= { tmnxMcRedundancyStatsObjs 10 }

tmnxMcLagStatsDropUnknownTlv     OBJECT-TYPE
    SYNTAX      Counter32
    MAX-ACCESS  read-only
    STATUS      current
    DESCRIPTION
        "The value of tmnxMcLagStatsDropUnknownTlv indicates how many MC-Lag
         control packets were dropped on this system because they contained an
         unknown TLV."
    ::= { tmnxMcRedundancyStatsObjs 11 }

tmnxMcLagStatsDropTlvInvldLagId  OBJECT-TYPE
    SYNTAX      Counter32
    MAX-ACCESS  read-only
    STATUS      current
    DESCRIPTION
        "The value of tmnxMcLagStatsDropTlvInvldLagId indicates how many MC-Lag
         control packets were dropped on this system because they refer to an
         invalid or non multi-chassis lag."
    ::= { tmnxMcRedundancyStatsObjs 12 }

tmnxMcLagStatsDropMD5            OBJECT-TYPE
    SYNTAX      Counter32
    MAX-ACCESS  read-only
    STATUS      current
    DESCRIPTION
        "The value of tmnxMcLagStatsDropMD5 indicates how many MC-Lag control
         packets were dropped on this system because they failed MD5
         authentication."
    ::= { tmnxMcRedundancyStatsObjs 13 }

tmnxMcLagStatsDropUnknownPeer    OBJECT-TYPE
    SYNTAX      Counter32
    MAX-ACCESS  read-only
    STATUS      current
    DESCRIPTION
        "The value of tmnxMcLagStatsDropUnknownPeer indicates how many MC-Lag
         control packets were dropped on this system because they are coming
         from an unknown peer."
    ::= { tmnxMcRedundancyStatsObjs 14 }

tmnxMcLagStatsPktsTx             OBJECT-TYPE
    SYNTAX      Counter32
    MAX-ACCESS  read-only
    STATUS      current
    DESCRIPTION
        "The value of tmnxMcLagStatsPktsTx indicates how many MC-Lag control
         packets were transmitted from this system."
    ::= { tmnxMcRedundancyStatsObjs 15 }

tmnxMcLagStatsPktsTxKeepalive    OBJECT-TYPE
    SYNTAX      Counter32
    MAX-ACCESS  read-only
    STATUS      current
    DESCRIPTION
        "The value of tmnxMcLagStatsPktsTxKeepalive indicates how many MC-Lag
         control packets were transmitted from this system of type keepalive."
    ::= { tmnxMcRedundancyStatsObjs 16 }

tmnxMcLagStatsPktsTxConfig       OBJECT-TYPE
    SYNTAX      Counter32
    MAX-ACCESS  read-only
    STATUS      current
    DESCRIPTION
        "The value of tmnxMcLagStatsPktsTxConfig indicates how many MC-Lag
         control packets were transmitted from this system of type lag config."
    ::= { tmnxMcRedundancyStatsObjs 17 }

tmnxMcLagStatsPktsTxPeerConfig   OBJECT-TYPE
    SYNTAX      Counter32
    MAX-ACCESS  read-only
    STATUS      current
    DESCRIPTION
        "The value of tmnxMcLagStatsPktsTxPeerConfig indicates how many MC-Lag
         control packets were transmitted from this system of type peer config."
    ::= { tmnxMcRedundancyStatsObjs 18 }

tmnxMcLagStatsPktsTxState        OBJECT-TYPE
    SYNTAX      Counter32
    MAX-ACCESS  read-only
    STATUS      current
    DESCRIPTION
        "The value of tmnxMcLagStatsPktsTxState indicates how many MC-Lag
         control packets were transmitted from this system of type lag state."
    ::= { tmnxMcRedundancyStatsObjs 19 }

tmnxMcLagStatsPktsTxFailed       OBJECT-TYPE
    SYNTAX      Counter32
    MAX-ACCESS  read-only
    STATUS      current
    DESCRIPTION
        "The value of tmnxMcLagStatsPktsTxFailed indicates how many MC-Lag
         control packets failed to be transmitted."
    ::= { tmnxMcRedundancyStatsObjs 20 }

tmnxMcLagPeerStatsTable          OBJECT-TYPE
    SYNTAX      SEQUENCE OF TmnxMcLagPeerStatsEntry
    MAX-ACCESS  not-accessible
    STATUS      current
    DESCRIPTION
        "The tmnxMcLagPeerStatsTable has an entry for each multi-chassis peer
         configured on this system."
    ::= { tmnxMcRedundancyStatsObjs 21 }

tmnxMcLagPeerStatsEntry          OBJECT-TYPE
    SYNTAX      TmnxMcLagPeerStatsEntry
    MAX-ACCESS  not-accessible
    STATUS      current
    DESCRIPTION
        "Each row entry represents a collection of statistics for a
         multi-chassis peer.

         Entries cannot be created and deleted via SNMP SET operations."
    INDEX       {
        tmnxMcPeerIpType,
        tmnxMcPeerIpAddr
    }
    ::= { tmnxMcLagPeerStatsTable 1 }

TmnxMcLagPeerStatsEntry          ::= SEQUENCE
{
    tmnxMcLagPeerStatsPktsRx         Counter32,
    tmnxMcLagPeerStatsPktsRxKpalive  Counter32,
    tmnxMcLagPeerStatsPktsRxConfig   Counter32,
    tmnxMcLagPeerStatsPktsRxPeerCfg  Counter32,
    tmnxMcLagPeerStatsPktsRxState    Counter32,
    tmnxMcLagPeerStatsDropStateDsbld Counter32,
    tmnxMcLagPeerStatsDropPktTooShrt Counter32,
    tmnxMcLagPeerStatsDropTlvInvldSz Counter32,
    tmnxMcLagPeerStatsDropTlvInvldId Counter32,
    tmnxMcLagPeerStatsDropOutOfSeq   Counter32,
    tmnxMcLagPeerStatsDropUnknownTlv Counter32,
    tmnxMcLagPeerStatsDropMD5        Counter32,
    tmnxMcLagPeerStatsPktsTx         Counter32,
    tmnxMcLagPeerStatsPktsTxKpalive  Counter32,
    tmnxMcLagPeerStatsPktsTxPeerCfg  Counter32,
    tmnxMcLagPeerStatsPktsTxFailed   Counter32
}

tmnxMcLagPeerStatsPktsRx         OBJECT-TYPE
    SYNTAX      Counter32
    MAX-ACCESS  read-only
    STATUS      current
    DESCRIPTION
        "The value of tmnxMcLagPeerStatsPktsRx indicates how many valid MC-Lag
         control packets were received on this system from the peer."
    ::= { tmnxMcLagPeerStatsEntry 1 }

tmnxMcLagPeerStatsPktsRxKpalive  OBJECT-TYPE
    SYNTAX      Counter32
    MAX-ACCESS  read-only
    STATUS      current
    DESCRIPTION
        "The value of tmnxMcLagPeerStatsPktsRxKpalive indicates how many valid
         MC-Lag control packets of type keepalive were received on this system
         from the peer."
    ::= { tmnxMcLagPeerStatsEntry 2 }

tmnxMcLagPeerStatsPktsRxConfig   OBJECT-TYPE
    SYNTAX      Counter32
    MAX-ACCESS  read-only
    STATUS      current
    DESCRIPTION
        "The value of tmnxMcLagPeerStatsPktsRxConfig indicates how many valid
         MC-Lag control packets of type lag config were received on this system
         from the peer."
    ::= { tmnxMcLagPeerStatsEntry 3 }

tmnxMcLagPeerStatsPktsRxPeerCfg  OBJECT-TYPE
    SYNTAX      Counter32
    MAX-ACCESS  read-only
    STATUS      current
    DESCRIPTION
        "The value of tmnxMcLagPeerStatsPktsRxPeerCfg indicates how many valid
         MC-Lag control packets of type peer config were received on this
         system from the peer."
    ::= { tmnxMcLagPeerStatsEntry 4 }

tmnxMcLagPeerStatsPktsRxState    OBJECT-TYPE
    SYNTAX      Counter32
    MAX-ACCESS  read-only
    STATUS      current
    DESCRIPTION
        "The value of tmnxMcLagPeerStatsPktsRxState indicates how many valid
         MC-Lag control packets of type lag state were received on this system
         from the peer."
    ::= { tmnxMcLagPeerStatsEntry 5 }

tmnxMcLagPeerStatsDropStateDsbld OBJECT-TYPE
    SYNTAX      Counter32
    MAX-ACCESS  read-only
    STATUS      current
    DESCRIPTION
        "The value of tmnxMcLagPeerStatsDropStateDsbld indicates how many
         MC-Lag control packets were dropped on this system from the peer
         because the peer was administratively disabled."
    ::= { tmnxMcLagPeerStatsEntry 6 }

tmnxMcLagPeerStatsDropPktTooShrt OBJECT-TYPE
    SYNTAX      Counter32
    MAX-ACCESS  read-only
    STATUS      current
    DESCRIPTION
        "The value of tmnxMcLagPeerStatsDropPktTooShrt indicates how many
         MC-Lag control packets were dropped on this system from the peer
         because the packet was too short."
    ::= { tmnxMcLagPeerStatsEntry 7 }

tmnxMcLagPeerStatsDropTlvInvldSz OBJECT-TYPE
    SYNTAX      Counter32
    MAX-ACCESS  read-only
    STATUS      current
    DESCRIPTION
        "The value of tmnxMcLagPeerStatsDropTlvInvldSz indicates how many
         MC-Lag control packets were dropped on this system from the peer
         because the packet size was invalid."
    ::= { tmnxMcLagPeerStatsEntry 8 }

tmnxMcLagPeerStatsDropTlvInvldId OBJECT-TYPE
    SYNTAX      Counter32
    MAX-ACCESS  read-only
    STATUS      current
    DESCRIPTION
        "The value of tmnxMcLagPeerStatsDropTlvInvldId indicates how many
         MC-Lag control packets were dropped on this system from the peer
         because the packet referred to an invalid or non multi-chassis lag."
    ::= { tmnxMcLagPeerStatsEntry 9 }

tmnxMcLagPeerStatsDropOutOfSeq   OBJECT-TYPE
    SYNTAX      Counter32
    MAX-ACCESS  read-only
    STATUS      current
    DESCRIPTION
        "The value of tmnxMcLagPeerStatsDropOutOfSeq indicates how many MC-Lag
         control packets were dropped on this system from the peer because the
         packet was out of sequence."
    ::= { tmnxMcLagPeerStatsEntry 10 }

tmnxMcLagPeerStatsDropUnknownTlv OBJECT-TYPE
    SYNTAX      Counter32
    MAX-ACCESS  read-only
    STATUS      current
    DESCRIPTION
        "The value of tmnxMcLagPeerStatsDropUnknownTlv indicates how many
         MC-Lag control packets were dropped on this system from the peer
         because the packet contained an unknown TLV."
    ::= { tmnxMcLagPeerStatsEntry 11 }

tmnxMcLagPeerStatsDropMD5        OBJECT-TYPE
    SYNTAX      Counter32
    MAX-ACCESS  read-only
    STATUS      current
    DESCRIPTION
        "The value of tmnxMcLagPeerStatsDropMD5 indicates how many MC-Lag
         control packets were dropped on this system from the peer because the
         packet failed MD5 authentication."
    ::= { tmnxMcLagPeerStatsEntry 12 }

tmnxMcLagPeerStatsPktsTx         OBJECT-TYPE
    SYNTAX      Counter32
    MAX-ACCESS  read-only
    STATUS      current
    DESCRIPTION
        "The value of tmnxMcLagPeerStatsPktsTx indicates how many MC-Lag
         control packets were transmitted from this system to the peer."
    ::= { tmnxMcLagPeerStatsEntry 13 }

tmnxMcLagPeerStatsPktsTxKpalive  OBJECT-TYPE
    SYNTAX      Counter32
    MAX-ACCESS  read-only
    STATUS      current
    DESCRIPTION
        "The value of tmnxMcLagPeerStatsPktsTxKpalive indicates how many MC-Lag
         control packets of type keepalive were transmitted from this system to
         the peer."
    ::= { tmnxMcLagPeerStatsEntry 14 }

tmnxMcLagPeerStatsPktsTxPeerCfg  OBJECT-TYPE
    SYNTAX      Counter32
    MAX-ACCESS  read-only
    STATUS      current
    DESCRIPTION
        "The value of tmnxMcLagPeerStatsPktsTxPeerCfg indicates how many MC-Lag
         control packets of type peer config were transmitted from this system
         to the peer."
    ::= { tmnxMcLagPeerStatsEntry 15 }

tmnxMcLagPeerStatsPktsTxFailed   OBJECT-TYPE
    SYNTAX      Counter32
    MAX-ACCESS  read-only
    STATUS      current
    DESCRIPTION
        "The value of tmnxMcLagPeerStatsPktsTxFailed indicates how many MC-Lag
         control packets failed to be transmitted from this system to the peer."
    ::= { tmnxMcLagPeerStatsEntry 16 }

tmnxMcLagLagStatsTable           OBJECT-TYPE
    SYNTAX      SEQUENCE OF TmnxMcLagLagStatsEntry
    MAX-ACCESS  not-accessible
    STATUS      current
    DESCRIPTION
        "The tmnxMcLagLagStatsTable has an entry for each lag that participates
         in a multi-chassis configuration for the indicated peer."
    ::= { tmnxMcRedundancyStatsObjs 22 }

tmnxMcLagLagStatsEntry           OBJECT-TYPE
    SYNTAX      TmnxMcLagLagStatsEntry
    MAX-ACCESS  not-accessible
    STATUS      current
    DESCRIPTION
        "Each row entry represents a collection of statistics for a lag that
         participates in a multi-chassis configuration with a given peer.

         Entries cannot be created and deleted via SNMP SET operations."
    INDEX       {
        tmnxMcPeerIpType,
        tmnxMcPeerIpAddr,
        tmnxMcLagConfigLagId
    }
    ::= { tmnxMcLagLagStatsTable 1 }

TmnxMcLagLagStatsEntry           ::= SEQUENCE
{
    tmnxMcLagLagStatsPktsRxConfig    Counter32,
    tmnxMcLagLagStatsPktsRxState     Counter32,
    tmnxMcLagLagStatsPktsTxConfig    Counter32,
    tmnxMcLagLagStatsPktsTxState     Counter32,
    tmnxMcLagLagStatsPktsTxFailed    Counter32
}

tmnxMcLagLagStatsPktsRxConfig    OBJECT-TYPE
    SYNTAX      Counter32
    MAX-ACCESS  read-only
    STATUS      current
    DESCRIPTION
        "The value of tmnxMcLagLagStatsPktsRxConfig indicates how many MC-Lag
         control packets of type lag config were received on this system from
         the peer for this lag."
    ::= { tmnxMcLagLagStatsEntry 1 }

tmnxMcLagLagStatsPktsRxState     OBJECT-TYPE
    SYNTAX      Counter32
    MAX-ACCESS  read-only
    STATUS      current
    DESCRIPTION
        "The value of tmnxMcLagLagStatsPktsRxState indicates how many MC-Lag
         control packets of type lag state were received on this system from
         the peer for this lag."
    ::= { tmnxMcLagLagStatsEntry 2 }

tmnxMcLagLagStatsPktsTxConfig    OBJECT-TYPE
    SYNTAX      Counter32
    MAX-ACCESS  read-only
    STATUS      current
    DESCRIPTION
        "The value of tmnxMcLagLagStatsPktsTxConfig indicates how many MC-Lag
         control packets of type lag config were sent on this system to the
         peer for this lag."
    ::= { tmnxMcLagLagStatsEntry 3 }

tmnxMcLagLagStatsPktsTxState     OBJECT-TYPE
    SYNTAX      Counter32
    MAX-ACCESS  read-only
    STATUS      current
    DESCRIPTION
        "The value of tmnxMcLagLagStatsPktsTxState indicates how many MC-Lag
         control packets of type lag state were sent on this system to the peer
         for this lag."
    ::= { tmnxMcLagLagStatsEntry 4 }

tmnxMcLagLagStatsPktsTxFailed    OBJECT-TYPE
    SYNTAX      Counter32
    MAX-ACCESS  read-only
    STATUS      current
    DESCRIPTION
        "The value of tmnxMcLagLagStatsPktsTxFailed indicates how many MC-Lag
         control packets failed to be transmitted on this system to the peer
         for this lag."
    ::= { tmnxMcLagLagStatsEntry 5 }

tmnxMcPeerSyncStatsTable         OBJECT-TYPE
    SYNTAX      SEQUENCE OF TmnxMcPeerSyncStatsEntry
    MAX-ACCESS  not-accessible
    STATUS      current
    DESCRIPTION
        "The tmnxMcPeerSyncStatsTable has an entry for each multi-chassis peer
         synchronization protocol entry."
    ::= { tmnxMcRedundancyStatsObjs 23 }

tmnxMcPeerSyncStatsEntry         OBJECT-TYPE
    SYNTAX      TmnxMcPeerSyncStatsEntry
    MAX-ACCESS  not-accessible
    STATUS      current
    DESCRIPTION
        "Each row entry represents a collection of statistics for a
         multi-chassis synchronization protocol entry.

         Entries cannot be created and deleted via SNMP SET operations."
    INDEX       {
        tmnxMcPeerIpType,
        tmnxMcPeerIpAddr
    }
    ::= { tmnxMcPeerSyncStatsTable 1 }

TmnxMcPeerSyncStatsEntry         ::= SEQUENCE
{
    tmnxMcPeerSyncPktsTxAll          Counter32,
    tmnxMcPeerSyncPktsTxHello        Counter32,
    tmnxMcPeerSyncPktsTxData         Counter32,
    tmnxMcPeerSyncPktsTxOther        Counter32,
    tmnxMcPeerSyncPktsTxErr          Counter32,
    tmnxMcPeerSyncPktsRxAll          Counter32,
    tmnxMcPeerSyncPktsRxHello        Counter32,
    tmnxMcPeerSyncPktsRxData         Counter32,
    tmnxMcPeerSyncPktsRxOther        Counter32,
    tmnxMcPeerSyncPktsRxErr          Counter32,
    tmnxMcPeerSyncPktsRxErrHeader    Counter32,
    tmnxMcPeerSyncPktsRxErrBody      Counter32,
    tmnxMcPeerSyncPktsRxErrSeqNum    Counter32
}

tmnxMcPeerSyncPktsTxAll          OBJECT-TYPE
    SYNTAX      Counter32
    MAX-ACCESS  read-only
    STATUS      current
    DESCRIPTION
        "The value of tmnxMcPeerSyncPktsTxAll indicates the total number of
         packets transmitted to the multi-chassis peer."
    ::= { tmnxMcPeerSyncStatsEntry 1 }

tmnxMcPeerSyncPktsTxHello        OBJECT-TYPE
    SYNTAX      Counter32
    MAX-ACCESS  read-only
    STATUS      current
    DESCRIPTION
        "The value of tmnxMcPeerSyncPktsTxHello indicates the number of hello
         packets transmitted to the multi-chassis peer."
    ::= { tmnxMcPeerSyncStatsEntry 2 }

tmnxMcPeerSyncPktsTxData         OBJECT-TYPE
    SYNTAX      Counter32
    MAX-ACCESS  read-only
    STATUS      current
    DESCRIPTION
        "The value of tmnxMcPeerSyncPktsTxData indicates the number of data
         packets transmitted to the multi-chassis peer."
    ::= { tmnxMcPeerSyncStatsEntry 3 }

tmnxMcPeerSyncPktsTxOther        OBJECT-TYPE
    SYNTAX      Counter32
    MAX-ACCESS  read-only
    STATUS      current
    DESCRIPTION
        "The value of tmnxMcPeerSyncPktsTxOther indicates the number of all
         other packet types transmitted to the multi-chassis peer."
    ::= { tmnxMcPeerSyncStatsEntry 4 }

tmnxMcPeerSyncPktsTxErr          OBJECT-TYPE
    SYNTAX      Counter32
    MAX-ACCESS  read-only
    STATUS      current
    DESCRIPTION
        "The value of tmnxMcPeerSyncPktsTxErr indicates the number of packet
         transmission errors."
    ::= { tmnxMcPeerSyncStatsEntry 5 }

tmnxMcPeerSyncPktsRxAll          OBJECT-TYPE
    SYNTAX      Counter32
    MAX-ACCESS  read-only
    STATUS      current
    DESCRIPTION
        "The value of tmnxMcPeerSyncPktsRxAll indicates the total number of
         packets received from the multi-chassis peer."
    ::= { tmnxMcPeerSyncStatsEntry 6 }

tmnxMcPeerSyncPktsRxHello        OBJECT-TYPE
    SYNTAX      Counter32
    MAX-ACCESS  read-only
    STATUS      current
    DESCRIPTION
        "The value of tmnxMcPeerSyncPktsRxHello indicates the number of hello
         packets received from the multi-chassis peer."
    ::= { tmnxMcPeerSyncStatsEntry 7 }

tmnxMcPeerSyncPktsRxData         OBJECT-TYPE
    SYNTAX      Counter32
    MAX-ACCESS  read-only
    STATUS      current
    DESCRIPTION
        "The value of tmnxMcPeerSyncPktsRxData indicates the number of hello
         packets received from the multi-chassis peer."
    ::= { tmnxMcPeerSyncStatsEntry 8 }

tmnxMcPeerSyncPktsRxOther        OBJECT-TYPE
    SYNTAX      Counter32
    MAX-ACCESS  read-only
    STATUS      current
    DESCRIPTION
        "The value of tmnxMcPeerSyncPktsRxOther indicates the number of all
         other packet types received from the multi-chassis peer."
    ::= { tmnxMcPeerSyncStatsEntry 9 }

tmnxMcPeerSyncPktsRxErr          OBJECT-TYPE
    SYNTAX      Counter32
    MAX-ACCESS  read-only
    STATUS      current
    DESCRIPTION
        "The value of tmnxMcPeerSyncPktsRxErr indicates the number of erroneous
         packets received from the multi-chassis peer."
    ::= { tmnxMcPeerSyncStatsEntry 10 }

tmnxMcPeerSyncPktsRxErrHeader    OBJECT-TYPE
    SYNTAX      Counter32
    MAX-ACCESS  read-only
    STATUS      current
    DESCRIPTION
        "The value of tmnxMcPeerSyncPktsRxErrHeader indicates the number of
         packets with header decode errors received from the multi-chassis
         peer."
    ::= { tmnxMcPeerSyncStatsEntry 11 }

tmnxMcPeerSyncPktsRxErrBody      OBJECT-TYPE
    SYNTAX      Counter32
    MAX-ACCESS  read-only
    STATUS      current
    DESCRIPTION
        "The value of tmnxMcPeerSyncPktsRxErrBody indicates the number of
         packets with body decode errors received from the multi-chassis peer."
    ::= { tmnxMcPeerSyncStatsEntry 12 }

tmnxMcPeerSyncPktsRxErrSeqNum    OBJECT-TYPE
    SYNTAX      Counter32
    MAX-ACCESS  read-only
    STATUS      current
    DESCRIPTION
        "The value of tmnxMcPeerSyncPktsRxErrSeqNum indicates  the number
         of packets with sequence number errors received from the multi-chassis
         peer."
    ::= { tmnxMcPeerSyncStatsEntry 13 }

tmnxMcrPeerStatsTableLastChanged OBJECT-TYPE
    SYNTAX      TimeStamp
    MAX-ACCESS  read-only
    STATUS      current
    DESCRIPTION
        "The value of tmnxMcrPeerStatsTableLastChanged indicates the sysUpTime
         at the time of the last change of an entry in the
         tmnxMcrPeerStatsTable.

         If no changes occurred since the last re-initialization of the local
         network management subsystem, then this object contains a zero value."
    ::= { tmnxMcRedundancyStatsObjs 24 }

tmnxMcrPeerStatsTable            OBJECT-TYPE
    SYNTAX      SEQUENCE OF TmnxMcrPeerStatsEntry
    MAX-ACCESS  not-accessible
    STATUS      current
    DESCRIPTION
        "The tmnxMcrPeerStatsTable has an entry for each multi-chassis peer."
    ::= { tmnxMcRedundancyStatsObjs 25 }

tmnxMcrPeerStatsEntry            OBJECT-TYPE
    SYNTAX      TmnxMcrPeerStatsEntry
    MAX-ACCESS  not-accessible
    STATUS      current
    DESCRIPTION
        "Each row entry in the tmnxMcrPeerStatsTable represents additional
         columns of operational data for a multi-chassis peer."
    AUGMENTS    { tmnxMcPeerEntry }
    ::= { tmnxMcrPeerStatsTable 1 }

TmnxMcrPeerStatsEntry            ::= SEQUENCE
{
    tmnxMcrPeerStatsLastChanged      TimeStamp,
    tmnxMcrPeerStatsRx               Counter32,
    tmnxMcrPeerStatsRxMcsIdReq       Counter32,
    tmnxMcrPeerStatsRxMcsIdRsp       Counter32,
    tmnxMcrPeerStatsRxRingExistsReq  Counter32,
    tmnxMcrPeerStatsRxRingExistsRsp  Counter32,
    tmnxMcrPeerStatsRxKeepAlive      Counter32,
    tmnxMcrPeerStatsTx               Counter32,
    tmnxMcrPeerStatsTxMcsIdReq       Counter32,
    tmnxMcrPeerStatsTxMcsIdRsp       Counter32,
    tmnxMcrPeerStatsTxRingExistsReq  Counter32,
    tmnxMcrPeerStatsTxRingExistsRsp  Counter32,
    tmnxMcrPeerStatsTxKeepAlive      Counter32
}

tmnxMcrPeerStatsLastChanged      OBJECT-TYPE
    SYNTAX      TimeStamp
    MAX-ACCESS  read-only
    STATUS      current
    DESCRIPTION
        "The value of tmnxMcrPeerStatsLastChanged indicates the sysUpTime at
         the time of the last change of this entry.

         If no changes occurred since the last re-initialization of the local
         network management subsystem, then this object contains a zero value."
    ::= { tmnxMcrPeerStatsEntry 1 }

tmnxMcrPeerStatsRx               OBJECT-TYPE
    SYNTAX      Counter32
    MAX-ACCESS  read-only
    STATUS      current
    DESCRIPTION
        "The value of tmnxMcrPeerStatsRx indicates how many valid MC-Ring
         signalling messages were received from the peer."
    ::= { tmnxMcrPeerStatsEntry 2 }

tmnxMcrPeerStatsRxMcsIdReq       OBJECT-TYPE
    SYNTAX      Counter32
    MAX-ACCESS  read-only
    STATUS      current
    DESCRIPTION
        "The value of tmnxMcrPeerStatsRxMcsIdReq indicates how many valid MCS
         ID requests were received from the peer."
    ::= { tmnxMcrPeerStatsEntry 3 }

tmnxMcrPeerStatsRxMcsIdRsp       OBJECT-TYPE
    SYNTAX      Counter32
    MAX-ACCESS  read-only
    STATUS      current
    DESCRIPTION
        "The value of tmnxMcrPeerStatsRxMcsIdRsp indicates how many valid MCS
         ID responses were received from the peer."
    ::= { tmnxMcrPeerStatsEntry 4 }

tmnxMcrPeerStatsRxRingExistsReq  OBJECT-TYPE
    SYNTAX      Counter32
    MAX-ACCESS  read-only
    STATUS      current
    DESCRIPTION
        "The value of tmnxMcrPeerStatsRxRingExistsReq indicates how many valid
         'ring exists' requests were received from the peer."
    ::= { tmnxMcrPeerStatsEntry 5 }

tmnxMcrPeerStatsRxRingExistsRsp  OBJECT-TYPE
    SYNTAX      Counter32
    MAX-ACCESS  read-only
    STATUS      current
    DESCRIPTION
        "The value of tmnxMcrPeerStatsRxRingExistsRsp indicates how many valid
         'ring exists' responses were received from the peer."
    ::= { tmnxMcrPeerStatsEntry 6 }

tmnxMcrPeerStatsRxKeepAlive      OBJECT-TYPE
    SYNTAX      Counter32
    MAX-ACCESS  read-only
    STATUS      current
    DESCRIPTION
        "The value of tmnxMcrPeerStatsRxKeepAlive indicates how many valid
         MC-Ring control packets of type 'keepalive' were received from the
         peer."
    ::= { tmnxMcrPeerStatsEntry 7 }

tmnxMcrPeerStatsTx               OBJECT-TYPE
    SYNTAX      Counter32
    MAX-ACCESS  read-only
    STATUS      current
    DESCRIPTION
        "The value of tmnxMcrPeerStatsTx indicates how many valid MC-Ring
         signalling messages were transmitted to the peer."
    ::= { tmnxMcrPeerStatsEntry 8 }

tmnxMcrPeerStatsTxMcsIdReq       OBJECT-TYPE
    SYNTAX      Counter32
    MAX-ACCESS  read-only
    STATUS      current
    DESCRIPTION
        "The value of tmnxMcrPeerStatsTxMcsIdReq indicates how many valid MCS
         ID requests were transmitted to the peer."
    ::= { tmnxMcrPeerStatsEntry 9 }

tmnxMcrPeerStatsTxMcsIdRsp       OBJECT-TYPE
    SYNTAX      Counter32
    MAX-ACCESS  read-only
    STATUS      current
    DESCRIPTION
        "The value of tmnxMcrPeerStatsTxMcsIdRsp indicates how many valid MCS
         ID responses were transmitted to the peer."
    ::= { tmnxMcrPeerStatsEntry 10 }

tmnxMcrPeerStatsTxRingExistsReq  OBJECT-TYPE
    SYNTAX      Counter32
    MAX-ACCESS  read-only
    STATUS      current
    DESCRIPTION
        "The value of tmnxMcrPeerStatsTxRingExistsReq indicates how many valid
         'ring exists' requests were transmitted to the peer."
    ::= { tmnxMcrPeerStatsEntry 11 }

tmnxMcrPeerStatsTxRingExistsRsp  OBJECT-TYPE
    SYNTAX      Counter32
    MAX-ACCESS  read-only
    STATUS      current
    DESCRIPTION
        "The value of tmnxMcrPeerStatsTxRingExistsRsp indicates how many valid
         'ring exists' responses were transmitted to the peer."
    ::= { tmnxMcrPeerStatsEntry 12 }

tmnxMcrPeerStatsTxKeepAlive      OBJECT-TYPE
    SYNTAX      Counter32
    MAX-ACCESS  read-only
    STATUS      current
    DESCRIPTION
        "The value of tmnxMcrPeerStatsTxKeepAlive indicates how many valid
         MC-Ring control packets of type 'keepalive' were transmitted to the
         peer."
    ::= { tmnxMcrPeerStatsEntry 13 }

tmnxMcrRingStatsTableLastChanged OBJECT-TYPE
    SYNTAX      TimeStamp
    MAX-ACCESS  read-only
    STATUS      current
    DESCRIPTION
        "The value of tmnxMcrRingStatsTableLastChanged indicates the sysUpTime
         at the time of the last change of an entry in the
         tmnxMcrRingStatsTable.

         If no changes occurred since the last re-initialization of the local
         network management subsystem, then this object contains a zero value."
    ::= { tmnxMcRedundancyStatsObjs 26 }

tmnxMcrRingStatsTable            OBJECT-TYPE
    SYNTAX      SEQUENCE OF TmnxMcrRingStatsEntry
    MAX-ACCESS  not-accessible
    STATUS      current
    DESCRIPTION
        "The tmnxMcrRingStatsTable has an entry for each multi-chassis ring
         that participates in a multi-chassis configuration for the indicated
         peer."
    ::= { tmnxMcRedundancyStatsObjs 27 }

tmnxMcrRingStatsEntry            OBJECT-TYPE
    SYNTAX      TmnxMcrRingStatsEntry
    MAX-ACCESS  not-accessible
    STATUS      current
    DESCRIPTION
        "Each row entry in the tmnxMcrRingStatsTable represents additional
         columns of operational data for a ring that participates in a
         multi-chassis operation with a given peer."
    AUGMENTS    { tmnxMcRingEntry }
    ::= { tmnxMcrRingStatsTable 1 }

TmnxMcrRingStatsEntry            ::= SEQUENCE
{
    tmnxMcrRingStatsLastChanged      TimeStamp,
    tmnxMcrRingStatsRxSapsChanged    Counter32,
    tmnxMcrRingStatsTxSapsChanged    Counter32,
    tmnxMcrRingStatsRxOpaqueDelivrd  Counter32,
    tmnxMcrRingStatsRxOpaqueNoDest   Counter32,
    tmnxMcrRingStatsTxOpaque         Counter32
}

tmnxMcrRingStatsLastChanged      OBJECT-TYPE
    SYNTAX      TimeStamp
    MAX-ACCESS  read-only
    STATUS      current
    DESCRIPTION
        "The value of tmnxMcrRingStatsLastChanged indicates the sysUpTime at
         the time of the last change of this entry.

         If no changes occurred since the last re-initialization of the local
         network management subsystem, then this object contains a zero value."
    ::= { tmnxMcrRingStatsEntry 1 }

tmnxMcrRingStatsRxSapsChanged    OBJECT-TYPE
    SYNTAX      Counter32
    MAX-ACCESS  read-only
    STATUS      current
    DESCRIPTION
        "The value of tmnxMcrRingStatsRxSapsChanged indicates how many valid
         'SAPs changed info' signalling messages were received from the peer
         for this multi-chassis ring."
    ::= { tmnxMcrRingStatsEntry 2 }

tmnxMcrRingStatsTxSapsChanged    OBJECT-TYPE
    SYNTAX      Counter32
    MAX-ACCESS  read-only
    STATUS      current
    DESCRIPTION
        "The value of tmnxMcrRingStatsTxSapsChanged indicates how many valid
         'SAPs changed info' signalling messages were transmitted to the peer
         for this multi-chassis ring."
    ::= { tmnxMcrRingStatsEntry 3 }

tmnxMcrRingStatsRxOpaqueDelivrd  OBJECT-TYPE
    SYNTAX      Counter32
    MAX-ACCESS  read-only
    STATUS      current
    DESCRIPTION
        "The value of tmnxMcrRingStatsRxOpaqueDelivrd indicates how many valid
         opaque signalling messages were received from the peer and delivered
         for this multi-chassis ring."
    ::= { tmnxMcrRingStatsEntry 4 }

tmnxMcrRingStatsRxOpaqueNoDest   OBJECT-TYPE
    SYNTAX      Counter32
    MAX-ACCESS  read-only
    STATUS      current
    DESCRIPTION
        "The value of tmnxMcrRingStatsRxOpaqueNoDest indicates how many valid
         opaque signalling messages were received from the peer and for which
         no destination could be found."
    ::= { tmnxMcrRingStatsEntry 5 }

tmnxMcrRingStatsTxOpaque         OBJECT-TYPE
    SYNTAX      Counter32
    MAX-ACCESS  read-only
    STATUS      current
    DESCRIPTION
        "The value of tmnxMcrRingStatsTxOpaque indicates how many valid opaque
         signalling messages were transmitted to the peer for this
         multi-chassis ring."
    ::= { tmnxMcrRingStatsEntry 6 }

tmnxMcrStatsRx                   OBJECT-TYPE
    SYNTAX      Counter32
    MAX-ACCESS  read-only
    STATUS      current
    DESCRIPTION
        "The value of tmnxMcrStatsRx indicates how many MC-Ring signalling
         packets were received by this system."
    ::= { tmnxMcRedundancyStatsObjs 28 }

tmnxMcrStatsRxTooShort           OBJECT-TYPE
    SYNTAX      Counter32
    MAX-ACCESS  read-only
    STATUS      current
    DESCRIPTION
        "The value of tmnxMcrStatsRxTooShort indicates how many MC-Ring
         signalling packets were received by this system that were too short."
    ::= { tmnxMcRedundancyStatsObjs 29 }

tmnxMcrStatsRxWrongAuth          OBJECT-TYPE
    SYNTAX      Counter32
    MAX-ACCESS  read-only
    STATUS      current
    DESCRIPTION
        "The value of tmnxMcrStatsRxWrongAuth indicates how many MC-Ring
         signalling packets were received by this system with invalid
         authentication."
    ::= { tmnxMcRedundancyStatsObjs 30 }

tmnxMcrStatsRxInvalidTlv         OBJECT-TYPE
    SYNTAX      Counter32
    MAX-ACCESS  read-only
    STATUS      current
    DESCRIPTION
        "The value of tmnxMcrStatsRxInvalidTlv indicates how many MC-Ring
         signalling packets were received by this system with invalid TLV."
    ::= { tmnxMcRedundancyStatsObjs 31 }

tmnxMcrStatsRxIncomplete         OBJECT-TYPE
    SYNTAX      Counter32
    MAX-ACCESS  read-only
    STATUS      current
    DESCRIPTION
        "The value of tmnxMcrStatsRxIncomplete indicates how many MC-Ring
         signalling packets were received by this system that were incomplete."
    ::= { tmnxMcRedundancyStatsObjs 32 }

tmnxMcrStatsRxUnknownType        OBJECT-TYPE
    SYNTAX      Counter32
    MAX-ACCESS  read-only
    STATUS      current
    DESCRIPTION
        "The value of tmnxMcrStatsRxUnknownType indicates how many MC-Ring
         signalling packets were received by this system that were of unknown
         type."
    ::= { tmnxMcRedundancyStatsObjs 33 }

tmnxMcrStatsRxUnknownPeer        OBJECT-TYPE
    SYNTAX      Counter32
    MAX-ACCESS  read-only
    STATUS      current
    DESCRIPTION
        "The value of tmnxMcrStatsRxUnknownPeer indicates how many MC-Ring
         signalling packets were received by this system that were related to
         an unknown peer."
    ::= { tmnxMcRedundancyStatsObjs 34 }

tmnxMcrStatsRxUnknownRing        OBJECT-TYPE
    SYNTAX      Counter32
    MAX-ACCESS  read-only
    STATUS      current
    DESCRIPTION
        "The value of tmnxMcrStatsRxUnknownRing indicates how many MC-Ring
         signalling packets were received by this system that were related to
         an unknown ring."
    ::= { tmnxMcRedundancyStatsObjs 35 }

tmnxMcrStatsRxUnknownRingNode    OBJECT-TYPE
    SYNTAX      Counter32
    MAX-ACCESS  read-only
    STATUS      current
    DESCRIPTION
        "The value of tmnxMcrStatsRxUnknownRingNode indicates how many MC-Ring
         signalling packets were received by this system that were related to
         an unknown ring node."
    ::= { tmnxMcRedundancyStatsObjs 36 }

tmnxMcrStatsRxDelivrdToPeer      OBJECT-TYPE
    SYNTAX      Counter32
    MAX-ACCESS  read-only
    STATUS      current
    DESCRIPTION
        "The value of tmnxMcrStatsRxDelivrdToPeer indicates how many MC-Ring
         signalling packets were received by this system that were correctly
         delivered to their peer."
    ::= { tmnxMcRedundancyStatsObjs 37 }

tmnxMcrStatsRxDelivrdToRing      OBJECT-TYPE
    SYNTAX      Counter32
    MAX-ACCESS  read-only
    STATUS      current
    DESCRIPTION
        "The value of tmnxMcrStatsRxDelivrdToRing indicates how many MC-Ring
         signalling packets were received by this system that were correctly
         delivered to their ring."
    ::= { tmnxMcRedundancyStatsObjs 38 }

tmnxMcrStatsRxDelivrdToRingNode  OBJECT-TYPE
    SYNTAX      Counter32
    MAX-ACCESS  read-only
    STATUS      current
    DESCRIPTION
        "The value of tmnxMcrStatsRxDelivrdToRingNode indicates how many MC-R
         signalling packets were received by this system that were correctly
         delivered to their ring node."
    ::= { tmnxMcRedundancyStatsObjs 39 }

tmnxMcrStatsTx                   OBJECT-TYPE
    SYNTAX      Counter32
    MAX-ACCESS  read-only
    STATUS      current
    DESCRIPTION
        "The value of tmnxMcrStatsTx indicates how many MC-Ring signalling
         packets were transmitted by this system."
    ::= { tmnxMcRedundancyStatsObjs 40 }

tmnxMcrStatsTxNoBuffer           OBJECT-TYPE
    SYNTAX      Counter32
    MAX-ACCESS  read-only
    STATUS      current
    DESCRIPTION
        "The value of tmnxMcrStatsTxNoBuffer indicates how many MC-Ring
         signalling packets could not be transmitted by this system due to a
         lack of packet buffers."
    ::= { tmnxMcRedundancyStatsObjs 41 }

tmnxMcrStatsTxTransmitFailed     OBJECT-TYPE
    SYNTAX      Counter32
    MAX-ACCESS  read-only
    STATUS      current
    DESCRIPTION
        "The value of tmnxMcrStatsTxTransmitFailed indicates how many MC-Ring
         signalling packets could not be transmitted by this system due to a
         transmission failure."
    ::= { tmnxMcRedundancyStatsObjs 42 }

tmnxMcrStatsMissedConfigEvent    OBJECT-TYPE
    SYNTAX      Counter32
    MAX-ACCESS  read-only
    STATUS      current
    DESCRIPTION
        "The value of tmnxMcrStatsMissedConfigEvent indicates the number of
         missed configuration events on this system."
    ::= { tmnxMcRedundancyStatsObjs 43 }

tmnxMcrStatsMissedBfdEvent       OBJECT-TYPE
    SYNTAX      Counter32
    MAX-ACCESS  read-only
    STATUS      current
    DESCRIPTION
        "The value of tmnxMcrStatsMissedBfdEvent indicates the number of missed
         BFD events on this system."
    ::= { tmnxMcRedundancyStatsObjs 44 }

tmnxMcrStatsTxUnknownDest        OBJECT-TYPE
    SYNTAX      Counter32
    MAX-ACCESS  read-only
    STATUS      current
    DESCRIPTION
        "The value of tmnxMcrStatsTxUnknownDest indicates how many MC-R
         signalling packets were dropped because the destination was unknown."
    ::= { tmnxMcRedundancyStatsObjs 45 }

tmnxMcrRingNodeStatsTableLastChanged OBJECT-TYPE
    SYNTAX      TimeStamp
    MAX-ACCESS  read-only
    STATUS      current
    DESCRIPTION
        "The value of tmnxMcrRingNodeStatsTableLastChanged indicates the
         sysUpTime at the time of the last change of an entry in the
         tmnxMcrRingNodeStatsTable.

         If no changes occurred since the last re-initialization of the local
         network management subsystem, then this object contains a zero value."
    ::= { tmnxMcRedundancyStatsObjs 46 }

tmnxMcrRingNodeStatsTable        OBJECT-TYPE
    SYNTAX      SEQUENCE OF TmnxMcrRingNodeStatsEntry
    MAX-ACCESS  not-accessible
    STATUS      current
    DESCRIPTION
        "The tmnxMcrRingNodeStatsTable has an entry for each access node that
         participates in a multi-chassis ring configuration for the indicated
         peer."
    ::= { tmnxMcRedundancyStatsObjs 47 }

tmnxMcrRingNodeStatsEntry        OBJECT-TYPE
    SYNTAX      TmnxMcrRingNodeStatsEntry
    MAX-ACCESS  not-accessible
    STATUS      current
    DESCRIPTION
        "Each row entry represents statistics related to an access node that
         participates in a multi-chassis ring configuration with a given peer.

         Rows are created or removed automatically by the system."
    AUGMENTS    { tmnxMcRingNodeEntry }
    ::= { tmnxMcrRingNodeStatsTable 1 }

TmnxMcrRingNodeStatsEntry        ::= SEQUENCE
{
    tmnxMcrRingNodeStatsLastChanged  TimeStamp,
    tmnxMcrRingNodeStatsRxDetect     Counter32,
    tmnxMcrRingNodeStatsRxDetectAck  Counter32,
    tmnxMcrRingNodeStatsRncvRxResp   Counter32,
    tmnxMcrRingNodeStatsTxDetect     Counter32,
    tmnxMcrRingNodeStatsTxDetectAck  Counter32,
    tmnxMcrRingNodeStatsRncvTxReq    Counter32,
    tmnxMcrRingNodeStatsRncvRtTime   TimeInterval
}

tmnxMcrRingNodeStatsLastChanged  OBJECT-TYPE
    SYNTAX      TimeStamp
    MAX-ACCESS  read-only
    STATUS      current
    DESCRIPTION
        "The value of tmnxMcrRingNodeStatsLastChanged indicates the sysUpTime
         at the time of the last change of this entry.

         If no changes occurred since the last re-initialization of the local
         network management subsystem, then this object contains a zero value."
    ::= { tmnxMcrRingNodeStatsEntry 1 }

tmnxMcrRingNodeStatsRxDetect     OBJECT-TYPE
    SYNTAX      Counter32
    MAX-ACCESS  read-only
    STATUS      current
    DESCRIPTION
        "The value of tmnxMcrRingNodeStatsRxDetect indicates how many valid
         'detected ring node' signalling messages were received from the peer
         for this multi-chassis ring node."
    ::= { tmnxMcrRingNodeStatsEntry 2 }

tmnxMcrRingNodeStatsRxDetectAck  OBJECT-TYPE
    SYNTAX      Counter32
    MAX-ACCESS  read-only
    STATUS      current
    DESCRIPTION
        "The value of tmnxMcrRingNodeStatsRxDetectAck indicates how many valid
         'detected ring node' signalling messages were acknowledged by the peer
         for this multi-chassis ring node."
    ::= { tmnxMcrRingNodeStatsEntry 3 }

tmnxMcrRingNodeStatsRncvRxResp   OBJECT-TYPE
    SYNTAX      Counter32
    MAX-ACCESS  read-only
    STATUS      current
    DESCRIPTION
        "The value of tmnxMcrRingNodeStatsRncvRxResp indicates how many valid
         connectivity verification messages were received from this
         multi-chassis ring node."
    ::= { tmnxMcrRingNodeStatsEntry 4 }

tmnxMcrRingNodeStatsTxDetect     OBJECT-TYPE
    SYNTAX      Counter32
    MAX-ACCESS  read-only
    STATUS      current
    DESCRIPTION
        "The value of tmnxMcrRingNodeStatsTxDetect indicates how many valid
         'detected ring node' signalling messages were transmitted to the peer
         for this multi-chassis ring node."
    ::= { tmnxMcrRingNodeStatsEntry 5 }

tmnxMcrRingNodeStatsTxDetectAck  OBJECT-TYPE
    SYNTAX      Counter32
    MAX-ACCESS  read-only
    STATUS      current
    DESCRIPTION
        "The value of tmnxMcrRingNodeStatsTxDetectAck indicates how many valid
         'detected ring node' signalling messages were acknowledged to the peer
         for this multi-chassis ring node."
    ::= { tmnxMcrRingNodeStatsEntry 6 }

tmnxMcrRingNodeStatsRncvTxReq    OBJECT-TYPE
    SYNTAX      Counter32
    MAX-ACCESS  read-only
    STATUS      current
    DESCRIPTION
        "The value of tmnxMcrRingNodeStatsRncvTxReq indicates how many valid
         connectivity verification messages were transmitted to this
         multi-chassis ring node."
    ::= { tmnxMcrRingNodeStatsEntry 7 }

tmnxMcrRingNodeStatsRncvRtTime   OBJECT-TYPE
    SYNTAX      TimeInterval
    MAX-ACCESS  read-only
    STATUS      current
    DESCRIPTION
        "The value of tmnxMcrRingNodeStatsRncvRtTime indicates the
         round-trip-time of the last successful connectivity verification for
         this multi-chassis ring node.

         If there has not been a successful connectivity verification, the
         value of tmnxMcrRingNodeStatsRncvRtTime is zero."
    ::= { tmnxMcrRingNodeStatsEntry 8 }

tmnxMcEPPeerStatsTable           OBJECT-TYPE
    SYNTAX      SEQUENCE OF TmnxMcEPPeerStatsEntry
    MAX-ACCESS  not-accessible
    STATUS      current
    DESCRIPTION
        "The tmnxMcEPPeerStatsTable has an entry for each multi-chassis peer
         configured on this system."
    ::= { tmnxMcRedundancyStatsObjs 48 }

tmnxMcEPPeerStatsEntry           OBJECT-TYPE
    SYNTAX      TmnxMcEPPeerStatsEntry
    MAX-ACCESS  not-accessible
    STATUS      current
    DESCRIPTION
        "Each row entry represents a collection of statistics for a
         multi-chassis peer.

         Entries cannot be created and deleted via SNMP SET operations."
    INDEX       {
        tmnxMcPeerIpType,
        tmnxMcPeerIpAddr
    }
    ::= { tmnxMcEPPeerStatsTable 1 }

TmnxMcEPPeerStatsEntry           ::= SEQUENCE
{
    tmnxMcEPPeerStatsPktsRx          Counter32,
    tmnxMcEPPeerStatsPktsRxKpalive   Counter32,
    tmnxMcEPPeerStatsPktsRxConfig    Counter32,
    tmnxMcEPPeerStatsPktsRxPeerCfg   Counter32,
    tmnxMcEPPeerStatsPktsRxState     Counter32,
    tmnxMcEPPeerStatsDropStateDsbld  Counter32,
    tmnxMcEPPeerStatsDropPktTooShrt  Counter32,
    tmnxMcEPPeerStatsDropTlvInvldSz  Counter32,
    tmnxMcEPPeerStatsDropTlvInvldId  Counter32,
    tmnxMcEPPeerStatsDropOutOfSeq    Counter32,
    tmnxMcEPPeerStatsDropUnknownTlv  Counter32,
    tmnxMcEPPeerStatsDropMD5         Counter32,
    tmnxMcEPPeerStatsPktsTx          Counter32,
    tmnxMcEPPeerStatsPktsTxKpalive   Counter32,
    tmnxMcEPPeerStatsPktsTxPeerCfg   Counter32,
    tmnxMcEPPeerStatsPktsTxFailed    Counter32,
    tmnxMcEPPeerStatsDropEpNoPeer    Counter32
}

tmnxMcEPPeerStatsPktsRx          OBJECT-TYPE
    SYNTAX      Counter32
    MAX-ACCESS  read-only
    STATUS      current
    DESCRIPTION
        "The value of tmnxMcEPPeerStatsPktsRx indicates how many valid
         MC-Endpoint control packets were received on this system from the
         peer."
    ::= { tmnxMcEPPeerStatsEntry 1 }

tmnxMcEPPeerStatsPktsRxKpalive   OBJECT-TYPE
    SYNTAX      Counter32
    MAX-ACCESS  read-only
    STATUS      current
    DESCRIPTION
        "The value of tmnxMcEPPeerStatsPktsRxKpalive indicates how many valid
         MC-Endpoint control packets of type keepalive were received on this
         system from the peer."
    ::= { tmnxMcEPPeerStatsEntry 2 }

tmnxMcEPPeerStatsPktsRxConfig    OBJECT-TYPE
    SYNTAX      Counter32
    MAX-ACCESS  read-only
    STATUS      current
    DESCRIPTION
        "The value of tmnxMcEPPeerStatsPktsRxConfig indicates how many valid
         MC-Endpoint control packets of type end-point config were received on
         this system from the peer."
    ::= { tmnxMcEPPeerStatsEntry 3 }

tmnxMcEPPeerStatsPktsRxPeerCfg   OBJECT-TYPE
    SYNTAX      Counter32
    MAX-ACCESS  read-only
    STATUS      current
    DESCRIPTION
        "The value of tmnxMcEPPeerStatsPktsRxPeerCfg indicates how many valid
         MC-Endpoint control packets of type peer config were received on this
         system from the peer."
    ::= { tmnxMcEPPeerStatsEntry 4 }

tmnxMcEPPeerStatsPktsRxState     OBJECT-TYPE
    SYNTAX      Counter32
    MAX-ACCESS  read-only
    STATUS      current
    DESCRIPTION
        "The value of tmnxMcEPPeerStatsPktsRxState indicates how many valid
         MC-Endpoint control packets of type end-point state were received on
         this system from the peer."
    ::= { tmnxMcEPPeerStatsEntry 5 }

tmnxMcEPPeerStatsDropStateDsbld  OBJECT-TYPE
    SYNTAX      Counter32
    MAX-ACCESS  read-only
    STATUS      current
    DESCRIPTION
        "The value of tmnxMcEPPeerStatsDropStateDsbld indicates how many
         MC-Endpoint control packets were dropped on this system from the peer
         because the peer was administratively disabled."
    ::= { tmnxMcEPPeerStatsEntry 6 }

tmnxMcEPPeerStatsDropPktTooShrt  OBJECT-TYPE
    SYNTAX      Counter32
    MAX-ACCESS  read-only
    STATUS      current
    DESCRIPTION
        "The value of tmnxMcEPPeerStatsDropPktTooShrt indicates how many
         MC-Endpoint control packets were dropped on this system from the peer
         because the packet was too short."
    ::= { tmnxMcEPPeerStatsEntry 7 }

tmnxMcEPPeerStatsDropTlvInvldSz  OBJECT-TYPE
    SYNTAX      Counter32
    MAX-ACCESS  read-only
    STATUS      current
    DESCRIPTION
        "The value of tmnxMcEPPeerStatsDropTlvInvldSz indicates how many
         MC-Endpoint control packets were dropped on this system from the peer
         because the packet size was invalid."
    ::= { tmnxMcEPPeerStatsEntry 8 }

tmnxMcEPPeerStatsDropTlvInvldId  OBJECT-TYPE
    SYNTAX      Counter32
    MAX-ACCESS  read-only
    STATUS      current
    DESCRIPTION
        "The value of tmnxMcEPPeerStatsDropTlvInvldId indicates how many
         MC-Endpoint control packets were dropped on this system from the peer
         because the packet referred to an invalid or non multi-chassis
         end-point."
    ::= { tmnxMcEPPeerStatsEntry 9 }

tmnxMcEPPeerStatsDropOutOfSeq    OBJECT-TYPE
    SYNTAX      Counter32
    MAX-ACCESS  read-only
    STATUS      current
    DESCRIPTION
        "The value of tmnxMcEPPeerStatsDropOutOfSeq indicates how many
         MC-Endpoint control packets were dropped on this system from the peer
         because the packet was out of sequence."
    ::= { tmnxMcEPPeerStatsEntry 10 }

tmnxMcEPPeerStatsDropUnknownTlv  OBJECT-TYPE
    SYNTAX      Counter32
    MAX-ACCESS  read-only
    STATUS      current
    DESCRIPTION
        "The value of tmnxMcEPPeerStatsDropUnknownTlv indicates how many
         MC-Endpoint control packets were dropped on this system from the peer
         because the packet contained an unknown TLV."
    ::= { tmnxMcEPPeerStatsEntry 11 }

tmnxMcEPPeerStatsDropMD5         OBJECT-TYPE
    SYNTAX      Counter32
    MAX-ACCESS  read-only
    STATUS      current
    DESCRIPTION
        "The value of tmnxMcEPPeerStatsDropMD5 indicates how many MC-Endpoint
         control packets were dropped on this system from the peer because the
         packet failed MD5 authentication."
    ::= { tmnxMcEPPeerStatsEntry 12 }

tmnxMcEPPeerStatsPktsTx          OBJECT-TYPE
    SYNTAX      Counter32
    MAX-ACCESS  read-only
    STATUS      current
    DESCRIPTION
        "The value of tmnxMcEPPeerStatsPktsTx indicates how many MC-Endpoint
         control packets were transmitted from this system to the peer."
    ::= { tmnxMcEPPeerStatsEntry 13 }

tmnxMcEPPeerStatsPktsTxKpalive   OBJECT-TYPE
    SYNTAX      Counter32
    MAX-ACCESS  read-only
    STATUS      current
    DESCRIPTION
        "The value of tmnxMcEPPeerStatsPktsTxKpalive indicates how many
         MC-Endpoint control packets of type keepalive were transmitted from
         this system to the peer."
    ::= { tmnxMcEPPeerStatsEntry 14 }

tmnxMcEPPeerStatsPktsTxPeerCfg   OBJECT-TYPE
    SYNTAX      Counter32
    MAX-ACCESS  read-only
    STATUS      current
    DESCRIPTION
        "The value of tmnxMcEPPeerStatsPktsTxPeerCfg indicates how many
         MC-Endpoint control packets of type peer config were transmitted from
         this system to the peer."
    ::= { tmnxMcEPPeerStatsEntry 15 }

tmnxMcEPPeerStatsPktsTxFailed    OBJECT-TYPE
    SYNTAX      Counter32
    MAX-ACCESS  read-only
    STATUS      current
    DESCRIPTION
        "The value of tmnxMcEPPeerStatsPktsTxFailed indicates how many
         MC-Endpoint control packets failed to be transmitted from this system
         to the peer."
    ::= { tmnxMcEPPeerStatsEntry 16 }

tmnxMcEPPeerStatsDropEpNoPeer    OBJECT-TYPE
    SYNTAX      Counter32
    MAX-ACCESS  read-only
    STATUS      current
    DESCRIPTION
        "The value of tmnxMcEPPeerStatsDropEpNoPeer indicates how many pkts
         were dropped because MC-Endpoint does not have a MC-peer assigned yet
         or MC-Endpoint is attached to a different peer."
    ::= { tmnxMcEPPeerStatsEntry 17 }

tmnxMcEpGlobalStats              OBJECT IDENTIFIER ::= { tmnxMcRedundancyStatsObjs 49 }

tmnxMcEpStatsPktsRx              OBJECT-TYPE
    SYNTAX      Counter32
    MAX-ACCESS  read-only
    STATUS      current
    DESCRIPTION
        "The value of tmnxMcEpStatsPktsRx indicates how many MC-EP control
         packets with valid authentication were received on this system."
    ::= { tmnxMcEpGlobalStats 1 }

tmnxMcEpStatsPktsRxKeepalive     OBJECT-TYPE
    SYNTAX      Counter32
    MAX-ACCESS  read-only
    STATUS      current
    DESCRIPTION
        "The value of tmnxMcEpStatsPktsRxKeepalive indicates how many valid
         MC-EP control packets of type keepalive were received on this system."
    ::= { tmnxMcEpGlobalStats 2 }

tmnxMcEpStatsPktsRxConfig        OBJECT-TYPE
    SYNTAX      Counter32
    MAX-ACCESS  read-only
    STATUS      current
    DESCRIPTION
        "The value of tmnxMcEpStatsPktsRxConfig indicates how many valid MC-EP
         control packets indicating the lag configuration were received on this
         system."
    ::= { tmnxMcEpGlobalStats 3 }

tmnxMcEpStatsPktsRxPeerConfig    OBJECT-TYPE
    SYNTAX      Counter32
    MAX-ACCESS  read-only
    STATUS      current
    DESCRIPTION
        "The value of tmnxMcEpStatsPktsRxPeerConfig indicates how many valid
         MC-EP control packets indicating the peer configuration were received
         on this system."
    ::= { tmnxMcEpGlobalStats 4 }

tmnxMcEpStatsPktsRxState         OBJECT-TYPE
    SYNTAX      Counter32
    MAX-ACCESS  read-only
    STATUS      current
    DESCRIPTION
        "The value of tmnxMcEpStatsPktsRxState indicates how many valid MC-EP
         control packets indicating the lag state were received on this system."
    ::= { tmnxMcEpGlobalStats 5 }

tmnxMcEpStatsDropPktKpaliveTask  OBJECT-TYPE
    SYNTAX      Counter32
    MAX-ACCESS  read-only
    STATUS      current
    DESCRIPTION
        "The value of tmnxMcEpStatsDropPktKpaliveTask indicates how many MC-EP
         control packets were dropped on this system because of invalid size,
         authentication or unknown peer."
    ::= { tmnxMcEpGlobalStats 6 }

tmnxMcEpStatsDropPktTooShort     OBJECT-TYPE
    SYNTAX      Counter32
    MAX-ACCESS  read-only
    STATUS      current
    DESCRIPTION
        "The value of tmnxMcEpStatsDropPktTooShort indicates how many MC-EP
         control packets were dropped on this system because the packet was too
         small."
    ::= { tmnxMcEpGlobalStats 7 }

tmnxMcEpStatsDropPktVerifyFailed OBJECT-TYPE
    SYNTAX      Counter32
    MAX-ACCESS  read-only
    STATUS      current
    DESCRIPTION
        "The value of tmnxMcEpStatsDropPktVerifyFailed indicates how many MC-EP
         control packets were dropped on this system because of invalid
         formatting."
    ::= { tmnxMcEpGlobalStats 8 }

tmnxMcEpStatsDropTlvInvalidSize  OBJECT-TYPE
    SYNTAX      Counter32
    MAX-ACCESS  read-only
    STATUS      current
    DESCRIPTION
        "The value of tmnxMcEpStatsDropTlvInvalidSize indicates how many MC-EP
         control packets were dropped on this system because of invalid size."
    ::= { tmnxMcEpGlobalStats 9 }

tmnxMcEpStatsDropOutOfSeq        OBJECT-TYPE
    SYNTAX      Counter32
    MAX-ACCESS  read-only
    STATUS      current
    DESCRIPTION
        "The value of tmnxMcEpStatsDropOutOfSeq indicates how many MC-EP
         control packets were dropped on this system because they were out of
         sequence."
    ::= { tmnxMcEpGlobalStats 10 }

tmnxMcEpStatsDropUnknownTlv      OBJECT-TYPE
    SYNTAX      Counter32
    MAX-ACCESS  read-only
    STATUS      current
    DESCRIPTION
        "The value of tmnxMcEpStatsDropUnknownTlv indicates how many MC-EP
         control packets were dropped on this system because they contained an
         unknown TLV."
    ::= { tmnxMcEpGlobalStats 11 }

tmnxMcEpStatsDropTlvInvldEpId    OBJECT-TYPE
    SYNTAX      Counter32
    MAX-ACCESS  read-only
    STATUS      current
    DESCRIPTION
        "The value of tmnxMcEpStatsDropTlvInvldEpId indicates how many MC-EP
         control packets were dropped on this system because they refer to an
         invalid or non multi-chassis lag."
    ::= { tmnxMcEpGlobalStats 12 }

tmnxMcEpStatsDropMD5             OBJECT-TYPE
    SYNTAX      Counter32
    MAX-ACCESS  read-only
    STATUS      current
    DESCRIPTION
        "The value of tmnxMcEpStatsDropMD5 indicates how many MC-EP control
         packets were dropped on this system because they failed MD5
         authentication."
    ::= { tmnxMcEpGlobalStats 13 }

tmnxMcEpStatsDropUnknownPeer     OBJECT-TYPE
    SYNTAX      Counter32
    MAX-ACCESS  read-only
    STATUS      current
    DESCRIPTION
        "The value of tmnxMcEpStatsDropUnknownPeer indicates how many MC-EP
         control packets were dropped on this system because they are coming
         from an unknown peer."
    ::= { tmnxMcEpGlobalStats 14 }

tmnxMcEpStatsPktsTx              OBJECT-TYPE
    SYNTAX      Counter32
    MAX-ACCESS  read-only
    STATUS      current
    DESCRIPTION
        "The value of tmnxMcEpStatsPktsTx indicates how many MC-EP control
         packets were transmitted from this system."
    ::= { tmnxMcEpGlobalStats 15 }

tmnxMcEpStatsPktsTxKeepalive     OBJECT-TYPE
    SYNTAX      Counter32
    MAX-ACCESS  read-only
    STATUS      current
    DESCRIPTION
        "The value of tmnxMcEpStatsPktsTxKeepalive indicates how many MC-EP
         control packets were transmitted from this system of type keepalive."
    ::= { tmnxMcEpGlobalStats 16 }

tmnxMcEpStatsPktsTxConfig        OBJECT-TYPE
    SYNTAX      Counter32
    MAX-ACCESS  read-only
    STATUS      current
    DESCRIPTION
        "The value of tmnxMcEpStatsPktsTxConfig indicates how many MC-EP
         control packets were transmitted from this system of type lag config."
    ::= { tmnxMcEpGlobalStats 17 }

tmnxMcEpStatsPktsTxPeerConfig    OBJECT-TYPE
    SYNTAX      Counter32
    MAX-ACCESS  read-only
    STATUS      current
    DESCRIPTION
        "The value of tmnxMcEpStatsPktsTxPeerConfig indicates how many MC-EP
         control packets were transmitted from this system of type peer config."
    ::= { tmnxMcEpGlobalStats 18 }

tmnxMcEpStatsPktsTxState         OBJECT-TYPE
    SYNTAX      Counter32
    MAX-ACCESS  read-only
    STATUS      current
    DESCRIPTION
        "The value of tmnxMcEpStatsPktsTxState indicates how many MC-EP control
         packets were transmitted from this system of type lag state."
    ::= { tmnxMcEpGlobalStats 19 }

tmnxMcEpStatsPktsTxFailed        OBJECT-TYPE
    SYNTAX      Counter32
    MAX-ACCESS  read-only
    STATUS      current
    DESCRIPTION
        "The value of tmnxMcEpStatsPktsTxFailed indicates how many MC-EP
         control packets failed to be transmitted."
    ::= { tmnxMcEpGlobalStats 20 }

tmnxMcEpStatsDropEpNoPeer        OBJECT-TYPE
    SYNTAX      Counter32
    MAX-ACCESS  read-only
    STATUS      current
    DESCRIPTION
        "The value of tmnxMcEpStatsDropEpNoPeer indicates how many MC-EP
         control packets were dropped on this system because no peer was
         assigned or peer did not match."
    ::= { tmnxMcEpGlobalStats 21 }

tmnxMcWppPeerStatsTableLastCh    OBJECT-TYPE
    SYNTAX      TimeStamp
    MAX-ACCESS  read-only
    STATUS      current
    DESCRIPTION
        "The value of tmnxMcWppPeerStatsTableLastCh indicates the sysUpTime at
         the time of the last change of an entry in the
         tmnxMcWppPeerStatsTable.

         If no changes occurred since the last re-initialization of the local
         network management subsystem, then this object contains a zero value."
    ::= { tmnxMcRedundancyStatsObjs 50 }

tmnxMcWppPeerStatsTable          OBJECT-TYPE
    SYNTAX      SEQUENCE OF TmnxMcWppPeerStatsEntry
    MAX-ACCESS  not-accessible
    STATUS      current
    DESCRIPTION
        "The tmnxMcWppPeerStatsTable shows multi-chassis WPP peer statistics."
    ::= { tmnxMcRedundancyStatsObjs 51 }

tmnxMcWppPeerStatsEntry          OBJECT-TYPE
    SYNTAX      TmnxMcWppPeerStatsEntry
    MAX-ACCESS  not-accessible
    STATUS      current
    DESCRIPTION
        "Each conceptual row represents multi-chassis WPP peer statistics of a
         specific instance.

         Entries in this table are created and destroyed by the system.

         Rows are only created where the statistics value is nonzero; this
         allows faster walking through this table; hence, it is recommended to
         perform only get-next-request operations to retrieve information from
         this table."
    INDEX       {
        tmnxMcPeerIpType,
        tmnxMcPeerIpAddr,
        tmnxMcWppPeerStatsInstance
    }
    ::= { tmnxMcWppPeerStatsTable 1 }

TmnxMcWppPeerStatsEntry          ::= SEQUENCE
{
    tmnxMcWppPeerStatsInstance       Unsigned32,
    tmnxMcWppPeerStatsLastChanged    TimeStamp,
    tmnxMcWppPeerStatsName           DisplayString,
    tmnxMcWppPeerStatsVal            Counter32
}

tmnxMcWppPeerStatsInstance       OBJECT-TYPE
    SYNTAX      Unsigned32 (0..40)
    MAX-ACCESS  not-accessible
    STATUS      current
    DESCRIPTION
        "The value of the object tmnxMcWppPeerStatsInstance indicates the
         instance identifier of the statistics contained in this conceptual
         row."
    ::= { tmnxMcWppPeerStatsEntry 1 }

tmnxMcWppPeerStatsLastChanged    OBJECT-TYPE
    SYNTAX      TimeStamp
    MAX-ACCESS  read-only
    STATUS      current
    DESCRIPTION
        "The value of tmnxMcWppPeerStatsLastChanged indicates the sysUpTime at
         the time of the last change of this entry.

         If no changes occurred since the last re-initialization of the local
         network management subsystem, then this object contains a zero value."
    ::= { tmnxMcWppPeerStatsEntry 2 }

tmnxMcWppPeerStatsName           OBJECT-TYPE
    SYNTAX      DisplayString (SIZE (1..64))
    MAX-ACCESS  read-only
    STATUS      current
    DESCRIPTION
        "The value of the object tmnxMcWppPeerStatsName indicates the
         human-readable identifier of the statistics contained in this
         conceptual row."
    ::= { tmnxMcWppPeerStatsEntry 3 }

tmnxMcWppPeerStatsVal            OBJECT-TYPE
    SYNTAX      Counter32
    MAX-ACCESS  read-only
    STATUS      current
    DESCRIPTION
        "The value of the object tmnxMcWppPeerStatsVal indicates the value of
         the statistics contained in this conceptual row."
    ::= { tmnxMcWppPeerStatsEntry 4 }

tmnxMcRedundancyNotifyObjs       OBJECT IDENTIFIER ::= { tmnxMcRedundancy 3 }

tmnxMcPeerIpAddrTypeForNotify    OBJECT-TYPE
    SYNTAX      InetAddressType
    MAX-ACCESS  accessible-for-notify
    STATUS      current
    DESCRIPTION
        "The value of tmnxMcPeerIpAddrTypeForNotify indicates the address type
         of tmnxMcPeerIpAddrForNotify."
    ::= { tmnxMcRedundancyNotifyObjs 1 }

tmnxMcPeerIpAddrForNotify        OBJECT-TYPE
    SYNTAX      InetAddress
    MAX-ACCESS  accessible-for-notify
    STATUS      current
    DESCRIPTION
        "The value of tmnxMcPeerIpAddrForNotify indicates the address of the
         multi-chassis peer to be used in notifications. Its type is specified
         by tmnxMcPeerIpAddrTypeForNotify."
    ::= { tmnxMcRedundancyNotifyObjs 2 }

tmnxMcPeerSyncClient             OBJECT-TYPE
    SYNTAX      TmnxMcsClientApp
    MAX-ACCESS  accessible-for-notify
    STATUS      current
    DESCRIPTION
        "The value of tmnxMcPeerSyncClient indicates which client has caused
         the generation of tmnxMcSyncClientAlarmRaised or
         tmnxMcSyncClientAlarmCleared."
    ::= { tmnxMcRedundancyNotifyObjs 3 }

tmnxMcRemoteGrpIfNameForNotify   OBJECT-TYPE
    SYNTAX      TNamedItem
    MAX-ACCESS  accessible-for-notify
    STATUS      current
    DESCRIPTION
        "The value of tmnxMcRemoteGrpIfNameForNotify indicates the name of a
         remote group interface."
    ::= { tmnxMcRedundancyNotifyObjs 4 }

tmnxMcRemoteRedIfNameForNotify   OBJECT-TYPE
    SYNTAX      TNamedItem
    MAX-ACCESS  accessible-for-notify
    STATUS      current
    DESCRIPTION
        "The value of tmnxMcRemoteRedIfNameForNotify indicates the name of a
         remote redundant interface."
    ::= { tmnxMcRedundancyNotifyObjs 5 }

tmnxMcRemoteSyncTag              OBJECT-TYPE
    SYNTAX      TNamedItem
    MAX-ACCESS  accessible-for-notify
    STATUS      current
    DESCRIPTION
        "The value of tmnxMcRemoteSyncTag indicates the sync tag of a remote
         object."
    ::= { tmnxMcRedundancyNotifyObjs 6 }

tmnxMcLagConfigLagIds            OBJECT-TYPE
    SYNTAX      OCTET STRING (SIZE (25))
    MAX-ACCESS  accessible-for-notify
    STATUS      current
    DESCRIPTION
        "The value of tmnxMcLagConfigLagIds is a bitmap that indicates a set of
         tmnxMcLagConfigLagId's."
    ::= { tmnxMcRedundancyNotifyObjs 7 }

tmnxMcPeerClockSkew              OBJECT-TYPE
    SYNTAX      Unsigned32 (0..65535)
    UNITS       "seconds"
    MAX-ACCESS  accessible-for-notify
    STATUS      current
    DESCRIPTION
        "The value of tmnxMcPeerClockSkew indicates the difference, in seconds,
         between the MCS peer system clock time and the local system clock."
    ::= { tmnxMcRedundancyNotifyObjs 8 }

tmnxSrrpNotifBfdIntfSvcId        OBJECT-TYPE
    SYNTAX      TmnxServId
    MAX-ACCESS  accessible-for-notify
    STATUS      current
    DESCRIPTION
        "The value of tmnxSrrpNotifBfdIntfSvcId specifies the service ID of the
         interface running BFD in the notification."
    ::= { tmnxMcRedundancyNotifyObjs 9 }

tmnxSrrpNotifBfdIntfIfName       OBJECT-TYPE
    SYNTAX      TNamedItem
    MAX-ACCESS  accessible-for-notify
    STATUS      current
    DESCRIPTION
        "The value of tmnxSrrpNotifBfdIntfIfName specifies the name of the
         interface running BFD in the notification."
    ::= { tmnxMcRedundancyNotifyObjs 10 }

tmnxSrrpNotifBfdIntfDestIpType   OBJECT-TYPE
    SYNTAX      InetAddressType
    MAX-ACCESS  accessible-for-notify
    STATUS      current
    DESCRIPTION
        "The value of tmnxSrrpNotifBfdIntfDestIpType specifies the address type
         of tmnxSrrpNotifBfdIntfDestIp object."
    ::= { tmnxMcRedundancyNotifyObjs 11 }

tmnxSrrpNotifBfdIntfDestIp       OBJECT-TYPE
    SYNTAX      InetAddress (SIZE (0|4|16|20))
    MAX-ACCESS  accessible-for-notify
    STATUS      current
    DESCRIPTION
        "The value of tmnxSrrpNotifBfdIntfDestIp specifies the destination IP
         address on the interface running BFD in the notification."
    ::= { tmnxMcRedundancyNotifyObjs 12 }

tmnxSrrpNotifBfdIntfSessState    OBJECT-TYPE
    SYNTAX      TmnxSrrpAssoBfdIntfSessOperState
    MAX-ACCESS  accessible-for-notify
    STATUS      current
    DESCRIPTION
        "The value of tmnxSrrpNotifBfdIntfSessState indicates the operational
         state of BFD session on the interface in the notification."
    ::= { tmnxMcRedundancyNotifyObjs 13 }

tmnxMcPeerEPBfdSessionOpenStatus OBJECT-TYPE
    SYNTAX      INTEGER {
        ok                   (0),
        invalidSrcAddr       (1),
        nonSysLoopbackIf     (2),
        clientUseSessionFail (3),
        clientAppUseIfFail   (4)
    }
    MAX-ACCESS  accessible-for-notify
    STATUS      current
    DESCRIPTION
        "The value of tmnxMcPeerEPBfdSessionOpenStatus indicates the status of
         multi-chassis endpoint's attempt to open BFD session to the
         multi-chassis endpoint peer."
    ::= { tmnxMcRedundancyNotifyObjs 14 }

tmnxMcPeerEPPsvModeConfigState   OBJECT-TYPE
    SYNTAX      INTEGER {
        mismatch         (1),
        mismatchResolved (2)
    }
    MAX-ACCESS  accessible-for-notify
    STATUS      current
    DESCRIPTION
        "The value of tmnxMcPeerEPPsvModeConfigState indicates the
         configuration state of passive-mode with peer."
    ::= { tmnxMcRedundancyNotifyObjs 15 }

tMcPeerIPsecTnlGrpMasterStateOld OBJECT-TYPE
    SYNTAX      TMcPeerIPsecTnlGrpMasterState
    MAX-ACCESS  accessible-for-notify
    STATUS      current
    DESCRIPTION
        "The value of tMcPeerIPsecTnlGrpMasterStateOld indicates the older
         mastership election state of the tunnel-group from which it
         transitioned to tMcPeerIPsecTnlGrpMasterState."
    ::= { tmnxMcRedundancyNotifyObjs 16 }

tmnxMcNotifyNumber               OBJECT-TYPE
    SYNTAX      Unsigned32
    MAX-ACCESS  accessible-for-notify
    STATUS      current
    DESCRIPTION
        "The value of tmnxMcNotifyNumber indicates an unsigned number.

         Its meaning depends on the context."
    ::= { tmnxMcRedundancyNotifyObjs 17 }

tMcPeerIPsecTnlGrpMasterStateChR OBJECT-TYPE
    SYNTAX      DisplayString
    MAX-ACCESS  accessible-for-notify
    STATUS      current
    DESCRIPTION
        "The value of the object tMcPeerIPsecTnlGrpMasterStateChR indicates the
         reason for the generation of the notification."
    ::= { tmnxMcRedundancyNotifyObjs 18 }

tmnxMcMobRedundancyObjs          OBJECT IDENTIFIER ::= { tmnxMcRedundancy 4 }

tmnxMcPeerMobileTableLstChgd     OBJECT-TYPE
    SYNTAX      TimeStamp
    MAX-ACCESS  read-only
    STATUS      current
    DESCRIPTION
        "The value of tmnxMcPeerMobileTableLstChgd indicates the sysUpTime at
         the time of the last change of an entry in the tmnxMcPeerMobileTable.

         If no changes occurred since the last re-initialization of the local
         network management subsystem, then this object contains a zero value."
    ::= { tmnxMcMobRedundancyObjs 1 }

tmnxMcPeerMobileTable            OBJECT-TYPE
    SYNTAX      SEQUENCE OF TmnxMcPeerMobileEntry
    MAX-ACCESS  not-accessible
    STATUS      current
    DESCRIPTION
        "The tmnxMcPeerMobileTable has an entry for each multi-chassis mobile
         configuration for the indicated peer."
    ::= { tmnxMcMobRedundancyObjs 2 }

tmnxMcPeerMobileEntry            OBJECT-TYPE
    SYNTAX      TmnxMcPeerMobileEntry
    MAX-ACCESS  not-accessible
    STATUS      current
    DESCRIPTION
        "Each row entry represents configuration data for a multi-chassis
         mobile control protocol with the given peer. Entries are
         create/deleted by the user."
    INDEX       {
        tmnxMcPeerIpType,
        tmnxMcPeerIpAddr
    }
    ::= { tmnxMcPeerMobileTable 1 }

TmnxMcPeerMobileEntry            ::= SEQUENCE
{
    tmnxMcPeerMobileRowStatus        RowStatus,
    tmnxMcPeerMobileBFDEnable        TruthValue,
    tmnxMcPeerMobileRouteAdvHoldTmr  Unsigned32,
    tmnxMcPeerMobileHoldOnNbrFail    Unsigned32,
    tmnxMcPeerMobileKeepAlvIntvl     Unsigned32,
    tmnxMcPeerMobileHoldDownTmr      Unsigned32,
    tmnxMcPeerMobileAdminState       TmnxAdminState,
    tmnxMcPeerMobileLastChanged      TimeStamp,
    tmnxMcPeerMobileMtu              Unsigned32
}

tmnxMcPeerMobileRowStatus        OBJECT-TYPE
    SYNTAX      RowStatus
    MAX-ACCESS  read-create
    STATUS      current
    DESCRIPTION
        "The value of tmnxMcPeerMobileRowStatus is used for creation/deletion
         of multi-chassis mobile configuration entries."
    ::= { tmnxMcPeerMobileEntry 1 }

tmnxMcPeerMobileBFDEnable        OBJECT-TYPE
    SYNTAX      TruthValue
    MAX-ACCESS  read-create
    STATUS      current
    DESCRIPTION
        "The value of tmnxMcPeerMobileBFDEnable specifies if the Bi-directional
         Forwarding Detection (BFD) is to be associated with this peer. The
         multi-chassis mobile redundancy protocol will use the BFD state to
         determine the liveliness of its peer."
    DEFVAL      { false }
    ::= { tmnxMcPeerMobileEntry 2 }

tmnxMcPeerMobileRouteAdvHoldTmr  OBJECT-TYPE
    SYNTAX      Unsigned32 (0 | 100..5000)
    UNITS       "milliseconds"
    MAX-ACCESS  read-create
    STATUS      current
    DESCRIPTION
        "The value of tmnxMcPeerMobileRouteAdvHoldTmr specifies the amount of
         time each node would wait before changing the multi-chassis mobile
         state for each tracked interface (e.g. from mobile-slave to
         mobile-master)."
    DEFVAL      { 0 }
    ::= { tmnxMcPeerMobileEntry 3 }

tmnxMcPeerMobileHoldOnNbrFail    OBJECT-TYPE
    SYNTAX      Unsigned32 (2..25)
    MAX-ACCESS  read-create
    STATUS      current
    DESCRIPTION
        "The value of tmnxMcPeerMobileHoldOnNbrFail specifies the number of
         keep alive intervals that may expire before the local node decides
         that the peer has failed."
    DEFVAL      { 3 }
    ::= { tmnxMcPeerMobileEntry 4 }

tmnxMcPeerMobileKeepAlvIntvl     OBJECT-TYPE
    SYNTAX      Unsigned32 (5..500)
    UNITS       "deci-seconds"
    MAX-ACCESS  read-create
    STATUS      current
    DESCRIPTION
        "The value of tmnxMcPeerMobileKeepAlvIntvl specifies the interval at
         which the keep-alive messages are sent to the peer when Bi-directional
         Forwarding Detection (BFD) is not enabled or is down."
    DEFVAL      { 10 }
    ::= { tmnxMcPeerMobileEntry 5 }

tmnxMcPeerMobileHoldDownTmr      OBJECT-TYPE
    SYNTAX      Unsigned32 (0..3600)
    UNITS       "seconds"
    MAX-ACCESS  read-create
    STATUS      current
    DESCRIPTION
        "The value of tmnxMcPeerMobileHoldDownTmr specifies the amount of time
         the node will not announce any routes for loopback interfaces."
    DEFVAL      { 10 }
    ::= { tmnxMcPeerMobileEntry 6 }

tmnxMcPeerMobileAdminState       OBJECT-TYPE
    SYNTAX      TmnxAdminState
    MAX-ACCESS  read-create
    STATUS      current
    DESCRIPTION
        "The value of tmnxMcPeerMobileAdminState specifies the administrative
         status of the mobile redundancy protocol with the multi-chassis peer."
    DEFVAL      { outOfService }
    ::= { tmnxMcPeerMobileEntry 7 }

tmnxMcPeerMobileLastChanged      OBJECT-TYPE
    SYNTAX      TimeStamp
    MAX-ACCESS  read-only
    STATUS      current
    DESCRIPTION
        "The value of tmnxMcPeerMobileLastChanged indicates the sysUpTime at
         the time of the last change of this entry.

         If no changes occurred since the last re-initialization of the local
         network management subsystem, then this object contains a zero value."
    ::= { tmnxMcPeerMobileEntry 8 }

tmnxMcPeerMobileMtu              OBJECT-TYPE
    SYNTAX      Unsigned32 (0 | 512..9212)
    UNITS       "bytes"
    MAX-ACCESS  read-create
    STATUS      current
    DESCRIPTION
        "The value of tmnxMcPeerMobileMtu specifies the Maximum Transmission
         Unit (MTU) of the Internet Protocol (IP) layer between the mobile
         gateways participating in geo-redundancy."
    DEFVAL      { 0 }
    ::= { tmnxMcPeerMobileEntry 9 }

tmnxMcPeerMobileMGTableLstChgd   OBJECT-TYPE
    SYNTAX      TimeStamp
    MAX-ACCESS  read-only
    STATUS      current
    DESCRIPTION
        "The value of tmnxMcPeerMobileMGTableLstChgd indicates the sysUpTime at
         the time of the last change of an entry in the
         tmnxMcPeerMobileMGTable.

         If no changes occurred since the last re-initialization of the local
         network management subsystem, then this object contains a zero value."
    ::= { tmnxMcMobRedundancyObjs 3 }

tmnxMcPeerMobileMGTable          OBJECT-TYPE
    SYNTAX      SEQUENCE OF TmnxMcPeerMobileMGEntry
    MAX-ACCESS  not-accessible
    STATUS      current
    DESCRIPTION
        "The tmnxMcPeerMobileMGTable has entries of mobile-gateways that
         participate in the geo-redundancy."
    ::= { tmnxMcMobRedundancyObjs 4 }

tmnxMcPeerMobileMGEntry          OBJECT-TYPE
    SYNTAX      TmnxMcPeerMobileMGEntry
    MAX-ACCESS  not-accessible
    STATUS      current
    DESCRIPTION
        "Each row entry represents a mobile-gateway which is configured to
         participate in the geo-redundancy. Entries are create/deleted by the
         user."
    INDEX       {
        tmnxMcPeerIpType,
        tmnxMcPeerIpAddr,
        tmnxMcPeerMobileMGId
    }
    ::= { tmnxMcPeerMobileMGTable 1 }

TmnxMcPeerMobileMGEntry          ::= SEQUENCE
{
    tmnxMcPeerMobileMGRowStatus      RowStatus,
    tmnxMcPeerMobileMGId             TmnxMobGwId,
    tmnxMcPeerMobileMGRole           INTEGER,
    tmnxMcPeerMobileMGRefPtTrigger   INTEGER,
    tmnxMcPeerMobileMGAdminState     TmnxAdminState,
    tmnxMcPeerMobileMGLastChanged    TimeStamp
}

tmnxMcPeerMobileMGRowStatus      OBJECT-TYPE
    SYNTAX      RowStatus
    MAX-ACCESS  read-create
    STATUS      current
    DESCRIPTION
        "The value of tmnxMcPeerMobileMGRowStatus is used for creation/deletion
         of multi-chassis peer mobile-gateway entries.

         In order for the row creation to succeed, values for tmnxMcPeerIpType,
         tmnxMcPeerIpAddr, tmnxMcPeerMobileMGId and tmnxMcPeerMobileMGRole must
         be included in the same SNMP SET PDU as tmnxMcPeerMobileRowStatus.
         Otherwise, the SET request will fail with an 'inconsistentValue'
         error."
    ::= { tmnxMcPeerMobileMGEntry 1 }

tmnxMcPeerMobileMGId             OBJECT-TYPE
    SYNTAX      TmnxMobGwId
    MAX-ACCESS  not-accessible
    STATUS      current
    DESCRIPTION
        "The value of tmnxMcPeerMobileMGId specifies the gateway-id of the
         mobile-gateway that will participate in the multi-chassis
         configuration."
    ::= { tmnxMcPeerMobileMGEntry 2 }

tmnxMcPeerMobileMGRole           OBJECT-TYPE
    SYNTAX      INTEGER {
        primary   (1),
        secondary (2)
    }
    MAX-ACCESS  read-create
    STATUS      current
    DESCRIPTION
        "The value of tmnxMcPeerMobileMGRole specifies the role of the
         mobile-gateway that will participate in the multi-chassis
         configuration."
    ::= { tmnxMcPeerMobileMGEntry 3 }

tmnxMcPeerMobileMGRefPtTrigger   OBJECT-TYPE
    SYNTAX      INTEGER {
        all (1),
        any (2)
    }
    MAX-ACCESS  read-create
    STATUS      current
    DESCRIPTION
        "The value of tmnxMcPeerMobileMGRefPtTrigger specifies whether the
         local node to wait for any or all reference points to pass their
         respective packet-count thresholds before performing a redundancy
         action."
    DEFVAL      { any }
    ::= { tmnxMcPeerMobileMGEntry 4 }

tmnxMcPeerMobileMGAdminState     OBJECT-TYPE
    SYNTAX      TmnxAdminState
    MAX-ACCESS  read-create
    STATUS      current
    DESCRIPTION
        "The value of tmnxMcPeerMobileMGAdminState specifies the administrative
         status of the mobile gateway, participating in the mobile redundancy
         protocol, with the multi-chassis peer."
    DEFVAL      { outOfService }
    ::= { tmnxMcPeerMobileMGEntry 5 }

tmnxMcPeerMobileMGLastChanged    OBJECT-TYPE
    SYNTAX      TimeStamp
    MAX-ACCESS  read-only
    STATUS      current
    DESCRIPTION
        "The value of tmnxMcPeerMobileMGLastChanged indicates the sysUpTime at
         the time of the last change of this entry.

         If no changes occurred since the last re-initialization of the local
         network management subsystem, then this object contains a zero value."
    ::= { tmnxMcPeerMobileMGEntry 6 }

tmnxMcPeerMobMGRefPtTableLstChgd OBJECT-TYPE
    SYNTAX      TimeStamp
    MAX-ACCESS  read-only
    STATUS      current
    DESCRIPTION
        "The value of tmnxMcPeerMobMGRefPtTableLstChgd indicates the sysUpTime
         at the time of the last change of an entry in the
         tmnxMcPeerMobileMGRefPtTable.

         If no changes occurred since the last re-initialization of the local
         network management subsystem, then this object contains a zero value."
    ::= { tmnxMcMobRedundancyObjs 5 }

tmnxMcPeerMobileMGRefPtTable     OBJECT-TYPE
    SYNTAX      SEQUENCE OF TmnxMcPeerMobileMGRefPtEntry
    MAX-ACCESS  not-accessible
    STATUS      current
    DESCRIPTION
        "The tmnxMcPeerMobileMGRefPtTable has an entry for each reference point
         of the mobile gateway participating in the geo-redundancy."
    ::= { tmnxMcMobRedundancyObjs 6 }

tmnxMcPeerMobileMGRefPtEntry     OBJECT-TYPE
    SYNTAX      TmnxMcPeerMobileMGRefPtEntry
    MAX-ACCESS  not-accessible
    STATUS      current
    DESCRIPTION
        "Each row entry represents a threshold packet count associated with
         each reference-point of a mobile-gateway, which is configured to
         participate in the geo-redundancy. Entries are create/deleted by the
         user."
    INDEX       {
        tmnxMcPeerIpType,
        tmnxMcPeerIpAddr,
        tmnxMcPeerMobileMGId,
        tmnxMcPeerMobileMGRefPt
    }
    ::= { tmnxMcPeerMobileMGRefPtTable 1 }

TmnxMcPeerMobileMGRefPtEntry     ::= SEQUENCE
{
    tmnxMcPeerMobileMGRefPtRowStatus RowStatus,
    tmnxMcPeerMobileMGRefPt          INTEGER,
    tmnxMcPeerMobileMGRefPtPktCnt    Unsigned32,
    tmnxMcPeerMobileMGRefPtLastChngd TimeStamp
}

tmnxMcPeerMobileMGRefPtRowStatus OBJECT-TYPE
    SYNTAX      RowStatus
    MAX-ACCESS  read-create
    STATUS      current
    DESCRIPTION
        "The value of tmnxMcPeerMobileMGRefPtRowStatus is used for
         creation/deletion of reference point entries for mobile-gateways
         participating in geo-redundancy."
    ::= { tmnxMcPeerMobileMGRefPtEntry 1 }

tmnxMcPeerMobileMGRefPt          OBJECT-TYPE
    SYNTAX      INTEGER {
        s11  (1),
        s1u  (2),
        s5s8 (3)
    }
    MAX-ACCESS  not-accessible
    STATUS      current
    DESCRIPTION
        "The value of tmnxMcPeerMobileMGRefPt specifies the reference-point of
         the mobile-gateway participating in the geo-redundancy for which the
         packet count threshold is configured."
    ::= { tmnxMcPeerMobileMGRefPtEntry 2 }

tmnxMcPeerMobileMGRefPtPktCnt    OBJECT-TYPE
    SYNTAX      Unsigned32 (0..10000)
    MAX-ACCESS  read-create
    STATUS      current
    DESCRIPTION
        "The value of tmnxMcPeerMobileMGRefPtPktCnt specifies the minimum
         number of packets that must be received before the local node performs
         a redundancy action."
    DEFVAL      { 100 }
    ::= { tmnxMcPeerMobileMGRefPtEntry 3 }

tmnxMcPeerMobileMGRefPtLastChngd OBJECT-TYPE
    SYNTAX      TimeStamp
    MAX-ACCESS  read-only
    STATUS      current
    DESCRIPTION
        "The value of tmnxMcPeerMobileMGRefPtLastChngd indicates the sysUpTime
         at the time of the last change of this entry.

         If no changes occurred since the last re-initialization of the local
         network management subsystem, then this object contains a zero value."
    ::= { tmnxMcPeerMobileMGRefPtEntry 4 }

tmnxMcMobRedundancyStatsObjs     OBJECT IDENTIFIER ::= { tmnxMcRedundancy 5 }

tmnxMcMobRedundancyNotifyObjs    OBJECT IDENTIFIER ::= { tmnxMcRedundancy 6 }

tmnxMcRedundancyConformance      OBJECT IDENTIFIER ::= { tmnxSRConfs 40 }

tmnxMcRedundancyCompliances      OBJECT IDENTIFIER ::= { tmnxMcRedundancyConformance 1 }

tmnxMcRedundancy7750V5v0Compliance MODULE-COMPLIANCE
    STATUS      obsolete
    DESCRIPTION
        "The compliance statement for management of multi-chassis redundancy on
         version 5.0 of the Nokia SROS series systems."
    MODULE
        MANDATORY-GROUPS {
            tmnxMcRedundancyV5v0Group,
            tmnxSrrpV5v0Group,
            tmnxMcRedundancyV5v0NotifGroup
        }
    ::= { tmnxMcRedundancyCompliances 1 }

tmnxMcRedundancy7450V5v0Compliance MODULE-COMPLIANCE
    STATUS      obsolete
    DESCRIPTION
        "The compliance statement for management of multi-chassis redundancy on
         version 5.0 of the Nokia 7450 series systems."
    MODULE
        MANDATORY-GROUPS {
            tmnxMcRedundancyV5v0Group,
            tmnxMcRedundancyV5v0NotifGroup
        }
    ::= { tmnxMcRedundancyCompliances 2 }

tmnxMcRedundancy7710V5v0Compliance MODULE-COMPLIANCE
    STATUS      obsolete
    DESCRIPTION
        "The compliance statement for management of multi-chassis redundancy on
         version 5.0 of the Nokia 7710 series systems."
    MODULE
        MANDATORY-GROUPS {
            tmnxMcRedundancyV5v0Group,
            tmnxSrrpV5v0Group,
            tmnxMcRedundancyV5v0NotifGroup
        }
    ::= { tmnxMcRedundancyCompliances 3 }

tmnxMcRedundancy7750V6v0Compliance MODULE-COMPLIANCE
    STATUS      obsolete
    DESCRIPTION
        "The compliance statement for management of multi-chassis redundancy on
         version 6.0 of the Nokia SROS series systems."
    MODULE
        MANDATORY-GROUPS {
            tmnxMcRedundancyV6v0Group,
            tmnxSrrpV5v0Group,
            tmnxMcRedundancySrrpNotifGroup,
            tmnxMcRingV6v0Group,
            tmnxMcPeerSyncGroup,
            tmnxMcRedundancyV5v0NotifGroup,
            tmnxMcRingV6v0NotifGroup,
            tmnxMcsDhcpsV6v0Group
        }
    ::= { tmnxMcRedundancyCompliances 4 }

tmnxMcRedundancy7450V6v0Compliance MODULE-COMPLIANCE
    STATUS      obsolete
    DESCRIPTION
        "The compliance statement for management of multi-chassis redundancy on
         version 6.0 of the Nokia 7450 series systems."
    MODULE
        MANDATORY-GROUPS {
            tmnxMcRedundancyV6v0Group,
            tmnxMcRingV6v0Group,
            tmnxMcPeerSyncGroup,
            tmnxMcRedundancyV5v0NotifGroup,
            tmnxMcRingV6v0NotifGroup
        }
    ::= { tmnxMcRedundancyCompliances 5 }

tmnxMcRedundancy7710V6v0Compliance MODULE-COMPLIANCE
    STATUS      obsolete
    DESCRIPTION
        "The compliance statement for management of multi-chassis redundancy on
         version 6.0 of the Nokia 7710 series systems."
    MODULE
        MANDATORY-GROUPS {
            tmnxMcRedundancyV6v0Group,
            tmnxSrrpV5v0Group,
            tmnxMcRedundancySrrpNotifGroup,
            tmnxMcRingV6v0Group,
            tmnxMcPeerSyncGroup,
            tmnxMcRedundancyV5v0NotifGroup,
            tmnxMcRingV6v0NotifGroup,
            tmnxMcsDhcpsV6v0Group
        }
    ::= { tmnxMcRedundancyCompliances 6 }

tmnxMcRedundancy7750V6v1Compliance MODULE-COMPLIANCE
    STATUS      obsolete
    DESCRIPTION
        "The compliance statement for management of multi-chassis redundancy on
         version 6.1 of the Nokia SROS series systems."
    MODULE
        MANDATORY-GROUPS {
            tmnxMcRedundancyV6v0Group,
            tmnxSrrpV5v0Group,
            tmnxSrrpV6v1Group,
            tmnxMcRedundancySrrpNotifGroup,
            tmnxSrrpNotifV6v1Group,
            tmnxMcRingV6v0Group,
            tmnxMcPeerSyncGroup,
            tmnxMcRedundancyV5v0NotifGroup,
            tmnxMcRingV6v0NotifGroup,
            tmnxMcsDhcpsV6v0Group
        }
    ::= { tmnxMcRedundancyCompliances 7 }

tmnxMcRedundancy7710V6v1Compliance MODULE-COMPLIANCE
    STATUS      obsolete
    DESCRIPTION
        "The compliance statement for management of multi-chassis redundancy on
         version 6.1 of the Nokia 7710 series systems."
    MODULE
        MANDATORY-GROUPS {
            tmnxMcRedundancyV6v0Group,
            tmnxSrrpV5v0Group,
            tmnxSrrpV6v1Group,
            tmnxMcRedundancySrrpNotifGroup,
            tmnxMcRingV6v0Group,
            tmnxMcPeerSyncGroup,
            tmnxMcRedundancyV5v0NotifGroup,
            tmnxMcRingV6v0NotifGroup,
            tmnxMcsDhcpsV6v0Group
        }
    ::= { tmnxMcRedundancyCompliances 8 }

tmnxMcRedundancy7450V7v0Compliance MODULE-COMPLIANCE
    STATUS      obsolete
    DESCRIPTION
        "The compliance statement for management of multi-chassis redundancy on
         version 7.0 of the Nokia 7450 series systems."
    MODULE
        MANDATORY-GROUPS {
            tmnxMcRedundancyV6v0Group,
            tmnxMcRingV6v0Group,
            tmnxMcPeerSyncGroup,
            tmnxMcRedundancyV5v0NotifGroup,
            tmnxMcRingV6v0NotifGroup,
            tmnxMcL3RingGroup,
            tmnxMcPeerEPGroup,
            tmnxMcPeerEPNotifyObjsV7v0Group,
            tmnxMcPeerEPV7v0NotifGroup,
            tmnxMcsSubHostTrkGroup,
            tmnxMcLagPbbGroup
        }
    ::= { tmnxMcRedundancyCompliances 9 }

tmnxMcRedundancy7750V7v0Compliance MODULE-COMPLIANCE
    STATUS      obsolete
    DESCRIPTION
        "The compliance statement for management of multi-chassis redundancy on
         version 7.0 of the Nokia SROS series systems."
    MODULE
        MANDATORY-GROUPS {
            tmnxMcRedundancyV6v0Group,
            tmnxSrrpV5v0Group,
            tmnxSrrpV6v1Group,
            tmnxMcRedundancySrrpNotifGroup,
            tmnxSrrpNotifV6v1Group,
            tmnxMcRingV6v0Group,
            tmnxMcPeerSyncGroup,
            tmnxMcRedundancyV5v0NotifGroup,
            tmnxMcRingV6v0NotifGroup,
            tmnxMcsDhcpsV6v0Group,
            tmnxMcL3RingGroup,
            tmnxMcPeerEPGroup,
            tmnxMcPeerEPNotifyObjsV7v0Group,
            tmnxMcPeerEPV7v0NotifGroup,
            tmnxMcsSubHostTrkGroup,
            tmnxMcLagPbbGroup
        }
    ::= { tmnxMcRedundancyCompliances 10 }

tmnxMcRedundancy7710V7v0Compliance MODULE-COMPLIANCE
    STATUS      obsolete
    DESCRIPTION
        "The compliance statement for management of multi-chassis redundancy on
         version 7.0 of the Nokia 7710 series systems."
    MODULE
        MANDATORY-GROUPS {
            tmnxMcRedundancyV6v0Group,
            tmnxSrrpV5v0Group,
            tmnxSrrpV6v1Group,
            tmnxMcRedundancySrrpNotifGroup,
            tmnxMcRingV6v0Group,
            tmnxMcPeerSyncGroup,
            tmnxMcRedundancyV5v0NotifGroup,
            tmnxMcRingV6v0NotifGroup,
            tmnxMcsDhcpsV6v0Group,
            tmnxMcL3RingGroup,
            tmnxMcPeerEPGroup,
            tmnxMcPeerEPNotifyObjsV7v0Group,
            tmnxMcPeerEPV7v0NotifGroup,
            tmnxMcsSubHostTrkGroup,
            tmnxMcLagPbbGroup
        }
    ::= { tmnxMcRedundancyCompliances 11 }

tmnxMcRedundancy7450V8v0Compliance MODULE-COMPLIANCE
    STATUS      obsolete
    DESCRIPTION
        "The compliance statement for management of multi-chassis redundancy on
         version 8.0 of the Nokia 7450 series systems."
    MODULE
        MANDATORY-GROUPS {
            tmnxMcRedundancyV6v0Group,
            tmnxMcRingV6v0Group,
            tmnxMcPeerSyncGroup,
            tmnxMcRedundancyV5v0NotifGroup,
            tmnxMcRingV6v0NotifGroup,
            tmnxMcL3RingGroup,
            tmnxMcPeerEPGroup,
            tmnxMcPeerEPNotifyObjsV7v0Group,
            tmnxMcPeerEPV7v0NotifGroup,
            tmnxMcsSubHostTrkGroup,
            tmnxMcLagPbbGroup,
            tmnxMcRedBgpMultiHomeGroup
        }
    ::= { tmnxMcRedundancyCompliances 12 }

tmnxMcRedundancy7750V8v0Compliance MODULE-COMPLIANCE
    STATUS      obsolete
    DESCRIPTION
        "The compliance statement for management of multi-chassis redundancy on
         version 8.0 of the Nokia SROS series systems."
    MODULE
        MANDATORY-GROUPS {
            tmnxMcRedundancyV6v0Group,
            tmnxSrrpV5v0Group,
            tmnxSrrpV6v1Group,
            tmnxMcRedundancySrrpNotifGroup,
            tmnxSrrpNotifV6v1Group,
            tmnxMcRingV6v0Group,
            tmnxMcPeerSyncGroup,
            tmnxMcRedundancyV5v0NotifGroup,
            tmnxMcRingV6v0NotifGroup,
            tmnxMcsDhcpsV6v0Group,
            tmnxMcL3RingGroup,
            tmnxMcPeerEPGroup,
            tmnxMcPeerEPNotifyObjsV7v0Group,
            tmnxMcPeerEPV7v0NotifGroup,
            tmnxMcsSubHostTrkGroup,
            tmnxMcLagPbbGroup,
            tmnxMcRedBgpMultiHomeGroup,
            tmnxSrrpV8v0Group,
            tmnxMcTlsSapGroup
        }
    ::= { tmnxMcRedundancyCompliances 13 }

tmnxMcRedundancy7710V8v0Compliance MODULE-COMPLIANCE
    STATUS      obsolete
    DESCRIPTION
        "The compliance statement for management of multi-chassis redundancy on
         version 7.0 of the Nokia 7710 series systems."
    MODULE
        MANDATORY-GROUPS {
            tmnxMcRedundancyV6v0Group,
            tmnxSrrpV5v0Group,
            tmnxSrrpV6v1Group,
            tmnxMcRedundancySrrpNotifGroup,
            tmnxMcRingV6v0Group,
            tmnxMcPeerSyncGroup,
            tmnxMcRedundancyV5v0NotifGroup,
            tmnxMcRingV6v0NotifGroup,
            tmnxMcsDhcpsV6v0Group,
            tmnxMcL3RingGroup,
            tmnxMcPeerEPGroup,
            tmnxMcPeerEPNotifyObjsV7v0Group,
            tmnxMcPeerEPV7v0NotifGroup,
            tmnxMcsSubHostTrkGroup,
            tmnxMcLagPbbGroup,
            tmnxMcRedBgpMultiHomeGroup,
            tmnxMcTlsSapGroup
        }
    ::= { tmnxMcRedundancyCompliances 14 }

tmnxMcRedundancy7450V9v0Compliance MODULE-COMPLIANCE
    STATUS      obsolete
    DESCRIPTION
        "The compliance statement for management of multi-chassis redundancy on
         version 9.0 of the Nokia 7450 series systems."
    MODULE
        MANDATORY-GROUPS {
            tmnxMcRedundancyV9v0Group,
            tmnxMcRingV6v0Group,
            tmnxMcPeerSyncGroup,
            tmnxMcRedundancyV5v0NotifGroup,
            tmnxMcRingV6v0NotifGroup,
            tmnxMcL3RingGroup,
            tmnxMcPeerEPGroup,
            tmnxMcPeerEPNotifyObjsV7v0Group,
            tmnxMcPeerEPV7v0NotifGroup,
            tmnxMcsSubHostTrkGroup,
            tmnxMcLagPbbGroup,
            tmnxSrrpV9v0Group,
            tmnxMcRedBgpMultiHomeGroup
        }
    ::= { tmnxMcRedundancyCompliances 15 }

tmnxMcRedundancy7750V9v0Compliance MODULE-COMPLIANCE
    STATUS      obsolete
    DESCRIPTION
        "The compliance statement for management of multi-chassis redundancy on
         version 9.0 of the Nokia SROS series systems."
    MODULE
        MANDATORY-GROUPS {
            tmnxMcRedundancyV9v0Group,
            tmnxSrrpV5v0Group,
            tmnxSrrpV6v1Group,
            tmnxMcRedundancySrrpNotifGroup,
            tmnxSrrpNotifV6v1Group,
            tmnxMcRingV6v0Group,
            tmnxMcPeerSyncGroup,
            tmnxMcRedundancyV5v0NotifGroup,
            tmnxMcRingV6v0NotifGroup,
            tmnxMcsDhcpsV6v0Group,
            tmnxMcL3RingGroup,
            tmnxMcPeerEPGroup,
            tmnxMcPeerEPNotifyObjsV7v0Group,
            tmnxMcPeerEPV7v0NotifGroup,
            tmnxMcsSubHostTrkGroup,
            tmnxMcLagPbbGroup,
            tmnxMcRedBgpMultiHomeGroup,
            tmnxSrrpV8v0Group,
            tmnxSrrpV9v0Group,
            tmnxMcTlsSapGroup
        }
    ::= { tmnxMcRedundancyCompliances 16 }

tmnxMcRedundancy7710V9v0Compliance MODULE-COMPLIANCE
    STATUS      obsolete
    DESCRIPTION
        "The compliance statement for management of multi-chassis redundancy on
         version 7.0 of the Nokia 7710 series systems."
    MODULE
        MANDATORY-GROUPS {
            tmnxMcRedundancyV9v0Group,
            tmnxSrrpV5v0Group,
            tmnxSrrpV6v1Group,
            tmnxMcRedundancySrrpNotifGroup,
            tmnxMcRingV6v0Group,
            tmnxMcPeerSyncGroup,
            tmnxMcRedundancyV5v0NotifGroup,
            tmnxMcRingV6v0NotifGroup,
            tmnxMcsDhcpsV6v0Group,
            tmnxMcL3RingGroup,
            tmnxMcPeerEPGroup,
            tmnxMcPeerEPNotifyObjsV7v0Group,
            tmnxMcPeerEPV7v0NotifGroup,
            tmnxMcsSubHostTrkGroup,
            tmnxMcLagPbbGroup,
            tmnxMcRedBgpMultiHomeGroup,
            tmnxMcTlsSapGroup
        }
    ::= { tmnxMcRedundancyCompliances 17 }

tmnxMcRed7450V10v0Compliance     MODULE-COMPLIANCE
    STATUS      obsolete
    DESCRIPTION
        "The compliance statement for management of multi-chassis redundancy on
         version 9.0 of the Nokia 7450 series systems."
    MODULE
        MANDATORY-GROUPS {
            tmnxMcRedundancyV9v0Group,
            tmnxMcRingV6v0Group,
            tmnxMcPeerSyncGroup,
            tmnxMcRedundancyV5v0NotifGroup,
            tmnxMcRingV6v0NotifGroup,
            tmnxMcL3RingGroup,
            tmnxMcPeerEPGroup,
            tmnxMcPeerEPNotifyObjsV7v0Group,
            tmnxMcPeerEPV7v0NotifGroup,
            tmnxMcsSubHostTrkGroup,
            tmnxMcLagPbbGroup,
            tmnxSrrpV9v0Group,
            tmnxMcPeerNotifyObjsV10v0Group,
            tmnxMcPeerV10v0NotifGroup,
            tmnxMcPeerIPsecTnlGrpV10v0Group,
            tmnxMcRedBgpMultiHomeGroup
        }
    ::= { tmnxMcRedundancyCompliances 18 }

tmnxMcRed7750V10v0Compliance     MODULE-COMPLIANCE
    STATUS      obsolete
    DESCRIPTION
        "The compliance statement for management of multi-chassis redundancy on
         version 9.0 of the Nokia SROS series systems."
    MODULE
        MANDATORY-GROUPS {
            tmnxMcRedundancyV9v0Group,
            tmnxMcRedundancyV10v0Group,
            tmnxSrrpV5v0Group,
            tmnxSrrpV6v1Group,
            tmnxMcRedundancySrrpNotifGroup,
            tmnxSrrpNotifV6v1Group,
            tmnxMcRingV6v0Group,
            tmnxMcPeerSyncGroup,
            tmnxMcRedundancyV5v0NotifGroup,
            tmnxMcRingV6v0NotifGroup,
            tmnxMcsDhcpsV6v0Group,
            tmnxMcL3RingGroup,
            tmnxMcPeerEPGroup,
            tmnxMcPeerEPNotifyObjsV7v0Group,
            tmnxMcPeerEPV7v0NotifGroup,
            tmnxMcsSubHostTrkGroup,
            tmnxMcLagPbbGroup,
            tmnxMcRedBgpMultiHomeGroup,
            tmnxSrrpV8v0Group,
            tmnxSrrpV9v0Group,
            tmnxMcTlsSapGroup,
            tmnxMcPeerNotifyObjsV10v0Group,
            tmnxMcPeerV10v0NotifGroup,
            tmnxMcPeerIPsecTnlGrpV10v0Group,
            tmnxMcMobRedundancyV4v0Group
        }
    ::= { tmnxMcRedundancyCompliances 19 }

tmnxMcRed7710V10v0Compliance     MODULE-COMPLIANCE
    STATUS      obsolete
    DESCRIPTION
        "The compliance statement for management of multi-chassis redundancy on
         version 7.0 of the Nokia 7710 series systems."
    MODULE
        MANDATORY-GROUPS {
            tmnxMcRedundancyV9v0Group,
            tmnxMcRedundancyV10v0Group,
            tmnxSrrpV5v0Group,
            tmnxSrrpV6v1Group,
            tmnxMcRedundancySrrpNotifGroup,
            tmnxMcRingV6v0Group,
            tmnxMcPeerSyncGroup,
            tmnxMcRedundancyV5v0NotifGroup,
            tmnxMcRingV6v0NotifGroup,
            tmnxMcsDhcpsV6v0Group,
            tmnxMcL3RingGroup,
            tmnxMcPeerEPGroup,
            tmnxMcPeerEPNotifyObjsV7v0Group,
            tmnxMcPeerEPV7v0NotifGroup,
            tmnxMcsSubHostTrkGroup,
            tmnxMcLagPbbGroup,
            tmnxMcRedBgpMultiHomeGroup,
            tmnxMcPeerNotifyObjsV10v0Group,
            tmnxMcPeerV10v0NotifGroup,
            tmnxMcPeerIPsecTnlGrpV10v0Group,
            tmnxMcTlsSapGroup
        }
    ::= { tmnxMcRedundancyCompliances 20 }

tmnxMcRed7450V11v0Compliance     MODULE-COMPLIANCE
    STATUS      obsolete
    DESCRIPTION
        "The compliance statement for management of multi-chassis redundancy on
         version 11.0 of the Nokia 7450 series systems."
    MODULE
        MANDATORY-GROUPS {
            tmnxMcRedundancyV9v0Group,
            tmnxMcRingV6v0Group,
            tmnxMcPeerSyncGroup,
            tmnxMcRedundancyV5v0NotifGroup,
            tmnxMcRingV6v0NotifGroup,
            tmnxMcL3RingGroup,
            tmnxMcPeerEPGroup,
            tmnxMcPeerEPNotifyObjsV7v0Group,
            tmnxMcPeerEPV7v0NotifGroup,
            tmnxMcsSubHostTrkGroup,
            tmnxMcLagPbbGroup,
            tmnxSrrpV9v0Group,
            tmnxMcPeerNotifyObjsV10v0Group,
            tmnxMcPeerV10v0NotifGroup,
            tmnxMcPeerIPsecTnlGrpV10v0Group,
            tmnxMcRedBgpMultiHomeGroup
        }
    ::= { tmnxMcRedundancyCompliances 21 }

tmnxMcRed7750V11v0Compliance     MODULE-COMPLIANCE
    STATUS      obsolete
    DESCRIPTION
        "The compliance statement for management of multi-chassis redundancy on
         version 11.0 of the Nokia SROS series systems."
    MODULE
        MANDATORY-GROUPS {
            tmnxMcRedundancyV9v0Group,
            tmnxMcRedundancyV10v0Group,
            tmnxSrrpV5v0Group,
            tmnxSrrpV6v1Group,
            tmnxMcRedundancySrrpNotifGroup,
            tmnxSrrpNotifV6v1Group,
            tmnxMcRingV6v0Group,
            tmnxMcPeerSyncGroup,
            tmnxMcRedundancyV5v0NotifGroup,
            tmnxMcRingV6v0NotifGroup,
            tmnxMcsDhcpsV6v0Group,
            tmnxMcsDhcpsV11v0Group,
            tmnxMcL3RingGroup,
            tmnxMcPeerEPGroup,
            tmnxMcPeerEPNotifyObjsV7v0Group,
            tmnxMcPeerEPV7v0NotifGroup,
            tmnxMcsSubHostTrkGroup,
            tmnxMcLagPbbGroup,
            tmnxMcRedBgpMultiHomeGroup,
            tmnxSrrpV8v0Group,
            tmnxSrrpV9v0Group,
            tmnxMcTlsSapGroup,
            tmnxMcPeerNotifyObjsV10v0Group,
            tmnxMcPeerV10v0NotifGroup,
            tmnxMcPeerIPsecTnlGrpV10v0Group,
            tmnxMcMobRedundancyV4v0Group
        }
    ::= { tmnxMcRedundancyCompliances 22 }

tmnxMcRed7710V11v0Compliance     MODULE-COMPLIANCE
    STATUS      obsolete
    DESCRIPTION
        "The compliance statement for management of multi-chassis redundancy on
         version 11.0 of the Nokia 7710 series systems."
    MODULE
        MANDATORY-GROUPS {
            tmnxMcRedundancyV9v0Group,
            tmnxMcRedundancyV10v0Group,
            tmnxSrrpV5v0Group,
            tmnxSrrpV6v1Group,
            tmnxMcRedundancySrrpNotifGroup,
            tmnxMcRingV6v0Group,
            tmnxMcPeerSyncGroup,
            tmnxMcRedundancyV5v0NotifGroup,
            tmnxMcRingV6v0NotifGroup,
            tmnxMcsDhcpsV6v0Group,
            tmnxMcsDhcpsV11v0Group,
            tmnxMcL3RingGroup,
            tmnxMcPeerEPGroup,
            tmnxMcPeerEPNotifyObjsV7v0Group,
            tmnxMcPeerEPV7v0NotifGroup,
            tmnxMcsSubHostTrkGroup,
            tmnxMcLagPbbGroup,
            tmnxMcRedBgpMultiHomeGroup,
            tmnxMcPeerNotifyObjsV10v0Group,
            tmnxMcPeerV10v0NotifGroup,
            tmnxMcPeerIPsecTnlGrpV10v0Group,
            tmnxMcTlsSapGroup
        }
    ::= { tmnxMcRedundancyCompliances 23 }

tmnxMcRedV12v0Compliance         MODULE-COMPLIANCE
    STATUS      obsolete
    DESCRIPTION
        "The compliance statement for management of multi-chassis redundancy on
         version 12.0 of the Nokia SROS series systems."
    MODULE
        MANDATORY-GROUPS {
            tmnxMcRedundancyV9v0Group,
            tmnxMcRedundancyV10v0Group,
            tmnxMcRedundancyV12v0Group,
            tmnxSrrpV5v0Group,
            tmnxSrrpV6v1Group,
            tmnxMcRedundancySrrpNotifGroup,
            tmnxSrrpNotifV6v1Group,
            tmnxMcRingV6v0Group,
            tmnxMcPeerSyncGroup,
            tmnxMcRedundancyV5v0NotifGroup,
            tmnxMcRingV6v0NotifGroup,
            tmnxMcsDhcpsV6v0Group,
            tmnxMcsDhcpsV11v0Group,
            tmnxMcL3RingGroup,
            tmnxMcPeerEPGroup,
            tmnxMcPeerEPNotifyObjsV7v0Group,
            tmnxMcPeerEPV7v0NotifGroup,
            tmnxMcsSubHostTrkGroup,
            tmnxMcLagPbbGroup,
            tmnxMcRedBgpMultiHomeGroup,
            tmnxSrrpV8v0Group,
            tmnxSrrpV9v0Group,
            tmnxMcTlsSapGroup,
            tmnxMcPeerNotifyObjsV10v0Group,
            tmnxMcPeerV10v0NotifGroup,
            tmnxMcPeerIPsecTnlGrpV10v0Group,
            tmnxMcMobRedundancyV4v0Group,
            tmnxMcWarmStandbyGroup,
            tmnxMcOmcrNotifGroup,
            tmnxSrrpV10v0Group,
            tmnxSrrpNotificationV10v0Group
        }
    ::= { tmnxMcRedundancyCompliances 24 }

tmnxMcRedV13v0Compliance         MODULE-COMPLIANCE
    STATUS      obsolete
    DESCRIPTION
        "The compliance statement for management of multi-chassis redundancy on
         version 13.0 of the Nokia SROS series systems."
    MODULE
        MANDATORY-GROUPS {
            tmnxMcRedundancyV9v0Group,
            tmnxMcRedundancyV10v0Group,
            tmnxMcRedundancyV12v0Group,
            tmnxMcRedundancyV13v0Group,
            tmnxSrrpV5v0Group,
            tmnxSrrpV6v1Group,
            tmnxMcRedundancySrrpNotifGroup,
            tmnxSrrpNotifV6v1Group,
            tmnxMcRingV6v0Group,
            tmnxMcPeerSyncGroup,
            tmnxMcRedundancyV5v0NotifGroup,
            tmnxMcRingV6v0NotifGroup,
            tmnxMcsDhcpsV6v0Group,
            tmnxMcsDhcpsV11v0Group,
            tmnxMcL3RingGroup,
            tmnxMcPeerEPGroup,
            tmnxMcPeerEPNotifyObjsV7v0Group,
            tmnxMcPeerEPV7v0NotifGroup,
            tmnxMcsSubHostTrkGroup,
            tmnxMcLagPbbGroup,
            tmnxMcRedBgpMultiHomeGroup,
            tmnxSrrpV8v0Group,
            tmnxSrrpV9v0Group,
            tmnxMcTlsSapGroup,
            tmnxMcPeerNotifyObjsV10v0Group,
            tmnxMcPeerV10v0NotifGroup,
            tmnxMcPeerIPsecTnlGrpV10v0Group,
            tmnxMcMobRedundancyV4v0Group,
            tmnxMcWarmStandbyGroup,
            tmnxMcOmcrNotifGroup,
            tmnxSrrpV10v0Group,
            tmnxSrrpNotificationV10v0Group,
            tmnxMcRedBgpEvpnGroup,
            tmnxMcRedBgpMHSiteGroup
        }
    ::= { tmnxMcRedundancyCompliances 25 }

tmnxMcRedV14v0Compliance         MODULE-COMPLIANCE
    STATUS      current
    DESCRIPTION
        "The compliance statement for management of multi-chassis redundancy on
         version 14.0 of the Nokia SROS series systems."
    MODULE
        MANDATORY-GROUPS {
            tmnxMcRedundancyV9v0Group,
            tmnxMcRedundancyV10v0Group,
            tmnxMcRedundancyV12v0Group,
            tmnxMcRedundancyV13v0Group,
            tmnxMcRedundancyV14v0Group,
            tmnxSrrpV5v0Group,
            tmnxSrrpV6v1Group,
            tmnxMcRedundancySrrpNotifGroup,
            tmnxSrrpNotifV6v1Group,
            tmnxMcRingV6v0Group,
            tmnxMcPeerSyncGroup,
            tmnxMcRedundancyV5v0NotifGroup,
            tmnxMcRingV6v0NotifGroup,
            tmnxMcsDhcpsV6v0Group,
            tmnxMcsDhcpsV11v0Group,
            tmnxMcL3RingGroup,
            tmnxMcPeerEPGroup,
            tmnxMcPeerEPNotifyObjsV7v0Group,
            tmnxMcPeerEPV7v0NotifGroup,
            tmnxMcsSubHostTrkGroup,
            tmnxMcLagPbbGroup,
            tmnxMcRedBgpMultiHomeGroup,
            tmnxSrrpV8v0Group,
            tmnxSrrpV9v0Group,
            tmnxMcTlsSapGroup,
            tmnxMcPeerNotifyObjsV10v0Group,
            tmnxMcPeerV10v0NotifGroup,
            tmnxMcPeerIPsecTnlGrpV10v0Group,
            tmnxMcMobRedundancyV4v0Group,
            tmnxMcWarmStandbyGroup,
            tmnxMcOmcrNotifGroup,
            tmnxSrrpV10v0Group,
            tmnxSrrpNotificationV10v0Group,
            tmnxMcRedBgpEvpnGroup,
            tmnxMcRedBgpMHSiteGroup
        }
    ::= { tmnxMcRedundancyCompliances 26 }

tmnxMcRedundancyGroups           OBJECT IDENTIFIER ::= { tmnxMcRedundancyConformance 2 }

tmnxMcRedundancyV5v0Group        OBJECT-GROUP
    OBJECTS     {
        tmnxMcPeerRowStatus,
        tmnxMcPeerDescription,
        tmnxMcPeerAuthKey,
        tmnxMcPeerSrcIpType,
        tmnxMcPeerSrcIpAddr,
        tmnxMcPeerAdminState,
        tmnxMcPeerSrcIpOperType,
        tmnxMcPeerSrcIpOperAddr,
        tmnxMcPeerRingsOperState,
        tmnxMcPeerSyncRowStatus,
        tmnxMcPeerSyncIgmp,
        tmnxMcPeerSyncIgmpSnooping,
        tmnxMcPeerSyncSubMgmt,
        tmnxMcPeerSyncSrrp,
        tmnxMcPeerSyncAdminState,
        tmnxMcPeerSyncOperState,
        tmnxMcPeerSyncOperFlags,
        tmnxMcPeerSyncStatus,
        tmnxMcPeerSyncLastSyncTime,
        tmnxMcPeerSyncNumEntries,
        tmnxMcPeerSyncLclDeletedEntries,
        tmnxMcPeerSyncAlarmedEntries,
        tmnxMcPeerSyncRemNumEntries,
        tmnxMcPeerSyncRemLclDelEntries,
        tmnxMcPeerSyncRemAlarmedEntries,
        tmnxMcPeerSyncPktsTxAll,
        tmnxMcPeerSyncPktsTxHello,
        tmnxMcPeerSyncPktsTxData,
        tmnxMcPeerSyncPktsTxOther,
        tmnxMcPeerSyncPktsTxErr,
        tmnxMcPeerSyncPktsRxAll,
        tmnxMcPeerSyncPktsRxHello,
        tmnxMcPeerSyncPktsRxData,
        tmnxMcPeerSyncPktsRxOther,
        tmnxMcPeerSyncPktsRxErr,
        tmnxMcPeerSyncPktsRxErrHeader,
        tmnxMcPeerSyncPktsRxErrBody,
        tmnxMcPeerSyncPktsRxErrSeqNum,
        tmnxMcPeerSyncPortRowStatus,
        tmnxMcPeerSyncPortSyncTag,
        tmnxMcPeerSyncPortEncapRowStatus,
        tmnxMcPeerSyncPortEncapSyncTag,
        tmnxMcPeerIpAddrForNotify,
        tmnxMcPeerSyncClient,
        tmnxMcsClientNumEntries,
        tmnxMcsClientLclDeletedEntries,
        tmnxMcsClientAlarmedEntries,
        tmnxMcsClientRemNumEntries,
        tmnxMcsClientRemLclDelEntries,
        tmnxMcsClientRemAlarmedEntries,
        tmnxMcLagConfigTableLastChanged,
        tmnxMcLagConfigPeerLastChanged,
        tmnxMcLagConfigPeerAdminstate,
        tmnxMcLagConfigKeepALiveIvl,
        tmnxMcLagConfigHoldOnNgbrFailure,
        tmnxMcLagConfigOperState,
        tmnxMcLagConfigLagTableLastChanged,
        tmnxMcLagConfigLagLastChanged,
        tmnxMcLagConfigLagRowStatus,
        tmnxMcLagConfigLaglacpKey,
        tmnxMcLagConfigLagSystemId,
        tmnxMcLagConfigLagSystemPriority,
        tmnxMcLagConfigLagRemoteLagId,
        tmnxMcLagActiveStandby,
        tmnxMcLagLacpIdInUse,
        tmnxMcLagExtendedTimeOut,
        tmnxMcLagSelectionLogic,
        tmnxMcLagConfigMismatchString,
        tmnxMcLagConfigMismatchFlags,
        tmnxMcLagConfigLagIds,
        tmnxMcLagStatsPktsRx,
        tmnxMcLagStatsPktsRxKeepalive,
        tmnxMcLagStatsPktsRxConfig,
        tmnxMcLagStatsPktsRxPeerConfig,
        tmnxMcLagStatsPktsRxState,
        tmnxMcLagStatsDropPktKpaliveTask,
        tmnxMcLagStatsDropPktTooShort,
        tmnxMcLagStatsDropPktVerifyFaild,
        tmnxMcLagStatsDropTlvInvalidSize,
        tmnxMcLagStatsDropOutOfSeq,
        tmnxMcLagStatsDropUnknownTlv,
        tmnxMcLagStatsDropTlvInvldLagId,
        tmnxMcLagStatsDropMD5,
        tmnxMcLagStatsDropUnknownPeer,
        tmnxMcLagStatsPktsTx,
        tmnxMcLagStatsPktsTxKeepalive,
        tmnxMcLagStatsPktsTxConfig,
        tmnxMcLagStatsPktsTxPeerConfig,
        tmnxMcLagStatsPktsTxState,
        tmnxMcLagStatsPktsTxFailed,
        tmnxMcLagPeerStatsPktsRx,
        tmnxMcLagPeerStatsPktsRxKpalive,
        tmnxMcLagPeerStatsPktsRxConfig,
        tmnxMcLagPeerStatsPktsRxPeerCfg,
        tmnxMcLagPeerStatsPktsRxState,
        tmnxMcLagPeerStatsDropStateDsbld,
        tmnxMcLagPeerStatsDropPktTooShrt,
        tmnxMcLagPeerStatsDropTlvInvldSz,
        tmnxMcLagPeerStatsDropTlvInvldId,
        tmnxMcLagPeerStatsDropOutOfSeq,
        tmnxMcLagPeerStatsDropUnknownTlv,
        tmnxMcLagPeerStatsDropMD5,
        tmnxMcLagPeerStatsPktsTx,
        tmnxMcLagPeerStatsPktsTxKpalive,
        tmnxMcLagPeerStatsPktsTxPeerCfg,
        tmnxMcLagPeerStatsPktsTxFailed,
        tmnxMcLagLagStatsPktsRxConfig,
        tmnxMcLagLagStatsPktsRxState,
        tmnxMcLagLagStatsPktsTxConfig,
        tmnxMcLagLagStatsPktsTxState,
        tmnxMcLagLagStatsPktsTxFailed
    }
    STATUS      obsolete
    DESCRIPTION
        "The group of objects supporting multi-chassis redundancy on version
         5.0 of the Nokia SROS series systems."
    ::= { tmnxMcRedundancyGroups 1 }

tmnxSrrpV5v0Group                OBJECT-GROUP
    OBJECTS     {
        tmnxSrrpOperRowStatus,
        tmnxSrrpOperDescription,
        tmnxSrrpOperGwMac,
        tmnxSrrpOperGwOperMac,
        tmnxSrrpOperPriority,
        tmnxSrrpOperInUsePriority,
        tmnxSrrpOperMasterPriority,
        tmnxSrrpOperKeepAliveInterval,
        tmnxSrrpOperMsgPathSapPortId,
        tmnxSrrpOperMsgPathSapEncapVal,
        tmnxSrrpOperAdminState,
        tmnxSrrpOperState,
        tmnxSrrpOperMasterSince,
        tmnxSrrpOperVrrpPolicy1,
        tmnxSrrpOperVrrpPolicy2,
        tmnxSrrpOperFlags,
        tmnxSrrpOperMasterDownInterval,
        tmnxSrrpOperMasterDownTimer,
        tmnxSrrpStatsBecomeMaster,
        tmnxSrrpStatsMasterChanges,
        tmnxSrrpStatsAdvSent,
        tmnxSrrpStatsAdvRcvd,
        tmnxSrrpStatsPriZeroPktsSent,
        tmnxSrrpStatsPriZeroPktsRcvd,
        tmnxSrrpStatsPreemptEvents,
        tmnxSrrpStatsPreemptedEvents,
        tmnxSrrpStatsAdvIntDiscards,
        tmnxSrrpStatsAdvIntErrors,
        tmnxSrrpStatsBecomeBackupRouting,
        tmnxSrrpStatsBecomeBackupShunt,
        tmnxSrrpStatsBecomeNonMaster
    }
    STATUS      current
    DESCRIPTION
        "The group of objects supporting subscriber router redundancy on
         version 5.0 of the Nokia SROS series systems."
    ::= { tmnxMcRedundancyGroups 2 }

tmnxMcRedundancyNotifyObjsV5v0Group OBJECT-GROUP
    OBJECTS     {
        tmnxMcPeerIpAddrTypeForNotify,
        tmnxMcPeerIpAddrForNotify,
        tmnxMcPeerSyncClient,
        tmnxMcRemoteGrpIfNameForNotify,
        tmnxMcRemoteRedIfNameForNotify,
        tmnxMcRemoteSyncTag,
        tmnxMcLagConfigLagIds,
        tmnxMcPeerClockSkew
    }
    STATUS      current
    DESCRIPTION
        "The group of objects supporting multi-chassis notifications on Nokia
         SROS series systems."
    ::= { tmnxMcRedundancyGroups 3 }

tmnxMcRingV6v0Group              OBJECT-GROUP
    OBJECTS     {
        tmnxMcPeerSyncMcRing,
        tmnxMcRingTableLastChanged,
        tmnxMcRingRowStatus,
        tmnxMcRingLastChanged,
        tmnxMcRingAdminState,
        tmnxMcRingInbCtrlSvcId,
        tmnxMcRingInbCtrlIfName,
        tmnxMcRingInbCtrlDestIpType,
        tmnxMcRingInbCtrlDestIp,
        tmnxMcRingVlanMap,
        tmnxMcRingVlanMapExcl,
        tmnxMcRingInbCtrlDbMax,
        tmnxMcRingInbCtrlDbAdmin,
        tmnxMcRingInfoTableLastChanged,
        tmnxMcRingInfoLastChanged,
        tmnxMcRingInfoOperState,
        tmnxMcRingInfoFailureReason,
        tmnxMcRingInfoInbCtrlOperState,
        tmnxMcRingInfoInbCtrlSrcIpType,
        tmnxMcRingInfoInbCtrlSrcIp,
        tmnxMcRingInfoInbCtrlDbStart,
        tmnxMcRingInfoInbCtrlDbTime,
        tmnxMcRingInfoInbCtrlDbGuard,
        tmnxMcRingInfoPortId,
        tmnxMcRingInfoVlanMap,
        tmnxMcRingInfoVlanMapExcl,
        tmnxMcRingInfoCtrlVlanMap,
        tmnxMcRingNodeTableLastChanged,
        tmnxMcRingNodeRowStatus,
        tmnxMcRingNodeLastChanged,
        tmnxMcRingNodeRncvAdminState,
        tmnxMcRingNodeRncvSvcId,
        tmnxMcRingNodeRncvEncapValue,
        tmnxMcRingNodeRncvSrcIpType,
        tmnxMcRingNodeRncvSrcIp,
        tmnxMcRingNodeRncvDestIpType,
        tmnxMcRingNodeRncvDestIp,
        tmnxMcRingNodeRncvInterval,
        tmnxMcRingNodeRncvSrcMac,
        tmnxMcRingNodeInfoTableLastChgd,
        tmnxMcRingNodeInfoLastChanged,
        tmnxMcRingNodeInfoLocOperState,
        tmnxMcRingNodeInfoRemOperState,
        tmnxMcRingNodeInfoInUse,
        tmnxMcRingNodeInfoFailureReason,
        tmnxMcTlsCfgTableLastChanged,
        tmnxMcTlsCfgLastChanged,
        tmnxMcTlsCfgDefGwIpType,
        tmnxMcTlsCfgDefGwIp,
        tmnxMcTlsCfgDefGwMac,
        tmnxMcEpipeSapTableLastChanged,
        tmnxMcEpipeSapRowStatus,
        tmnxMcEpipeSapLastChanged,
        tmnxMcEpipeSapRingNodeName,
        tmnxMcrPeerStatsTableLastChanged,
        tmnxMcrPeerStatsLastChanged,
        tmnxMcrPeerStatsRx,
        tmnxMcrPeerStatsRxMcsIdReq,
        tmnxMcrPeerStatsRxMcsIdRsp,
        tmnxMcrPeerStatsRxRingExistsReq,
        tmnxMcrPeerStatsRxRingExistsRsp,
        tmnxMcrPeerStatsRxKeepAlive,
        tmnxMcrPeerStatsTx,
        tmnxMcrPeerStatsTxMcsIdReq,
        tmnxMcrPeerStatsTxMcsIdRsp,
        tmnxMcrPeerStatsTxRingExistsReq,
        tmnxMcrPeerStatsTxRingExistsRsp,
        tmnxMcrPeerStatsTxKeepAlive,
        tmnxMcrRingStatsTableLastChanged,
        tmnxMcrRingStatsLastChanged,
        tmnxMcrRingStatsRxSapsChanged,
        tmnxMcrRingStatsTxSapsChanged,
        tmnxMcrRingStatsRxOpaqueDelivrd,
        tmnxMcrRingStatsRxOpaqueNoDest,
        tmnxMcrRingStatsTxOpaque,
        tmnxMcrStatsRx,
        tmnxMcrStatsRxTooShort,
        tmnxMcrStatsRxWrongAuth,
        tmnxMcrStatsRxInvalidTlv,
        tmnxMcrStatsRxIncomplete,
        tmnxMcrStatsRxUnknownType,
        tmnxMcrStatsRxUnknownPeer,
        tmnxMcrStatsRxUnknownRing,
        tmnxMcrStatsRxUnknownRingNode,
        tmnxMcrStatsRxDelivrdToPeer,
        tmnxMcrStatsRxDelivrdToRing,
        tmnxMcrStatsRxDelivrdToRingNode,
        tmnxMcrStatsTx,
        tmnxMcrStatsTxNoBuffer,
        tmnxMcrStatsTxTransmitFailed,
        tmnxMcrStatsMissedConfigEvent,
        tmnxMcrStatsMissedBfdEvent,
        tmnxMcrStatsTxUnknownDest,
        tmnxMcrRingNodeStatsTableLastChanged,
        tmnxMcrRingNodeStatsLastChanged,
        tmnxMcrRingNodeStatsRxDetect,
        tmnxMcrRingNodeStatsRxDetectAck,
        tmnxMcrRingNodeStatsRncvRxResp,
        tmnxMcrRingNodeStatsTxDetect,
        tmnxMcrRingNodeStatsTxDetectAck,
        tmnxMcrRingNodeStatsRncvTxReq,
        tmnxMcrRingNodeStatsRncvRtTime,
        tmnxMcRingDbTableLastChanged,
        tmnxMcRingDbTableSize,
        tmnxMcRingDbTime,
        tmnxMcRingDbOperState
    }
    STATUS      current
    DESCRIPTION
        "The group of objects supporting multi-chassis ring on the Nokia SROS
         series systems."
    ::= { tmnxMcRedundancyGroups 4 }

tmnxMcPeerSyncGroup              OBJECT-GROUP
    OBJECTS     {
        tmnxMcPeerSyncMldSnooping
    }
    STATUS      current
    DESCRIPTION
        "The group of objects supporting multi-chassis peer synchronization on
         the Nokia SROS series systems."
    ::= { tmnxMcRedundancyGroups 5 }

tmnxMcsDhcpsV6v0Group            OBJECT-GROUP
    OBJECTS     {
        tmnxMcsDhcpsTableLastChgd,
        tmnxMcsDhcpsRowStatus,
        tmnxMcsDhcpsPeerIpType,
        tmnxMcsDhcpsPeerIpAddr,
        tmnxMcsDhcpsSyncTag,
        tmnxMcPeerSyncDhcpServer
    }
    STATUS      current
    DESCRIPTION
        "The group of objects supporting multi-chassis peer synchronization of
         DHCP Server information on the Nokia SROS series systems."
    ::= { tmnxMcRedundancyGroups 6 }

tmnxMcRedundancyV6v0Group        OBJECT-GROUP
    OBJECTS     {
        tmnxMcPeerRowStatus,
        tmnxMcPeerDescription,
        tmnxMcPeerAuthKey,
        tmnxMcPeerSrcIpType,
        tmnxMcPeerSrcIpAddr,
        tmnxMcPeerAdminState,
        tmnxMcPeerSrcIpOperType,
        tmnxMcPeerSrcIpOperAddr,
        tmnxMcPeerRingsOperState,
        tmnxMcPeerSyncRowStatus,
        tmnxMcPeerSyncIgmp,
        tmnxMcPeerSyncIgmpSnooping,
        tmnxMcPeerSyncSubMgmt,
        tmnxMcPeerSyncSrrp,
        tmnxMcPeerSyncAdminState,
        tmnxMcPeerSyncOperState,
        tmnxMcPeerSyncOperFlags,
        tmnxMcPeerSyncStatus,
        tmnxMcPeerSyncLastSyncTime,
        tmnxMcPeerSyncNumEntries,
        tmnxMcPeerSyncLclDeletedEntries,
        tmnxMcPeerSyncAlarmedEntries,
        tmnxMcPeerSyncRemNumEntries,
        tmnxMcPeerSyncRemLclDelEntries,
        tmnxMcPeerSyncRemAlarmedEntries,
        tmnxMcPeerSyncPktsTxAll,
        tmnxMcPeerSyncPktsTxHello,
        tmnxMcPeerSyncPktsTxData,
        tmnxMcPeerSyncPktsTxOther,
        tmnxMcPeerSyncPktsTxErr,
        tmnxMcPeerSyncPktsRxAll,
        tmnxMcPeerSyncPktsRxHello,
        tmnxMcPeerSyncPktsRxData,
        tmnxMcPeerSyncPktsRxOther,
        tmnxMcPeerSyncPktsRxErr,
        tmnxMcPeerSyncPktsRxErrHeader,
        tmnxMcPeerSyncPktsRxErrBody,
        tmnxMcPeerSyncPktsRxErrSeqNum,
        tmnxMcPeerSyncPortRowStatus,
        tmnxMcPeerSyncPortSyncTag,
        tmnxMcPeerSyncPortEncapRowStatus,
        tmnxMcPeerSyncPortEncapSyncTag,
        tmnxMcsClientNumEntries,
        tmnxMcsClientLclDeletedEntries,
        tmnxMcsClientAlarmedEntries,
        tmnxMcsClientRemNumEntries,
        tmnxMcsClientRemLclDelEntries,
        tmnxMcsClientRemAlarmedEntries,
        tmnxMcLagConfigTableLastChanged,
        tmnxMcLagConfigPeerLastChanged,
        tmnxMcLagConfigPeerAdminstate,
        tmnxMcLagConfigKeepALiveIvl,
        tmnxMcLagConfigHoldOnNgbrFailure,
        tmnxMcLagConfigOperState,
        tmnxMcLagConfigPeerLastStateChge,
        tmnxMcLagConfigLagTableLastChanged,
        tmnxMcLagConfigLagLastChanged,
        tmnxMcLagConfigLagRowStatus,
        tmnxMcLagConfigLaglacpKey,
        tmnxMcLagConfigLagSystemId,
        tmnxMcLagConfigLagSystemPriority,
        tmnxMcLagConfigLagRemoteLagId,
        tmnxMcLagActiveStandby,
        tmnxMcLagLacpIdInUse,
        tmnxMcLagExtendedTimeOut,
        tmnxMcLagSelectionLogic,
        tmnxMcLagConfigMismatchString,
        tmnxMcLagConfigMismatchFlags,
        tmnxMcLagStatsPktsRx,
        tmnxMcLagStatsPktsRxKeepalive,
        tmnxMcLagStatsPktsRxConfig,
        tmnxMcLagStatsPktsRxPeerConfig,
        tmnxMcLagStatsPktsRxState,
        tmnxMcLagStatsDropPktKpaliveTask,
        tmnxMcLagStatsDropPktTooShort,
        tmnxMcLagStatsDropPktVerifyFaild,
        tmnxMcLagStatsDropTlvInvalidSize,
        tmnxMcLagStatsDropOutOfSeq,
        tmnxMcLagStatsDropUnknownTlv,
        tmnxMcLagStatsDropTlvInvldLagId,
        tmnxMcLagStatsDropMD5,
        tmnxMcLagStatsDropUnknownPeer,
        tmnxMcLagStatsPktsTx,
        tmnxMcLagStatsPktsTxKeepalive,
        tmnxMcLagStatsPktsTxConfig,
        tmnxMcLagStatsPktsTxPeerConfig,
        tmnxMcLagStatsPktsTxState,
        tmnxMcLagStatsPktsTxFailed,
        tmnxMcLagPeerStatsPktsRx,
        tmnxMcLagPeerStatsPktsRxKpalive,
        tmnxMcLagPeerStatsPktsRxConfig,
        tmnxMcLagPeerStatsPktsRxPeerCfg,
        tmnxMcLagPeerStatsPktsRxState,
        tmnxMcLagPeerStatsDropStateDsbld,
        tmnxMcLagPeerStatsDropPktTooShrt,
        tmnxMcLagPeerStatsDropTlvInvldSz,
        tmnxMcLagPeerStatsDropTlvInvldId,
        tmnxMcLagPeerStatsDropOutOfSeq,
        tmnxMcLagPeerStatsDropUnknownTlv,
        tmnxMcLagPeerStatsDropMD5,
        tmnxMcLagPeerStatsPktsTx,
        tmnxMcLagPeerStatsPktsTxKpalive,
        tmnxMcLagPeerStatsPktsTxPeerCfg,
        tmnxMcLagPeerStatsPktsTxFailed,
        tmnxMcLagLagStatsPktsRxConfig,
        tmnxMcLagLagStatsPktsRxState,
        tmnxMcLagLagStatsPktsTxConfig,
        tmnxMcLagLagStatsPktsTxState,
        tmnxMcLagLagStatsPktsTxFailed
    }
    STATUS      obsolete
    DESCRIPTION
        "The group of objects supporting multi-chassis redundancy on version
         6.0 of the Nokia SROS series systems."
    ::= { tmnxMcRedundancyGroups 7 }

tmnxSrrpV6v1Group                OBJECT-GROUP
    OBJECTS     {
        tmnxSrrpAssoBfdIntfTblLastChgd,
        tmnxSrrpAssoBfdIntfRowStatus,
        tmnxSrrpAssoBfdIntfLastChanged,
        tmnxSrrpAssoBfdIntfSrcIpType,
        tmnxSrrpAssoBfdIntfSrcIp,
        tmnxSrrpAssoBfdIntfSessOperState
    }
    STATUS      current
    DESCRIPTION
        "The group of objects supporting SRRP BFD on version 6.1 of the Nokia
         SROS series systems."
    ::= { tmnxMcRedundancyGroups 8 }

tmnxSrrpNotificationObjV6v1Group OBJECT-GROUP
    OBJECTS     {
        tmnxSrrpNotifBfdIntfSvcId,
        tmnxSrrpNotifBfdIntfIfName,
        tmnxSrrpNotifBfdIntfDestIpType,
        tmnxSrrpNotifBfdIntfDestIp,
        tmnxSrrpNotifBfdIntfSessState
    }
    STATUS      current
    DESCRIPTION
        "The group of notification objects supporting multi-chassis redundancy
         SRRP on Nokia SROS 6.1 series systems."
    ::= { tmnxMcRedundancyGroups 9 }

tmnxMcL3RingGroup                OBJECT-GROUP
    OBJECTS     {
        tmnxMcRingType,
        tmnxMcL3RingSrrpLastChanged,
        tmnxMcL3RingSrrpRowStatus,
        tmnxMcL3RingSrrpTableLastChanged
    }
    STATUS      current
    DESCRIPTION
        "The group of notification objects supporting multi-chassis redundancy
         L3 Ring on Nokia SROS 7.0 series systems."
    ::= { tmnxMcRedundancyGroups 10 }

tmnxMcPeerEPGroup                OBJECT-GROUP
    OBJECTS     {
        tmnxMcPeerEPAdminState,
        tmnxMcPeerEPBootTimer,
        tmnxMcPeerEPHoldOnNbrFail,
        tmnxMcPeerEPKeepAliveIntvl,
        tmnxMcPeerEPLastChanged,
        tmnxMcPeerEPPassiveMode,
        tmnxMcPeerEPPassiveModeOper,
        tmnxMcPeerEPRefCount,
        tmnxMcPeerEPBfd,
        tmnxMcPeerEPRowStatus,
        tmnxMcPeerEPSysPriority,
        tmnxMcPeerEPTableLastChanged,
        tmnxMcPeerName,
        tmnxMcEPPeerStatsDropMD5,
        tmnxMcEPPeerStatsDropOutOfSeq,
        tmnxMcEPPeerStatsDropPktTooShrt,
        tmnxMcEPPeerStatsDropStateDsbld,
        tmnxMcEPPeerStatsDropTlvInvldId,
        tmnxMcEPPeerStatsDropTlvInvldSz,
        tmnxMcEPPeerStatsDropUnknownTlv,
        tmnxMcEPPeerStatsPktsRx,
        tmnxMcEPPeerStatsPktsRxConfig,
        tmnxMcEPPeerStatsPktsRxKpalive,
        tmnxMcEPPeerStatsPktsRxPeerCfg,
        tmnxMcEPPeerStatsPktsRxState,
        tmnxMcEPPeerStatsPktsTx,
        tmnxMcEPPeerStatsPktsTxFailed,
        tmnxMcEPPeerStatsPktsTxKpalive,
        tmnxMcEPPeerStatsPktsTxPeerCfg,
        tmnxMcEPPeerStatsDropEpNoPeer,
        tmnxMcPeerEPOperState,
        tmnxMcPeerEPPeerLastStateChge,
        tmnxMcEpStatsDropEpNoPeer,
        tmnxMcEpStatsDropMD5,
        tmnxMcEpStatsDropOutOfSeq,
        tmnxMcEpStatsDropPktKpaliveTask,
        tmnxMcEpStatsDropPktTooShort,
        tmnxMcEpStatsDropPktVerifyFailed,
        tmnxMcEpStatsDropTlvInvalidSize,
        tmnxMcEpStatsDropTlvInvldEpId,
        tmnxMcEpStatsDropUnknownPeer,
        tmnxMcEpStatsDropUnknownTlv,
        tmnxMcEpStatsPktsRx,
        tmnxMcEpStatsPktsRxConfig,
        tmnxMcEpStatsPktsRxKeepalive,
        tmnxMcEpStatsPktsRxPeerConfig,
        tmnxMcEpStatsPktsRxState,
        tmnxMcEpStatsPktsTx,
        tmnxMcEpStatsPktsTxConfig,
        tmnxMcEpStatsPktsTxFailed,
        tmnxMcEpStatsPktsTxKeepalive,
        tmnxMcEpStatsPktsTxPeerConfig,
        tmnxMcEpStatsPktsTxState
    }
    STATUS      current
    DESCRIPTION
        "The group of notification objects supporting multi-chassis redundancy
         peer group on Nokia SROS 7.0 series systems."
    ::= { tmnxMcRedundancyGroups 11 }

tmnxMcPeerEPNotifyObjsV7v0Group  OBJECT-GROUP
    OBJECTS     {
        tmnxMcPeerEPBfdSessionOpenStatus,
        tmnxMcPeerEPPsvModeConfigState
    }
    STATUS      current
    DESCRIPTION
        "The group of objects supporting management of multi-chassis endpoint
         notification objects on Nokia SROS series systems."
    ::= { tmnxMcRedundancyGroups 12 }

tmnxMcsSubHostTrkGroup           OBJECT-GROUP
    OBJECTS     {
        tmnxMcPeerSyncSubHostTrk
    }
    STATUS      current
    DESCRIPTION
        "The group of objects supporting multi-chassis peer synchronization of
         subscriber host tracking information on the Nokia SROS series systems."
    ::= { tmnxMcRedundancyGroups 13 }

tmnxMcLagPbbGroup                OBJECT-GROUP
    OBJECTS     {
        tmnxMcLagConfigLagSrcBMacLSB,
        tmnxMcLagConfigLagOperSrcBMacLSB
    }
    STATUS      current
    DESCRIPTION
        "The group of objects supporting multi-chassis Lag specific provider
         backbone feature objects on the Nokia SROS series systems."
    ::= { tmnxMcRedundancyGroups 14 }

tmnxMcRedBgpMultiHomeGroup       OBJECT-GROUP
    OBJECTS     {
        tmnxMcRedBgpMultiHomeBootTimer,
        tmnxMcRedBgpMultiHomeSiteTimer
    }
    STATUS      current
    DESCRIPTION
        "The group of objects supporting multi-chassis redundancy specific
         multi-home feature objects on the Nokia SROS series systems."
    ::= { tmnxMcRedundancyGroups 15 }

tmnxMcTlsSapGroup                OBJECT-GROUP
    OBJECTS     {
        tmnxMcTlsSapLastChanged,
        tmnxMcTlsSapRingNodeName,
        tmnxMcTlsSapRowStatus,
        tmnxMcTlsSapTableLastChanged
    }
    STATUS      current
    DESCRIPTION
        "The group of objects supporting multi-chassis redundancy specific TLS
         SAP objects on the Nokia SROS series systems."
    ::= { tmnxMcRedundancyGroups 16 }

tmnxSrrpV8v0Group                OBJECT-GROUP
    OBJECTS     {
        tmnxSrrpOperSendFibPopulation
    }
    STATUS      current
    DESCRIPTION
        "The group of objects supporting subscriber router redundancy on on
         Nokia SROS series systems 8.0 release."
    ::= { tmnxMcRedundancyGroups 17 }

tmnxSrrpV9v0Group                OBJECT-GROUP
    OBJECTS     {
        tmnxSrrpOperMonitorOperGrp,
        tmnxSrrpOperOneGarpPerSap,
        tmnxSrrpOperPreempt,
        tmnxSrrpOperPriorityStep
    }
    STATUS      current
    DESCRIPTION
        "The group of objects supporting subscriber router redundancy on on
         Nokia SROS series systems 8.0 release."
    ::= { tmnxMcRedundancyGroups 18 }

tmnxMcRedundancyV9v0Group        OBJECT-GROUP
    OBJECTS     {
        tmnxMcPeerRowStatus,
        tmnxMcPeerDescription,
        tmnxMcPeerAuthKey,
        tmnxMcPeerSrcIpType,
        tmnxMcPeerSrcIpAddr,
        tmnxMcPeerAdminState,
        tmnxMcPeerSrcIpOperType,
        tmnxMcPeerSrcIpOperAddr,
        tmnxMcPeerRingsOperState,
        tmnxMcPeerSyncRowStatus,
        tmnxMcPeerSyncIgmp,
        tmnxMcPeerSyncIgmpSnooping,
        tmnxMcPeerSyncSubMgmt,
        tmnxMcPeerSyncSrrp,
        tmnxMcPeerSyncAdminState,
        tmnxMcPeerSyncOperState,
        tmnxMcPeerSyncOperFlags,
        tmnxMcPeerSyncStatus,
        tmnxMcPeerSyncLastSyncTime,
        tmnxMcPeerSyncNumEntries,
        tmnxMcPeerSyncLclDeletedEntries,
        tmnxMcPeerSyncAlarmedEntries,
        tmnxMcPeerSyncRemNumEntries,
        tmnxMcPeerSyncRemLclDelEntries,
        tmnxMcPeerSyncRemAlarmedEntries,
        tmnxMcPeerSyncPktsTxAll,
        tmnxMcPeerSyncPktsTxHello,
        tmnxMcPeerSyncPktsTxData,
        tmnxMcPeerSyncPktsTxOther,
        tmnxMcPeerSyncPktsTxErr,
        tmnxMcPeerSyncPktsRxAll,
        tmnxMcPeerSyncPktsRxHello,
        tmnxMcPeerSyncPktsRxData,
        tmnxMcPeerSyncPktsRxOther,
        tmnxMcPeerSyncPktsRxErr,
        tmnxMcPeerSyncPktsRxErrHeader,
        tmnxMcPeerSyncPktsRxErrBody,
        tmnxMcPeerSyncPktsRxErrSeqNum,
        tmnxMcPeerSyncPortRowStatus,
        tmnxMcPeerSyncPortSyncTag,
        tmnxMcPeerSyncPortEncapRowStatus,
        tmnxMcPeerSyncPortEncapSyncTag,
        tmnxMcsClientNumEntries,
        tmnxMcsClientLclDeletedEntries,
        tmnxMcsClientAlarmedEntries,
        tmnxMcsClientRemNumEntries,
        tmnxMcsClientRemLclDelEntries,
        tmnxMcsClientRemAlarmedEntries,
        tmnxMcLagConfigTableLastChanged,
        tmnxMcLagConfigPeerLastChanged,
        tmnxMcLagConfigPeerAdminstate,
        tmnxMcLagConfigKeepALiveIvl,
        tmnxMcLagConfigHoldOnNgbrFailure,
        tmnxMcLagConfigOperState,
        tmnxMcLagConfigPeerLastStateChge,
        tmnxMcLagConfigLagTableLastChanged,
        tmnxMcLagConfigLagLastChanged,
        tmnxMcLagConfigLagRowStatus,
        tmnxMcLagConfigLaglacpKey,
        tmnxMcLagConfigLagSystemId,
        tmnxMcLagConfigLagSystemPriority,
        tmnxMcLagConfigLagRemoteLagId,
        tmnxMcLagActiveStandby,
        tmnxMcLagLacpIdInUse,
        tmnxMcLagExtendedTimeOut,
        tmnxMcLagSelectionLogic,
        tmnxMcLagConfigMismatchString,
        tmnxMcLagConfigMismatchFlags,
        tmnxMcLagStatsPktsRx,
        tmnxMcLagStatsPktsRxKeepalive,
        tmnxMcLagStatsPktsRxConfig,
        tmnxMcLagStatsPktsRxPeerConfig,
        tmnxMcLagStatsPktsRxState,
        tmnxMcLagStatsDropPktKpaliveTask,
        tmnxMcLagStatsDropPktTooShort,
        tmnxMcLagStatsDropPktVerifyFaild,
        tmnxMcLagStatsDropTlvInvalidSize,
        tmnxMcLagStatsDropOutOfSeq,
        tmnxMcLagStatsDropUnknownTlv,
        tmnxMcLagStatsDropTlvInvldLagId,
        tmnxMcLagStatsDropMD5,
        tmnxMcLagStatsDropUnknownPeer,
        tmnxMcLagStatsPktsTx,
        tmnxMcLagStatsPktsTxKeepalive,
        tmnxMcLagStatsPktsTxConfig,
        tmnxMcLagStatsPktsTxPeerConfig,
        tmnxMcLagStatsPktsTxState,
        tmnxMcLagStatsPktsTxFailed,
        tmnxMcLagPeerStatsPktsRx,
        tmnxMcLagPeerStatsPktsRxKpalive,
        tmnxMcLagPeerStatsPktsRxConfig,
        tmnxMcLagPeerStatsPktsRxPeerCfg,
        tmnxMcLagPeerStatsPktsRxState,
        tmnxMcLagPeerStatsDropStateDsbld,
        tmnxMcLagPeerStatsDropPktTooShrt,
        tmnxMcLagPeerStatsDropTlvInvldSz,
        tmnxMcLagPeerStatsDropTlvInvldId,
        tmnxMcLagPeerStatsDropOutOfSeq,
        tmnxMcLagPeerStatsDropUnknownTlv,
        tmnxMcLagPeerStatsDropMD5,
        tmnxMcLagPeerStatsPktsTx,
        tmnxMcLagPeerStatsPktsTxKpalive,
        tmnxMcLagPeerStatsPktsTxPeerCfg,
        tmnxMcLagPeerStatsPktsTxFailed,
        tmnxMcLagLagStatsPktsRxConfig,
        tmnxMcLagLagStatsPktsRxState,
        tmnxMcLagLagStatsPktsTxConfig,
        tmnxMcLagLagStatsPktsTxState,
        tmnxMcLagLagStatsPktsTxFailed,
        tmnxMcPeerSyncSubMgmtPppoe
    }
    STATUS      current
    DESCRIPTION
        "The group of objects supporting multi-chassis redundancy on version
         9.0 of the Nokia SROS series systems."
    ::= { tmnxMcRedundancyGroups 19 }

tmnxMcRedundancyV10v0Group       OBJECT-GROUP
    OBJECTS     {
        tmnxMcsTnlGrpTblLastChgd,
        tmnxMcsTnlGrpRowStatus,
        tmnxMcsTnlGrpSyncTag,
        tmnxMcPeerSyncIpsec,
        tMcPeerIPsecDiscoveryIntvlBoot,
        tMcPeerIPsecDiscoveryIntvl,
        tMcPeerIPsecRowStatus,
        tMcPeerIPsecLastChgd,
        tMcPeerIPsecBfdEnable,
        tMcPeerIPsecBfdEnableSvc,
        tMcPeerIPsecBfdIntfDestIp,
        tMcPeerIPsecBfdIntfDestIpType,
        tMcPeerIPsecBfdIntfIfName,
        tMcPeerIPsecTnlGrpAdminState,
        tMcPeerIPsecTnlGrpLastChgd,
        tMcPeerIPsecTnlGrpPeerGrpId,
        tMcPeerIPsecTnlGrpPreempt,
        tMcPeerIPsecTnlGrpPriority,
        tMcPeerIPsecTnlGrpRowStatus,
        tMcPeerIPsecTnlGrpTblLastChgd,
        tMcPeerIPsecTnlGrpOperState,
        tMcPeerIPsecTnlGrpMasterState,
        tMcPeerIPsecTnlGrpReason,
        tMcPeerIPsecTnlGrpForceSwitch,
        tMcPeerIPsecHoldOnNgbrFail,
        tMcPeerIPsecKeepAliveIntvl,
        tMcPeerIPsecTnlGrpProtectStatus,
        tMcPeerIPsecTblLastChgd,
        tMcPeerTnlGrpStatDynInstalled,
        tMcPeerTnlGrpStatDynInstalling,
        tMcPeerTnlGrpStatDynAwaitConf,
        tMcPeerTnlGrpStatDynFailed,
        tMcPeerTnlGrpStatInstalled,
        tMcPeerTnlGrpStatInstalling,
        tMcPeerTnlGrpStatAwaitConf,
        tMcPeerTnlGrpStatFailed
    }
    STATUS      current
    DESCRIPTION
        "The group of objects supporting multi-chassis redundancy on version
         10.0 of the Nokia SROS series systems."
    ::= { tmnxMcRedundancyGroups 20 }

tmnxMcsDhcpsV11v0Group           OBJECT-GROUP
    OBJECTS     {
        tmnxMcsDhcpsPoolTableLastChgd,
        tmnxMcsDhcpsPoolRowStatus,
        tmnxMcsDhcpsPoolPeerIpType,
        tmnxMcsDhcpsPoolPeerIpAddr,
        tmnxMcsDhcpsPoolSyncTag
    }
    STATUS      current
    DESCRIPTION
        "The group of objects supporting multi-chassis peer synchronization of
         DHCP Server information on the Nokia SROS series systems."
    ::= { tmnxMcRedundancyGroups 21 }

tmnxMcPeerNotifyObjsV10v0Group   OBJECT-GROUP
    OBJECTS     {
        tMcPeerIPsecTnlGrpMasterStateOld
    }
    STATUS      current
    DESCRIPTION
        "The group of notification objects supporting multi-chassis redundancy
         SRRP on Nokia SROS 11.0 series systems."
    ::= { tmnxMcRedundancyGroups 22 }

tmnxMcPeerIPsecTnlGrpV10v0Group  OBJECT-GROUP
    OBJECTS     {
        tMcPeerIPsecTnlGrpForceSwitchTo
    }
    STATUS      current
    DESCRIPTION
        "The group of objects supporting IPsec tunnel-group multi-chassis
         redundancy on on Nokia SROS series systems 11.0 release."
    ::= { tmnxMcRedundancyGroups 23 }

tmnxMcWarmStandbyGroup           OBJECT-GROUP
    OBJECTS     {
        tmnxMcPeerWarmStandby,
        tmnxMcPeerRemoteWarmStandby,
        tmnxMcOmcrStatFailed,
        tmnxMcOmcrStatFailure,
        tmnxMcOmcrStatNumFailedEntries,
        tmnxMcOmcrDomainTableLastCh,
        tmnxMcOmcrDomainLastMgmtChange,
        tmnxMcOmcrDomainRowStatus,
        tmnxMcOmcrDomainDescription,
        tmnxMcOmcrDomainHoldDownTime,
        tmnxMcOmcrDomainState,
        tmnxSrrpOperDomain,
        tmnxSrrpOperDomainColor
    }
    STATUS      current
    DESCRIPTION
        "The group of objects supporting multi-chassis warm standby mode of
         operation on the Nokia SROS series systems."
    ::= { tmnxMcRedundancyGroups 24 }

tmnxMcRedundancyV12v0Group       OBJECT-GROUP
    OBJECTS     {
        tmnxMcWppPeerStatsTableLastCh,
        tmnxMcWppPeerStatsLastChanged,
        tmnxMcWppPeerStatsName,
        tmnxMcWppPeerStatsVal,
        tmnxMcPeerSyncOmcrStandby,
        tmnxMcPeerSyncOmcrAlarmed,
        tmnxMcPeerSyncOmcrRemStandby,
        tmnxMcPeerSyncOmcrRemAlarmed,
        tmnxMcsClientOmcrStandby,
        tmnxMcsClientOmcrAlarmed,
        tmnxMcsClientOmcrRemStandby,
        tmnxMcsClientOmcrRemAlarmed,
        tmnxMcPeerSyncMld,
        tmnxMcPeerSyncPythonCache,
        tmnxMcsPyPlcyTableLastChgd,
        tmnxMcsPyPlcyRowStatus,
        tmnxMcsPyPlcyPeerIpAddrType,
        tmnxMcsPyPlcyPeerIpAddr,
        tmnxMcsPyPlcyMcsSyncTag,
        tmnxMcsPyPlcyTableLastChanged
    }
    STATUS      current
    DESCRIPTION
        "The group of objects supporting multi-chassis redundancy added in
         release 12.0 of the Nokia SROS."
    ::= { tmnxMcRedundancyGroups 25 }

tmnxSrrpV10v0Group               OBJECT-GROUP
    OBJECTS     {
        tmnxSrrpOperDownReason
    }
    STATUS      current
    DESCRIPTION
        "The group of objects supporting subscriber router redundancy on on
         Nokia SROS series systems 10.0 release."
    ::= { tmnxMcRedundancyGroups 26 }

tmnxMcRedundancyV13v0Group       OBJECT-GROUP
    OBJECTS     {
        tmnxMcPeerSyncL2tp,
        tmnxMcPeerSyncDiameterProxy,
        tmnxMcL2tpRowStatus,
        tmnxMcL2tpLastChanged,
        tmnxMcL2tpPeerIpAddrType,
        tmnxMcL2tpPeerIpAddr,
        tmnxMcL2tpSyncTag,
        tmnxMcL2tpTableLastChanged,
        tmnxMcTrkSrrpRowStatus,
        tmnxMcTrkSrrpLastCh,
        tmnxMcTrkSrrpL2tpTuStart,
        tmnxMcTrkSrrpL2tpTuEnd,
        tmnxMcTrkSrrpTableLastChanged,
        tmnxMcDiamPrxRowStatus,
        tmnxMcDiamPrxLastChanged,
        tmnxMcDiamPrxPeerIpAddrType,
        tmnxMcDiamPrxPeerIpAddr,
        tmnxMcDiamPrxSyncTag,
        tmnxMcDiamPrxTableLastChanged
    }
    STATUS      current
    DESCRIPTION
        "The group of objects supporting multi-chassis redundancy added in
         release 13.0 of the Nokia SROS."
    ::= { tmnxMcRedundancyGroups 27 }

tmnxMcRedBgpEvpnGroup            OBJECT-GROUP
    OBJECTS     {
        tmnxMcRedBgpEvpnMHBootTimer,
        tmnxMcRedBgpEvpnMHEsActTimer,
        tmnxMcRedBgpEvpnMHBootTimerRem
    }
    STATUS      current
    DESCRIPTION
        "A group of objects supporting multi-chassis redundancy BGP EVPN
         feature on Nokia SROS series systems."
    ::= { tmnxMcRedundancyGroups 28 }

tmnxMcRedBgpMHSiteGroup          OBJECT-GROUP
    OBJECTS     {
        tmnxMcRedBgpMHSiteMinDnTimer
    }
    STATUS      current
    DESCRIPTION
        "A group of objects supporting multi-chassis redundancy BGP
         multi-homing site feature on Nokia SROS series systems."
    ::= { tmnxMcRedundancyGroups 29 }

tmnxMcRedundancyV14v0Group       OBJECT-GROUP
    OBJECTS     {
        tmnxMcPeerSyncPimSnpgSap,
        tmnxMcPeerSyncPimSnpgSdp,
        tmnxMcPeerSyncSdpRowStatus,
        tmnxMcPeerSyncSdpSyncTag,
        tmnxMcPeerSyncSdpVcIdRowStatus,
        tmnxMcPeerSyncSdpVcIdSyncTag
    }
    STATUS      current
    DESCRIPTION
        "The group of objects supporting multi-chassis redundancy added in
         release 14.0 of the Nokia SROS."
    ::= { tmnxMcRedundancyGroups 30 }

tmnxMcNotifyObjsGroup            OBJECT-GROUP
    OBJECTS     {
        tmnxMcNotifyNumber,
        tMcPeerIPsecTnlGrpMasterStateChR
    }
    STATUS      current
    DESCRIPTION
        "A group of notification objects supporting multi-chassis redundancy on
         Nokia SROS series systems."
    ::= { tmnxMcRedundancyGroups 99 }

tmnxMcRedundancyNotifGroups      OBJECT IDENTIFIER ::= { tmnxMcRedundancyConformance 3 }

tmnxMcRedundancyV5v0NotifGroup   NOTIFICATION-GROUP
    NOTIFICATIONS {
        tmnxMcRedundancyPeerStateChanged,
        tmnxMcRedundancyMismatchDetected,
        tmnxMcRedundancyMismatchResolved,
        tmnxMcPeerSyncStatusChanged,
        tmnxMcSyncClientAlarmRaised,
        tmnxMcSyncClientAlarmCleared,
        tmnxSrrpSubnetMismatch,
        tmnxSrrpSubnetMismatchCleared,
        tmnxSrrpInstanceIdMismatch,
        tmnxSrrpSapMismatch,
        tmnxSrrpSapTagMismatch,
        tmnxSrrpRedIfMismatch,
        tmnxSrrpDualMaster,
        tmnxMcLagInfoLagChanged,
        tmnxSrrpSystemIpNotSet,
        tmnxMcSyncClockSkewRaised,
        tmnxMcSyncClockSkewCleared,
        tmnxSrrpDuplicateSubIfAddress
    }
    STATUS      current
    DESCRIPTION
        "The group of objects supporting multi-chassis redundancy on version
         5.0 of the Nokia SROS series systems."
    ::= { tmnxMcRedundancyNotifGroups 1 }

tmnxMcRingV6v0NotifGroup         NOTIFICATION-GROUP
    NOTIFICATIONS {
        tmnxMcRingOperStateChanged,
        tmnxMcRingInbCtrlOperStateChgd,
        tmnxMcRingNodeLocOperStateChgd,
        tmnxMcPeerRingsOperStateChanged
    }
    STATUS      current
    DESCRIPTION
        "The group of notifications supporting multi-chassis ring on version
         6.0 of the Nokia SROS series systems."
    ::= { tmnxMcRedundancyNotifGroups 2 }

tmnxMcRedundancySrrpNotifGroup   NOTIFICATION-GROUP
    NOTIFICATIONS {
        tmnxSrrpTrapNewMaster,
        tmnxSrrpBecameBackup
    }
    STATUS      current
    DESCRIPTION
        "The group of notifications supporting multi-chassis redundancy on the
         Nokia SROS series systems."
    ::= { tmnxMcRedundancyNotifGroups 3 }

tmnxSrrpNotifV6v1Group           NOTIFICATION-GROUP
    NOTIFICATIONS {
        tmnxSrrpBfdIntfSessStateChgd
    }
    STATUS      current
    DESCRIPTION
        "The group of notifications supporting multi-chassis redundancy SRRP on
         the Nokia SROS series systems."
    ::= { tmnxMcRedundancyNotifGroups 4 }

tmnxMcPeerEPV7v0NotifGroup       NOTIFICATION-GROUP
    NOTIFICATIONS {
        tmnxMCEPSessionPsvModeDisabled,
        tmnxMCEPSessionPsvModeEnabled,
        tmnxMcPeerEPBfdSessionClose,
        tmnxMcPeerEPBfdSessionOpen,
        tmnxMcPeerEPBfdSessionDown,
        tmnxMcPeerEPBfdSessionUp,
        tmnxMcPeerEPOperDown,
        tmnxMcPeerEPOperUp
    }
    STATUS      current
    DESCRIPTION
        "The group of notifications supporting multi-chassis endpoint on the
         Nokia SROS series systems."
    ::= { tmnxMcRedundancyNotifGroups 5 }

tmnxMcPeerV10v0NotifGroup        NOTIFICATION-GROUP
    NOTIFICATIONS {
        tMcPeerIPsecTnlGrpProtStatusChg,
        tMcPeerIPsecTnlGrpMasterStateChg
    }
    STATUS      current
    DESCRIPTION
        "The group of notifications supporting multi-chassis redundancy
         features the Nokia SROS 11.0 series systems."
    ::= { tmnxMcRedundancyNotifGroups 6 }

tmnxMcOmcrNotifGroup             NOTIFICATION-GROUP
    NOTIFICATIONS {
        tmnxMcOmcrStatFailedChanged,
        tmnxMcOmcrClientNumEntriesHigh
    }
    STATUS      current
    DESCRIPTION
        "The group of notifications supporting multi-chassis redundancy OMCR
         for the Nokia SROS series systems."
    ::= { tmnxMcRedundancyNotifGroups 7 }

tmnxSrrpNotificationV10v0Group   NOTIFICATION-GROUP
    NOTIFICATIONS {
        tmnxSrrpOperDownInvalidMac,
        tmnxSrrpOperDownInvalidMacClear
    }
    STATUS      current
    DESCRIPTION
        "The group of notifications supporting the extended SRRP feature on
         Nokia SROS series systems for 10.0 release."
    ::= { tmnxMcRedundancyNotifGroups 8 }

tmnxMcMobRedundancyCompliances   OBJECT IDENTIFIER ::= { tmnxMcRedundancyConformance 4 }

tmnxMcMobRedundancyGroups        OBJECT IDENTIFIER ::= { tmnxMcRedundancyConformance 5 }

tmnxMcMobRedundancyV4v0Group     OBJECT-GROUP
    OBJECTS     {
        tmnxMcPeerMobileMGRefPtPktCnt,
        tmnxMcPeerMobileMGRole,
        tmnxMcPeerMobileMGRefPtTrigger,
        tmnxMcPeerMobileBFDEnable,
        tmnxMcPeerMobileRouteAdvHoldTmr,
        tmnxMcPeerMobileHoldOnNbrFail,
        tmnxMcPeerMobileKeepAlvIntvl,
        tmnxMcPeerMobileHoldDownTmr,
        tmnxMcPeerMobileMGRefPtRowStatus,
        tmnxMcPeerMobileMGRowStatus,
        tmnxMcPeerMobileRowStatus,
        tmnxMcPeerSyncMobile,
        tmnxMcPeerMobileTableLstChgd,
        tmnxMcPeerMobileMGTableLstChgd,
        tmnxMcPeerMobMGRefPtTableLstChgd,
        tmnxMcPeerMobileAdminState,
        tmnxMcPeerMobileMGAdminState,
        tmnxMcPeerMobileLastChanged,
        tmnxMcPeerMobileMGLastChanged,
        tmnxMcPeerMobileMGRefPtLastChngd,
        tmnxMcPeerMobileMtu
    }
    STATUS      current
    DESCRIPTION
        "The group of objects supporting multi-chassis redundancy on version
         4.0 of the Nokia mobile-gateway system."
    ::= { tmnxMcMobRedundancyGroups 1 }

tmnxMcMobRedundancyNotifyGroups  OBJECT IDENTIFIER ::= { tmnxMcRedundancyConformance 6 }

tmnxMcRedundancyNotifyPrefix     OBJECT IDENTIFIER ::= { tmnxSRNotifyPrefix 40 }

tmnxMcRedundancyNotifications    OBJECT IDENTIFIER ::= { tmnxMcRedundancyNotifyPrefix 0 }

tmnxMcRedundancyPeerStateChanged NOTIFICATION-TYPE
    OBJECTS     {
        tmnxMcLagConfigOperState
    }
    STATUS      current
    DESCRIPTION
        "The notification tmnxMcRedundancyPeerStateChanged is sent when the
         connection to a specific peer is lost or established."
    ::= { tmnxMcRedundancyNotifications 1 }

tmnxMcRedundancyMismatchDetected NOTIFICATION-TYPE
    OBJECTS     {
        tmnxMcLagConfigMismatchString
    }
    STATUS      current
    DESCRIPTION
        "The notification tmnxMcRedundancyMismatchDetected is sent when a
         configuration mismatch is detected."
    ::= { tmnxMcRedundancyNotifications 2 }

tmnxMcRedundancyMismatchResolved NOTIFICATION-TYPE
    OBJECTS     {
        tmnxMcLagConfigMismatchString
    }
    STATUS      current
    DESCRIPTION
        "The notification tmnxMcRedundancyMismatchResolved is sent when all
         configuration mismatches are resolved."
    ::= { tmnxMcRedundancyNotifications 3 }

tmnxMcPeerSyncStatusChanged      NOTIFICATION-TYPE
    OBJECTS     {
        tmnxMcPeerSyncStatus
    }
    STATUS      current
    DESCRIPTION
        "The notification tmnxMcPeerSyncStatusChanged is generated when the
         status of the synchronization with the multi-chassis peer changes."
    ::= { tmnxMcRedundancyNotifications 4 }

tmnxMcSyncClientAlarmRaised      NOTIFICATION-TYPE
    OBJECTS     {
        tmnxMcPeerIpAddrTypeForNotify,
        tmnxMcPeerIpAddrForNotify,
        tmnxMcPeerSyncClient
    }
    STATUS      current
    DESCRIPTION
        "The notification tmnxMcSyncClientAlarmRaised is generated when a
         multi-chassis sync client has at least one locally deleted entry in
         the database."
    ::= { tmnxMcRedundancyNotifications 5 }

tmnxMcSyncClientAlarmCleared     NOTIFICATION-TYPE
    OBJECTS     {
        tmnxMcPeerIpAddrTypeForNotify,
        tmnxMcPeerIpAddrForNotify,
        tmnxMcPeerSyncClient
    }
    STATUS      current
    DESCRIPTION
        "The notification tmnxMcSyncClientAlarmCleared is generated when a
         multi-chassis sync client has no locally deleted entries in the
         database."
    ::= { tmnxMcRedundancyNotifications 6 }

tmnxSrrpSubnetMismatch           NOTIFICATION-TYPE
    OBJECTS     {
        tmnxSrrpOperFlags,
        tmnxMcPeerSrcIpType,
        tmnxMcPeerSrcIpAddr,
        tmnxMcPeerIpAddrTypeForNotify,
        tmnxMcPeerIpAddrForNotify
    }
    STATUS      current
    DESCRIPTION
        "The notification tmnxSrrpSubnetMismatch is generated when the IP
         address list received through SRRP-MCS synchronization received from
         the current master does not match the local configured IP address
         list.

         This is an edge triggered notification. A second notification will not
         be generated for a packet from the same master until this event has
         been cleared."
    ::= { tmnxMcRedundancyNotifications 7 }

tmnxSrrpSubnetMismatchCleared    NOTIFICATION-TYPE
    OBJECTS     {
        tmnxSrrpOperFlags,
        tmnxMcPeerSrcIpType,
        tmnxMcPeerSrcIpAddr,
        tmnxMcPeerIpAddrTypeForNotify,
        tmnxMcPeerIpAddrForNotify
    }
    STATUS      current
    DESCRIPTION
        "The notification tmnxSrrpSubnetMismatchCleared is generated when the
         mismatch in the IP address list received through SRRP-MCS
         synchronization received from the current master is cleared."
    ::= { tmnxMcRedundancyNotifications 8 }

tmnxSrrpInstanceIdMismatch       NOTIFICATION-TYPE
    OBJECTS     {
        tmnxSrrpOperFlags,
        tmnxMcPeerSrcIpType,
        tmnxMcPeerSrcIpAddr,
        tmnxMcPeerIpAddrTypeForNotify,
        tmnxMcPeerIpAddrForNotify
    }
    STATUS      current
    DESCRIPTION
        "[CAUSE] The notification tmnxSrrpInstanceIdMismatch is generated when
         an SRRP instance has detected that at least one SAP it is protecting
         is associated with a different SRRP instance on the remote peer.

         [EFFECT] One or more SAPs are not protected by SRRP.

         [RECOVERY] Verify configuration on the local and remote end routers to
         ensure that all SAPs are associated with the same SRRP instance on
         both sides."
    ::= { tmnxMcRedundancyNotifications 9 }

tmnxSrrpSapMismatch              NOTIFICATION-TYPE
    OBJECTS     {
        tmnxSrrpOperFlags,
        tmnxMcRemoteGrpIfNameForNotify
    }
    STATUS      current
    DESCRIPTION
        "The notification tmnxSrrpSapMismatch is generated when the SAPs SRRP
         is backing up on the local interface do not match with the ones on the
         remote interface."
    ::= { tmnxMcRedundancyNotifications 10 }

tmnxSrrpSapTagMismatch           NOTIFICATION-TYPE
    OBJECTS     {
        tmnxSrrpOperFlags,
        tmnxMcPeerSyncPortEncapSyncTag,
        tmnxMcRemoteGrpIfNameForNotify,
        tmnxMcRemoteSyncTag
    }
    STATUS      current
    DESCRIPTION
        "The notification tmnxSrrpSapTagMismatch is generated when the tag for
         a local SAP do not match those of the remote SAP."
    ::= { tmnxMcRedundancyNotifications 11 }

tmnxSrrpRedIfMismatch            NOTIFICATION-TYPE
    OBJECTS     {
        tmnxSrrpOperFlags,
        tmnxMcPeerSrcIpType,
        tmnxMcPeerSrcIpAddr,
        tmnxMcPeerIpAddrTypeForNotify,
        tmnxMcPeerIpAddrForNotify,
        tmnxMcRemoteGrpIfNameForNotify,
        tmnxMcRemoteRedIfNameForNotify
    }
    STATUS      current
    DESCRIPTION
        "The notification tmnxSrrpRedIfMismatch is generated when the local and
         remote redundant interfaces are not properly paired."
    ::= { tmnxMcRedundancyNotifications 12 }

tmnxSrrpDualMaster               NOTIFICATION-TYPE
    OBJECTS     {
        tmnxSrrpOperFlags,
        tmnxMcPeerSrcIpType,
        tmnxMcPeerSrcIpAddr,
        tmnxMcPeerIpAddrTypeForNotify,
        tmnxMcPeerIpAddrForNotify,
        tmnxMcRemoteGrpIfNameForNotify
    }
    STATUS      current
    DESCRIPTION
        "The notification tmnxSrrpDualMaster is generated when both the local
         and remote SRRP instances are in the master state."
    ::= { tmnxMcRedundancyNotifications 13 }

tmnxMcLagInfoLagChanged          NOTIFICATION-TYPE
    OBJECTS     {
        tmnxMcPeerIpAddrTypeForNotify,
        tmnxMcPeerIpAddrForNotify,
        tmnxMcLagConfigLagIds
    }
    STATUS      current
    DESCRIPTION
        "The notification tmnxMcLagInfoLagChanged is generated when entries in
         tmnxMcLagInfoLagTable were changed."
    ::= { tmnxMcRedundancyNotifications 14 }

tmnxSrrpSystemIpNotSet           NOTIFICATION-TYPE
    STATUS      current
    DESCRIPTION
        "The notification tmnxSrrpSystemIpNotSet is generated when SRRP tries
         to send out advertisement packets but the system IP address has not
         yet been set."
    ::= { tmnxMcRedundancyNotifications 15 }

tmnxMcRingOperStateChanged       NOTIFICATION-TYPE
    OBJECTS     {
        tmnxMcRingInfoOperState
    }
    STATUS      current
    DESCRIPTION
        "The notification tmnxMcRingOperStateChanged is generated when the
         operational state of a multi-chassis ring changes."
    ::= { tmnxMcRedundancyNotifications 16 }

tmnxMcRingInbCtrlOperStateChgd   NOTIFICATION-TYPE
    OBJECTS     {
        tmnxMcRingInfoInbCtrlOperState
    }
    STATUS      current
    DESCRIPTION
        "The notification tmnxMcRingInbCtrlOperStateChgd is generated when the
         operational state of a multi-chassis ring's inband control connection
         changes."
    ::= { tmnxMcRedundancyNotifications 17 }

tmnxMcRingNodeLocOperStateChgd   NOTIFICATION-TYPE
    OBJECTS     {
        tmnxMcRingNodeInfoLocOperState,
        tmnxMcRingNodeInfoInUse
    }
    STATUS      current
    DESCRIPTION
        "The notification tmnxMcRingNodeLocOperStateChgd is generated upon a
         change of the operational state of a provisioned ring node as
         monitored by the local chassis, or when an unprovisioned ring node
         appears or disappears."
    ::= { tmnxMcRedundancyNotifications 18 }

tmnxMcSyncClockSkewRaised        NOTIFICATION-TYPE
    OBJECTS     {
        tmnxMcPeerIpAddrTypeForNotify,
        tmnxMcPeerIpAddrForNotify,
        tmnxMcPeerClockSkew
    }
    STATUS      current
    DESCRIPTION
        "The notification tmnxMcSyncClockSkewRaised is generated when the MCS
         peer system clock time is greater than 60 seconds different than the
         local system clock."
    ::= { tmnxMcRedundancyNotifications 19 }

tmnxMcSyncClockSkewCleared       NOTIFICATION-TYPE
    OBJECTS     {
        tmnxMcPeerIpAddrTypeForNotify,
        tmnxMcPeerIpAddrForNotify,
        tmnxMcPeerClockSkew
    }
    STATUS      current
    DESCRIPTION
        "The notification tmnxMcSyncClockSkewCleared is generated when the MCS
         peer system clock time has returned to less than 60 seconds different
         than the local system clock.

         This notification would only be generated following a
         tmnxMcSyncClockSkewRaised notification."
    ::= { tmnxMcRedundancyNotifications 20 }

tmnxSrrpDuplicateSubIfAddress    NOTIFICATION-TYPE
    OBJECTS     {
        tmnxSrrpOperFlags,
        tmnxMcPeerSrcIpType,
        tmnxMcPeerSrcIpAddr,
        tmnxMcPeerIpAddrTypeForNotify,
        tmnxMcPeerIpAddrForNotify
    }
    STATUS      current
    DESCRIPTION
        "The notification tmnxSrrpDuplicateSubIfAddress is generated when the
         IP address for a local subscriber interface conflicts with the IP
         address for a remote subscriber interface."
    ::= { tmnxMcRedundancyNotifications 21 }

tmnxMcPeerRingsOperStateChanged  NOTIFICATION-TYPE
    OBJECTS     {
        tmnxMcPeerRingsOperState
    }
    STATUS      current
    DESCRIPTION
        "The notification tmnxMcPeerRingsOperStateChanged is sent when the
         operational state - with respect to multi-chassis ring operation - of
         a peer changes."
    ::= { tmnxMcRedundancyNotifications 22 }

tmnxSrrpTrapNewMaster            NOTIFICATION-TYPE
    OBJECTS     {
        tmnxSrrpOperFlags,
        tmnxMcPeerIpAddrTypeForNotify,
        tmnxMcPeerIpAddrForNotify
    }
    STATUS      current
    DESCRIPTION
        "The tmnxSrrpTrapNewMaster trap indicates that the sending
         multi-chassis SRRP instance has transitioned to 'Master' state."
    ::= { tmnxMcRedundancyNotifications 23 }

tmnxSrrpBecameBackup             NOTIFICATION-TYPE
    OBJECTS     {
        tmnxSrrpOperFlags,
        tmnxMcPeerIpAddrTypeForNotify,
        tmnxMcPeerIpAddrForNotify
    }
    STATUS      current
    DESCRIPTION
        "The tmnxSrrpBecameBackup trap is generated when the sending
         multi-chassis SRRP instance has transitioned to 'Backup' state."
    ::= { tmnxMcRedundancyNotifications 24 }

tmnxSrrpBfdIntfSessStateChgd     NOTIFICATION-TYPE
    OBJECTS     {
        tmnxSrrpNotifBfdIntfSvcId,
        tmnxSrrpNotifBfdIntfIfName,
        tmnxSrrpNotifBfdIntfDestIpType,
        tmnxSrrpNotifBfdIntfDestIp,
        tmnxSrrpNotifBfdIntfSessState
    }
    STATUS      current
    DESCRIPTION
        "The notification tmnxSrrpBfdIntfSessStateChgd is generated when the
         operational state of BFD session of the SRRP instance changes."
    ::= { tmnxMcRedundancyNotifications 25 }

tmnxMcPeerEPBfdSessionOpen       NOTIFICATION-TYPE
    OBJECTS     {
        tmnxMcPeerSrcIpAddr,
        tmnxMcPeerEPBfdSessionOpenStatus
    }
    STATUS      current
    DESCRIPTION
        "The tmnxMcPeerEPBfdSessionOpen notification is generated when the
         multi-chassis endpoint is attempting to open BFD session to the
         multi-chassis endpoint peer."
    ::= { tmnxMcRedundancyNotifications 26 }

tmnxMcPeerEPBfdSessionClose      NOTIFICATION-TYPE
    OBJECTS     {
        tmnxMcPeerSrcIpAddr
    }
    STATUS      current
    DESCRIPTION
        "The tmnxMcPeerEPBfdSessionClose notification is generated when the
         multi-chassis endpoint is closing BFD session to the multi-chassis
         endpoint peer."
    ::= { tmnxMcRedundancyNotifications 27 }

tmnxMcPeerEPBfdSessionUp         NOTIFICATION-TYPE
    OBJECTS     {
        tmnxMcPeerSrcIpAddr
    }
    STATUS      current
    DESCRIPTION
        "The tmnxMcPeerEPBfdSessionUp notification is generated when
         operational state of the BFD session between the multi-chassis
         endpoint and its peer is changed to 'up'."
    ::= { tmnxMcRedundancyNotifications 28 }

tmnxMcPeerEPBfdSessionDown       NOTIFICATION-TYPE
    OBJECTS     {
        tmnxMcPeerSrcIpAddr
    }
    STATUS      current
    DESCRIPTION
        "The tmnxMcPeerEPBfdSessionDown notification is generated when
         operational state of the BFD session between the multi-chassis
         endpoint and its peer is changed to 'down'."
    ::= { tmnxMcRedundancyNotifications 29 }

tmnxMcPeerEPOperDown             NOTIFICATION-TYPE
    OBJECTS     {
        tmnxMcPeerSrcIpAddr
    }
    STATUS      current
    DESCRIPTION
        "The tmnxMcPeerEPOperDown notification is generated when the
         multi-chassis endpoint detects time-out communicating with the
         multi-chassis endpoint peer."
    ::= { tmnxMcRedundancyNotifications 30 }

tmnxMcPeerEPOperUp               NOTIFICATION-TYPE
    OBJECTS     {
        tmnxMcPeerSrcIpAddr
    }
    STATUS      current
    DESCRIPTION
        "The tmnxMcPeerEPOperUp notification is generated when the
         multi-chassis endpoint clears time-out condition in communicating with
         the multi-chassis endpoint peer."
    ::= { tmnxMcRedundancyNotifications 31 }

tmnxMCEPSessionPsvModeEnabled    NOTIFICATION-TYPE
    OBJECTS     {
        tmnxMcPeerSrcIpAddr,
        tmnxMcPeerEPPassiveMode,
        tmnxMcPeerEPPsvModeConfigState
    }
    STATUS      current
    DESCRIPTION
        "The notification tmnxMCEPSessionPsvModeEnabled is generated when
         passive-mode for the session between the multi-chassis endpoint and
         its peer is 'enabled' from either local or peer endpoint."
    ::= { tmnxMcRedundancyNotifications 32 }

tmnxMCEPSessionPsvModeDisabled   NOTIFICATION-TYPE
    OBJECTS     {
        tmnxMcPeerSrcIpAddr,
        tmnxMcPeerEPPassiveMode
    }
    STATUS      current
    DESCRIPTION
        "The notification tmnxMCEPSessionPsvModeDisabled is generated when
         passive-mode for the session between the multi-chassis endpoint and
         its peer is 'disabled' from both local and peer."
    ::= { tmnxMcRedundancyNotifications 33 }

tMcPeerIPsecTnlGrpMasterStateChg NOTIFICATION-TYPE
    OBJECTS     {
        tMcPeerIPsecTnlGrpMasterState,
        tMcPeerIPsecTnlGrpMasterStateOld,
        tMcPeerIPsecTnlGrpMasterStateChR
    }
    STATUS      current
    DESCRIPTION
        "[CAUSE] The notification tMcPeerIPsecTnlGrpMasterStateChg is generated
         whenever mastership election state of a tunnel-group changes.

         [EFFECT] This notification is informational. The effects associated
         with this notification depend upon the new state of the tunnel-group.

         For example, when a tunnel-group becomes master it will begin
         attracting traffic towards its chassis and will begin to manage IKE
         sessions for all IPsec tunnels in that tunnel-group.

         [RECOVERY] No recovery actions are required, although unexpected state
         transitions often indicate causal fault conditions which may require
         investigation."
    ::= { tmnxMcRedundancyNotifications 34 }

tMcPeerIPsecTnlGrpProtStatusChg  NOTIFICATION-TYPE
    OBJECTS     {
        tMcPeerIPsecTnlGrpProtectStatus
    }
    STATUS      current
    DESCRIPTION
        "[CAUSE] The notification tMcPeerIPsecTnlGrpProtStatusChg is generated
         whenever protection status of a tunnel-group changes.

         [EFFECT] This notification is informational. A change in
         tMcPeerIPsecTnlGrpProtectStatus to 'nominal' indicates protection
         status readiness for switchover.

         [RECOVERY] No recovery actions are required."
    ::= { tmnxMcRedundancyNotifications 35 }

tmnxMcOmcrStatFailedChanged      NOTIFICATION-TYPE
    OBJECTS     {
        tmnxMcOmcrStatFailed,
        tmnxMcOmcrStatFailure
    }
    STATUS      current
    DESCRIPTION
        "[CAUSE] The notification tmnxMcOmcrStatFailedChanged is generated when
         the value of the object tmnxMcOmcrStatFailed changes.

         The most interesting change is from 'notAct' to any of the other
         values; when an OMCR client application access protection instance
         (for example an SRRP instance) becomes active, the system will attempt
         to allocate resources for all associated client application entries
         (for example IPOE subscriber hosts); if this succeeds, the value of
         tmnxMcOmcrStatFailed becomes 'no', if it fails, it becomes 'yes'.

         [EFFECT] A transition from 'notAct' or 'no' to 'yes' means that the
         traffic of some or all associated client application entries' is being
         dropped. For example, all traffic from some or all of the IPOE
         subscriber hosts protected by a failed SRRP instance is dropped by
         this system.

         A transition to 'no' means that the system has successfully allocated
         resources for the traffic of all associated client application
         entries.

         A transition to 'notAct' means that this system is not performing the
         active role anymore for this access protection instance. For example,
         the value of the object tmnxSrrpOperState has become different from
         'master' for the corresponding instance.

         [RECOVERY] There are three recovery actions possible, depending on the
         reason of the transition of the access protection instance.

         If it is caused by a problem in the access network, fix that problem,
         or make additional resources available for this access protection
         instance.

         If it is caused by a misconfiguration of this system, correct that, or
         make additional resources available for this access protection
         instance."
    ::= { tmnxMcRedundancyNotifications 37 }

tmnxMcOmcrClientNumEntriesHigh   NOTIFICATION-TYPE
    OBJECTS     {
        tmnxMcsClientNumEntries,
        tmnxMcNotifyNumber
    }
    STATUS      current
    DESCRIPTION
        "[CAUSE] The notification tmnxMcOmcrClientNumEntriesHigh is generated
         when the this system is configured as an OMCR warm standby system, and
         the total number of entries in the MCS database for a particular
         application becomes high.

         This system is configured as a warm standby system as soon as the
         value of the object tmnxMcPeerWarmStandby is equal to 'true' for any
         multi-chassis peer in this system.

         The total number of entries is the sum of the values of the object
         tmnxMcsClientNumEntries for the client application specified by
         tmnxMcsClientApplication.

         The maximum number of entries for a client application is equal to
         786432. The value of tmnxMcNotifyNumber indicates the ratio in percent
         of the total number of entries and the maximum number of entries. The
         threshold ratios are at 80%, 90% and 100%.

         The values of tmnxMcPeerIpType and tmnxMcPeerIpAddr indicate the peer
         that reached the threshold.

         [EFFECT] When the 80% and 90% threshold is crossed, there is no
         effect. When the 100% threshold is exceeded, the peer indicated by the
         values of tmnxMcPeerIpType and tmnxMcPeerIpAddr is shut down
         automatically by this system (the value of tmnxMcPeerSyncAdminState is
         set to 'outOfService' and the value of tmnxMcPeerSyncOperFlags is set
         to 'omcrNumEntriesHigh').

         [RECOVERY] Reconfigure the oversubscribed multi-chassis redundancy
         set-up to reduce the number of entries protected by this system.

         When the total number of entries in the MCS database for this client
         application becomes lower than the 80% threshold again, there is no
         further notification."
    ::= { tmnxMcRedundancyNotifications 38 }

tmnxSrrpOperDownInvalidMac       NOTIFICATION-TYPE
    OBJECTS     {
        tmnxSrrpOperState
    }
    STATUS      current
    DESCRIPTION
        "[CAUSE] tmnxSrrpOperDownInvalidMac is generated when the operational
         virtual MAC of an SRRP instance conflicts with the MAC of the parent
         interface.

         [EFFECT] The SRRP virtual router instance is not allowed to become
         operationally 'up'.

         [RECOVERY] There is no recovery required for this notification."
    ::= { tmnxMcRedundancyNotifications 39 }

tmnxSrrpOperDownInvalidMacClear  NOTIFICATION-TYPE
    OBJECTS     {
        tmnxSrrpOperState
    }
    STATUS      current
    DESCRIPTION
        "[CAUSE] The tmnxSrrpOperDownInvalidMacClear is generated when a
         previously occurring tmnxSrrpOperDownInvalidMac notification has been
         cleared. Operational virtual MAC of an IPv4 SRRP instance does not
         have any conflict with the MAC of the parent interface.

         [EFFECT] The SRRP virtual router instance is allowed to become
         operationally 'up'.

         [RECOVERY] There is no recovery required for this notification."
    ::= { tmnxMcRedundancyNotifications 40 }

tmnxMcMobRedundancyNotifications OBJECT IDENTIFIER ::= { tmnxMcRedundancyNotifyPrefix 1 }

END
