TIMETRA-OAM-TEST-MIB DEFINITIONS ::= BEGIN

IMPORTS
    AtmVcIdentifier, AtmVpIdentifier
                                                         FROM ATM-TC-MIB
    Dot1agCfmMepIdOrZero
                                                         FROM IEEE8021-CFM-MIB
    InterfaceIndex, InterfaceIndexOrZero
                                                         FROM IF-MIB
    InetAddress, InetAddressPrefixLength,
    InetAddressType, InetPortNumber
                                                         FROM INET-ADDRESS-MIB
    MplsLabel
                                                         FROM MPLS-LDP-MIB
    RouterID
                                                         FROM OSPF-MIB
    SnmpAdminString
                                                         FROM SNMP-FRAMEWORK-MIB
    MODULE-COMPLIANCE, NOTIFICATION-GROUP,
    OBJECT-GROUP
                                                         FROM SNMPv2-CONF
    Counter32, Counter64, Gauge32,
    Integer32, IpAddress, MODULE-IDENTITY,
    NOTIFICATION-TYPE, OBJECT-TYPE,
    Unsigned32
                                                         FROM SNMPv2-SMI
    DateAndTime, DisplayString, MacAddress,
    RowStatus, StorageType,
    TEXTUAL-CONVENTION, TimeStamp,
    TruthValue
                                                         FROM SNMPv2-TC
    timetraSRMIBModules, tmnxSRConfs,
    tmnxSRNotifyPrefix, tmnxSRObjs
                                                         FROM TIMETRA-GLOBAL-MIB
    SdpBindVcType, SdpId
                                                         FROM TIMETRA-SERV-MIB
    TmnxMobGwId
                                                         FROM TIMETRA-TC-MG-MIB
    IpAddressPrefixLength, SdpBindId,
    TFCName, TItemDescription,
    TLNamedItemOrEmpty, TNamedItem,
    TNamedItemOrEmpty,
    TPolicyStatementNameOrEmpty, TProfile,
    TmnxAdminState, TmnxBfdOnLspSessFecType,
    TmnxBgpRouteTarget, TmnxEncapVal,
    TmnxIgpInstance, TmnxMplsTpGlobalID,
    TmnxMplsTpNodeID, TmnxPortID,
    TmnxPwGlobalIdOrZero, TmnxServId,
    TmnxSpokeSdpIdOrZero, TmnxStrSapId,
    TmnxTunnelID, TmnxTunnelType,
    TmnxVPNRouteDistinguisher, TmnxVRtrID,
    TmnxVcId, TmnxVcIdOrNone
                                                         FROM TIMETRA-TC-MIB
    vRtrID
                                                         FROM TIMETRA-VRTR-MIB
    ;

timetraOamTestMIBModule          MODULE-IDENTITY
    LAST-UPDATED "201701010000Z"
    ORGANIZATION "Nokia"
    CONTACT-INFO
        "Nokia SROS Support
         Web: http://www.nokia.com"
    DESCRIPTION
        "This document is the SNMP MIB module to manage and provision the Nokia
         SROS OAM tests.

         Copyright 2003-2017 Nokia.  All rights reserved.
         Reproduction of this document is authorized on the condition that
         the foregoing copyright notice is included.

         This SNMP MIB module (Specification) embodies Nokia's
         proprietary intellectual property.  Nokia retains
         all title and ownership in the Specification, including any
         revisions.

         Nokia grants all interested parties a non-exclusive license to use and
         distribute an unmodified copy of this Specification in connection with
         management of Nokia products, and without fee, provided this copyright
         notice and license appear on all copies.

         This Specification is supplied 'as is', and Nokia makes no warranty,
         either express or implied, as to the use, operation, condition, or
         performance of the Specification."

    REVISION    "201701010000Z"
    DESCRIPTION
        "Rev 15.0               1 Jan 2017 00:00
         15.0 release of the TIMETRA-OAM-TEST-MIB."

    REVISION    "201601010000Z"
    DESCRIPTION
        "Rev 14.0               1 Jan 2016 00:00
         14.0 release of the TIMETRA-OAM-TEST-MIB."

    REVISION    "201501010000Z"
    DESCRIPTION
        "Rev 13.0               1 Jan 2015 00:00
         13.0 release of the TIMETRA-OAM-TEST-MIB."

    REVISION    "201401010000Z"
    DESCRIPTION
        "Rev 12.0               1 Jan 2014 00:00
         12.0 release of the TIMETRA-OAM-TEST-MIB."

    REVISION    "201102010000Z"
    DESCRIPTION
        "Rev 9.0                1 Feb 2011 00:00
         9.0 release of the TIMETRA-OAM-TEST-MIB."

    REVISION    "200902280000Z"
    DESCRIPTION
        "Rev 7.0                28 Feb 2009 00:00
         7.0 release of the TIMETRA-OAM-TEST-MIB."

    REVISION    "200801010000Z"
    DESCRIPTION
        "Rev 6.0                01 Jan 2008 00:00
         6.0 release of the TIMETRA-OAM-TEST-MIB."

    REVISION    "200701010000Z"
    DESCRIPTION
        "Rev 5.0                01 Jan 2007 00:00
         5.0 release of the TIMETRA-OAM-TEST-MIB."

    REVISION    "200603090000Z"
    DESCRIPTION
        "Rev 4.0                09 Mar 2006 00:00
         4.0 release of the TIMETRA-OAM-TEST-MIB."

    REVISION    "200508310000Z"
    DESCRIPTION
        "Rev 3.0                31 Aug 2005 00:00
         3.0 release of the TIMETRA-OAM-TEST-MIB."

    REVISION    "200501240000Z"
    DESCRIPTION
        "Rev 2.1                24 Jan 2005 00:00
         2.1 release of the TIMETRA-OAM-TEST-MIB."

    REVISION    "200401150000Z"
    DESCRIPTION
        "Rev 2.0                15 Jan 2004 00:00
         2.0 release of the TIMETRA-OAM-TEST-MIB."

    REVISION    "200308150000Z"
    DESCRIPTION
        "Rev 1.2                15 Aug 2003 00:00
         1.2 release of the TIMETRA-OAM-TEST-MIB."

    REVISION    "200301200000Z"
    DESCRIPTION
        "Rev 1.0                20 Jan 2003 00:00
         1.0 Release of the TIMETRA-OAM-TEST-MIB."

    REVISION    "200111150000Z"
    DESCRIPTION
        "Rev 0.1                15 Nov 2001 00:00
         Initial version of the TIMETRA-OAM-TEST-MIB."

    ::= { timetraSRMIBModules 11 }

TmnxOamLspAssocChannel           ::= TEXTUAL-CONVENTION
    STATUS      current
    DESCRIPTION
        "A value of type TmnxOamLspAssocChannel specifies the launched echo
         request's usage of the Associated Channel (ACH) mechanism, when
         testing an MPLS-TP LSP.

         Values:
            notApplicable(1)
                Used when the test is not testing an MPLS-TP LSP.
            nonIp(2)
                Use the Associated Channel mechanism described in RFC 6426,
                Section 3.3.
            none(3)
                Do not use an Associated Channel, as described in RFC 6426,
                Section 3.1.
            ipv4(4)
                Use the Associated Channel mechanism described in RFC 6426,
                Section 3.2."
    REFERENCE
        "RFC 6426, 'MPLS On-Demand Connectivity Verification and Route Tracing',
         Section 3.1, 'LSP Ping with IP Encapsulation',
         Section 3.2, 'On-Demand CV with IP Encapsulation, over ACH',
         Section 3.3, 'Non-IP-Based On-Demand CV, Using ACH'."
    SYNTAX      INTEGER {
        notApplicable (1),
        nonIp         (2),
        none          (3),
        ipv4          (4)
    }

TmnxOamLspTestSubMode            ::= TEXTUAL-CONVENTION
    STATUS      current
    DESCRIPTION
        "A value of type TmnxOamLspTestSubMode specifies the type of LSP ping
         or LSP trace route test to perform.

         LSP test types:
             static(2)
                 Perform an LSP ping or LSP trace route test using the RFC 6426
                 'Target FEC Stack' code point 'Static LSP'.
             bgpLabeledPrefix(3)
                 Perform an LSP ping or LSP trace route test using the RFC 4379
                 'Target FEC Stack' code point 'BGP labeled IPv4 prefix'.  In
                 future, 'bgpLabeledPrefix(3)' will also be used for the RFC
                 4379 'Target FEC Stack' code point 'BGP labeled IPv6 prefix'.
             srIsis(4)
                 Perform an LSP ping or LSP trace route test in the Segment
                 Routing (SR) case, where the Interior Gateway Protocol (IGP)
                 is Intermediate System to Intermediate System (IS-IS).
             srOspf(5)
                 Perform an LSP ping or LSP trace route test in the Segment
                 Routing (SR) case, where the Interior Gateway Protocol (IGP)
                 is Open Shortest Path First (OSPF).
             srTe(6)
                 Perform an LSP ping or LSP trace route test in the Segment
                 Routing Traffic Engineering (SR-TE) case.
             unspecified(1)
                 Perform any other supported type of LSP ping or trace route
                 test.  Examples:  an LSP ping or trace route test using the RFC
                 4379 'Target FEC Stack' code point 'LDP IPv4 prefix'; an LSP
                 ping or trace route test using the RFC 4379 'Target FEC Stack'
                 code point 'RSVP IPv4 LSP'."
    REFERENCE
        "IETF draft-ietf-mpls-spring-lsp-ping-00, 'Label Switched Path (LSP)
         Ping/Trace for Segment Routing Networks Using MPLS Dataplane'.
         RFC 4379, 'Detecting Multi-Protocol Label Switched (MPLS) Data Plane
         Failures', Section 3.2 ('Target FEC Stack').
         RFC 6426, 'MPLS On-Demand Connectivity Verification and Route Tracing',
         Section 2.3.1 ('Static LSP Sub-TLV')."
    SYNTAX      INTEGER {
        unspecified      (1),
        static           (2),
        bgpLabeledPrefix (3),
        srIsis           (4),
        srOspf           (5),
        srTe             (6)
    }

TmnxOamMplsEchoDownMapTlv        ::= TEXTUAL-CONVENTION
    STATUS      current
    DESCRIPTION
        "An object of type TmnxOamMplsEchoDownMapTlv specifies the type of
         downstream mapping TLV in an MPLS echo request PDU.

         'dsmap(1)' specifies the Downstream Mapping TLV, as described in RFC
         4379, Section 3.3.

         'ddmap(2)' specifies the Downstream Detailed Mapping TLV, as described
         in RFC 6424, Section 3.3."
    REFERENCE
        "RFC 4379, 'Detecting Multi-Protocol Label Switched (MPLS) Data Plane
         Failures', Section 3.3 ('Downstream Mapping').
         RFC 6424, 'Mechanism for Performing Label Switched Path Ping (LSP Ping)
         over MPLS Tunnels', Section 3.3 ('Downstream Detailed Mapping TLV')."
    SYNTAX      INTEGER {
        dsmap (1),
        ddmap (2)
    }

TmnxOamMplsEchoDownMapTlvOrNone  ::= TEXTUAL-CONVENTION
    STATUS      current
    DESCRIPTION
        "An object of type TmnxOamMplsEchoDownMapTlvOrNone specifies the type
         of downstream mapping TLV in an MPLS echo request PDU (or no
         downstream mapping TLV).

         'dsmap(1)' specifies the Downstream Mapping TLV, as described in RFC
         4379, Section 3.3.

         'ddmap(2)' specifies the Downstream Detailed Mapping TLV, as described
         in RFC 6424, Section 3.3.
         'none(3)'  specifies none of the above TLVs."
    REFERENCE
        "RFC 4379, 'Detecting Multi-Protocol Label Switched (MPLS) Data Plane
         Failures', Section 3.3 ('Downstream Mapping').
         RFC 6424, 'Mechanism for Performing Label Switched Path Ping (LSP Ping)
         over MPLS Tunnels', Section 3.3 ('Downstream Detailed Mapping TLV')."
    SYNTAX      INTEGER {
        dsmap (1),
        ddmap (2),
        none  (3)
    }

TmnxOamMplsTpPathType            ::= TEXTUAL-CONVENTION
    STATUS      current
    DESCRIPTION
        "A value of type TmnxOamMplsTpPathType specifies the type of an MPLS-TP
         path to be tested.

         Path types:
            working(1) - test the primary path of the MPLS-TP LSP
            protect(2) - test the secondary path of the MPLS-TP LSP
            active(3)  - test the currently-active path of the MPLS-TP LSP"
    REFERENCE
        "RFC 5921, 'A Framework for MPLS in Transport Networks',
         Section 1.3.4, 'MPLS-TP Label Switched Path'."
    SYNTAX      INTEGER {
        working (1),
        protect (2),
        active  (3)
    }

TmnxOamTestMode                  ::= TEXTUAL-CONVENTION
    STATUS      current
    DESCRIPTION
        "The value of TmnxOamTestMode is an enumerated integer that indicates
         the type of OAM test."
    SYNTAX      INTEGER {
        notConfigured (0),
        ping          (1),
        traceroute    (2)
    }

TmnxOamPingRtnCode               ::= TEXTUAL-CONVENTION
    STATUS      current
    DESCRIPTION
        "The value of TmnxOamPingRtnCode is an enumerated integer that
         indicates the return code received in the OAM ping response common
         header.

         Code points:
            notApplicable       The return code has no significance in the
                                context of the test being conducted.
            fecEgress           Replying router is an egress for the Forwarding
                                Equivalence Class (FEC).
            fecNoMap            Replying router has no mapping for the FEC.
            notDownstream       Replying router is not one of the
                                downstream routers.
            downstream          Replying router is one of the downstream
                                routers and its mapping for this FEC on the
                                received interface is the given label.
            downstreamNotLabel  Replying router is one of the downstream
                                routers but its mapping for this FEC is not
                                the given label.
            downstreamNotMac    Replying router is one of the downstream
                                routers but it does not have the given MAC
                                address
            downstreamNotMacFlood   Replying router is one of the downstream
                                routers but it does not have the given MAC
                                address and is unable to flood the request.
            malformedEchoRequest    A malformed echo request was received.
            tlvNotUnderstood    One or more of the TLVs was not understood.
            downstreamNotInMfib Replying router is one of the downstream
                                routers but it does not have an MFIB entry
                                for the given source-group combination.
            downstreamMismatched    Downstream mapping mismatched.
            upstreamIfIdUnkn    Upstream interface index unknown.
            noMplsFwd           Label switched but no MPLS forwarding at
                                stack-depth.
            noLabelAtStackDepth No label entry at stack-depth.
            protoIntfMismatched Protocol not associated with interface at
                                FEC stack-depth.
            terminatedByOneLabel    Premature termination of ping due to
                                label stack shrinking to a single label.
            seeDDMapForRetCodeSubCode   See DDMap TLV for rc and sub-rc.
            fecStackChange      Label switched with FEC stack change."
    SYNTAX      INTEGER {
        notApplicable             (0),
        fecEgress                 (1),
        fecNoMap                  (2),
        notDownstream             (3),
        downstream                (4),
        downstreamNotLabel        (5),
        downstreamNotMac          (6),
        downstreamNotMacFlood     (7),
        malformedEchoRequest      (8),
        tlvNotUnderstood          (9),
        downstreamNotInMfib       (10),
        downstreamMismatched      (11),
        upstreamIfIdUnkn          (12),
        noMplsFwd                 (13),
        noLabelAtStackDepth       (14),
        protoIntfMismatched       (15),
        terminatedByOneLabel      (16),
        seeDDMapForRetCodeSubCode (17),
        fecStackChange            (18)
    }

TmnxOamAddressType               ::= TEXTUAL-CONVENTION
    STATUS      current
    DESCRIPTION
        "The value of TmnxOamAddressType is an enumerated integer that
         indicates the type of address used in OAM test requests and responses."
    SYNTAX      INTEGER {
        unknown          (0),
        ipv4Address      (1),
        ipv6Address      (2),
        macAddress       (3),
        sapId            (4),
        sdpId            (5),
        localCpu         (6),
        ipv4Unnumbered   (7),
        ipv6Unnumbered   (8),
        sdpBindId        (9),
        nonIp            (10),
        networkInterface (11)
    }

TmnxOamResponseStatus            ::= TEXTUAL-CONVENTION
    STATUS      current
    DESCRIPTION
        "An object of type TmnxOamResponseStatus indicates the status of an OAM
         Echo probe operation.

         responseReceived(1) - Operation completed successfully.
         unknown(2) - Operation failed due to unknown error.
         internalError(3) - An implementation detected an error in its own
            processing that caused an operation to fail.
         maxConcurrentLimitReached(4) - The maximum number of concurrent active
            operations would have been exceeded if the corresponding operation
            was allowed.
         requestTimedOut(5) - Operation failed to receive a valid reply within
            the time limit imposed on it.
         unknownOrigSdpId(6) - Invalid or non-existent originating SDP-ID.
         downOrigSdpId(7) - The originating SDP-ID is operationally down.
         requestTerminated(8) - The OAM ping test was terminated by the manager
            before reply or timeout.
         invalidOriginatorId(9) - The far-end replied with an invalid
            originator-ID error.
         invalidResponderId(10) - The far-end replied with an invalid
            responder-ID error.
         unknownRespSdpId(11) - The far-end replied with an invalid response
            SDP-ID error.
         downRespSdpId(12) - The far-end replied with down (admin or oper)
            response SDP-ID.
         invalidServiceId(13) - Invalid or non-existent originator Service-ID
            (svc-ping).
         invalidSdp(14) - Invalid or non-existent SDP for Service (svc-ping).
         downServiceSdp(15) - SDP for the Service is down.  (svc-ping).
         noServiceEgressLabel(16) - Non-existent Service egress label.
            (svc-ping).
         invalidHostAddress(17) - The IP address for a host has been determined
            to be invalid.  Examples of this are broadcast or multicast
            addresses. (svc-ping).
         invalidMacAddress(18) - The MAC address specified has been determined
            to be invalid. (macPing).
         invalidLspName(19) - The LSP name specified has been determined to be
            invalid. (lspPing).
         macIsLocal(20) - MAC Ping or Trace route not sent because the MAC
            address is on a local SAP or CPU. (MAC-Ping/MAC-TR).
         farEndUnreachable(21) - No route to the far end of the GRE SDP tunnel.
         downOriginatorId(22) - The ping originator is operationally down.
         downResponderId(23) - The ping responder is operationally down.
         changedResponderId(24) - The ping responder-ID is changed.
         downOrigSvcId(25) - Service on the originator side is operationally
            down. (svc-ping).
         downRespSvcId(26) - Service on the responder side is operationally
            down. (svc-ping).
         noServiceIngressLabel(27) - Non-existent service ingress label.
            (svc-ping).
         mismatchCustId(28) - Service customer ID mismatch between originator
            and responder. (svc-ping).
         mismatchSvcType(29) - Service type mismatch between originator and
            responder. (svc-ping).
         mismatchSvcMtu(30) - Service MTU mismatch between originator and
            responder. (svc-ping).
         mismatchSvcLabel(31) - Service label mismatch between originator and
            responder. (svc-ping).
         noSdpBoundToSvc(32) - No SDP bound to the service. (svc-ping).
         downOrigSdpBinding(33) - SDP binding is down on the Originator side.
            (sdp-ping).
         invalidLspPathName(34) - The LSP path name specified is invalid.
            (lsp-ping).
         noLspEndpointAddr(35) - No LSP Endpoint address. (lsp-ping).
         invalidLspId(36) - No active LSP path found. (lsp-ping).
         downLspPath(37) - LSP path is operationally down. (lsp-ping).
         invalidLspProtocol(38) - LSP Protocol is not supported or is invalid.
            (lsp-ping).
         invalidLspLabel(39) - LSP label is invalid. (lsp-ping).
         routeIsLocal(40) - The route is a local route. (vprn-ping).
         noRouteToDest(41) - There is no route to the destination.  (vprn-ping).
         localExtranetRoute(42) - The route is a local extranet route.
            (vprn-ping).
         srcIpInBgpVpnRoute(43) - The source IP belongs to a BGP-VPN route.
            (vprn-ping).
         srcIpInvalid(44) - The source IP is invalid or there is no route to the
            source. (vprn-ping)
         bgpDaemonBusy(45) - The BGP routing daemon is busy; vprn route target
            information is not retrievable. (vprn-trace)
         mcastNotEnabled(46) - Multicast is not enabled. Multicast trace cannot
            be initiated. (mtrace)
         mTraceNoSGFlow(47) - No (*,G)/(S,G) flow on the router. Multicast trace
            cannot be initiated. (mtrace)
         mTraceSysIpNotCfg(48) - System ip address not configured. It is used as
            the response address in the multicast trace query. (mtrace)
         noFwdEntryInMfib(49) - No forwarding entry could be found for the
            specified source and destination address in the MFIB.  (mfib-ping).
         dnsNameNotFound(50) -  The domain name specified in the DNS query does
            not exist.
         noSocket(51) - unable to get socket. (icmp-ping).
         socketOptVprnIdFail(52) - unable to set SO_VPRNID for socket.
            (icmp-ping).
         socketOptIfInexFail(53) -  unable to set IP_IFINDEX for socket.
            (icmp-ping).
         socketOptNextHopFail(54) - unable to set IP_NEXT_HOP for socket.
            (icmp-ping).
         socketOptMtuDiscFail(55) - unable to set IP_MTU_DISC for socket.
            (icmp-ping).
         socketOptSndbufFail(56) - unable to set SO_SNDBUF for socket.
            (icmp-ping).
         socketOptHdrincFail(57) - unable to set IP_HDRINCL for socket.
            (icmp-ping).
         socketOptTosFail(58) - unable to set IP_TOS for socket. (icmp-ping).
         socketOptTtlFail(59) - unable to set IP_TTL for socket. (icmp-ping).
         bindSocketFail(60) - unable to bind socket. (icmp-ping).
         noRouteByIntf(61) - no route to destination via the specified
            interface. (icmp-ping).
         noIntf(62) - no interface specified. (icmp-ping).
         noLocalIp(63) - unable to find local IP address. (icmp-ping).
         sendtoFail(64) - sendto function failed. (icmp-ping).
         rcvdWrongType(65) - received packet of wrong ICMP type. (icmp-ping).
         noDirectInterface(66) - no direct interface to reach destination.
            (icmp-ping).
         nexthopUnreachable (67) - unable to reach the next-hop. (icmp-ping).
         socketOptHwTimeStampFail (68) - unable to set IP_TIM_TIME for socket.
            (icmp-ping).
         noSpokeSdpInVll (69) - unable to find spoke-sdp given sdp-id:vc-id
            (vccv-ping).
         farEndVccvNotSupported (70) - far end does not support the VCCV
            options.  (vccv-ping).
         noVcEgressLabel (71) - no VC egress label to send vccv-ping.
         socketOptIpSessionFail (72) - unable to set IP_SESSION for socket.
            (icmp-ping).
         rcvdWrongSize(73) - received packet of wrong size. (icmp-ping).
         dnsLookupFail (74) - DNS lookup failed. (icmp-ping).
         noIpv6SrcAddrOnIntf (75) - no IPv6 source on the interface (icmp-ping).
         multipathNotSupported (76) - downstream node does not support
            multipath.  (lsp-trace).
         nhIntfNameNotFound (77) - Given next-hop interface name not found.
            (lsp-ping/trace).
         msPwInvalidReplyMode (78) - MS-PW switching node supports ip-routed
            reply mode only (vccv-ping).
         ancpNoAncpString (79) - ANCP string unknown to the system.
         ancpNoSubscriber (80) - subscriber unknown to the system.
         ancpNoAncpStringForSubscriber (81) - subscriber has no associated ANCP
            string.
         ancpNoAccessNodeforAncpString (82) - no access node is found for the
            given ANCP string.
         ancpNoAncpCapabilityNegotiated (83) - ANCP capability not negotiated
            with the involved DSLAM.
         ancpOtherTestInProgress (84) - another ANCP test is running for this
            ANCP string.
         ancpMaxNbrAncpTestsInProgress (85) - max number of concurrent ANCP
            tests reached.
         spokeSdpOperDown (86) - spoke-sdp is operationally down (vccv-ping).
         noMsPwVccvInReplyDir (87) - Switching node in MS-PW with no VCCV
            support in echo reply direction.
         p2mpLspNameOrInstInvalid (88) - P2MP LSP name or instance provided is
            not valid.
         p2mpLspS2LPathDown (89) - LSP path to S2L is down.
         p2mpLspS2LAddressInvalid (90) - One or more S2L address is not valid.
         p2mpLspNotOperational (91) - P2MP LSP is operationally down.
         p2mpLspTrMultipleReplies (92) - Probe returned multiple responses.
            Result may be inconsistent.
         invalidMepId (93) - The user-configured MEP identifier is not valid.
         multipleReplies (94) - more than one reply received, when one was
            expected.
         packetSizeTooBig (95) - The packet is larger than the network's MTU and
            cannot be fragmented. For ICMP-ping tests, this results from an
            ICMPv4 type 3 code 4 or ICMPv6 type 2 message.
         gtpPingError (96) - General GTP Ping Error.
         gtpPingRsrcUnavailable (97) - GTP Path management resource unavailable.
         gtpPingDupRequest (98) - Duplicate request for the same peer.
         gtpPingCleanUpInProg (99) - GTP Path management clean up in progress.
         invalidInterface (100) - The egress interface specified does not exist.
         p2mpLspNotFound (101) - The P2MP-LSP not found given LDP-ID or
            sender-address.
         ethCfmSlmInLoss(102) - Synthetic Loss Measurement (SLM) probe lost in
            transit from far-end node to local agent.
         ethCfmSlmOutLoss(103) - SLM probe lost on transmit from local agent to
            far-end node.
         ethCfmSlmUnacknowledged(104) - SLM probe lost but unable to identify
            loss reason.
         spokeSdpFecNoBndFound(105) - Spoke-sdp-fec is invalid or has no
            associated SDP binding yet.
         mtraceNotSupportedP2mp(106) - mtrace not supported in base routing
            context when incoming interface is p2mp
         useFec129Parameters(107) - specify FEC129 parameters for FEC129 PW
            instead of sdp-id:vc-id
         dnsServerUnexpectedResponse(108) - nameserver unexpected response.
         dnsServerResponseFormErr(109) - nameserver responded with FORMERR.
         dnsServerResponseServFail(110) - nameserver responded with SERVFAIL.
         dnsServerResponseNotImp(111) - nameserver responded with NOTIMP.
         dnsServerResponseRefused(112) - nameserver responded with REFUSED.
         sendFailUndefinedServiceId(113) - The OAM test cannot be performed
            because the associated service does not exist.
         sendFailWrongServiceType(114) - The OAM test cannot be performed
            because the associated service is of the wrong type.
         sendFailSubnettedService(115) - The OAM test cannot be performed
            on a service with a specified MAC subnet length.
         invalidRespServiceId(116) - Invalid or non-existent responder
            Service-ID.
         adminDownOrigSdpBind(117) - SDP binding is administratively down on the
            originator side.
         operDownRespSdpBind(118) - SDP binding is operationally down on the
            responder side.
         adminDownRespSdpBind(119) - SDP binding is administratively down on the
            responder side.
         sdpBindVcidMismatch(120) - SDP binding VC ID mismatch between
            originator and responder.
         sdpBindTypeMismatch(121) - SDP binding type mismatch between originator
            and responder.
         sdpBindVcTypeMismatch(122) - SDP binding VC type mismatch between
            originator and responder.
         sdpBindVlanVcTagMismatch(123) - SDP binding VLAN VC tag mismatch
            between originator and responder.
         adminDownOrigSvc(124) - Service on the originator side is
            administratively down.
         adminDownRespSvc(125) - Service on the responder side is
            administratively down.
         adminDownOrigSdpId(126) - The originating SDP-ID is administratively
            down.
         adminDownRespSdpId(127) - The responding SDP-ID is administratively
            down.
         mTraceSourceIsNotRemote(128) - The multicast trace route test cannot be
            performed because the source address is not remote.
         invalidVirtualRouterId(129) - The OAM test cannot be performed because
            the associated virtual router ID is invalid.
         ldpPrefixIsLocal(130) - The OAM test cannot be performed because the
            associated LDP prefix is local to the system.
         sourceIpIsNotLocal(131) - The OAM test cannot be performed because the
            associated source address is not local to the system.
         nextHopIpIsLocal(132) - The OAM test cannot be performed because the
            associated next hop address is local to the system.
         targetIpIsLocal(133) - The OAM test cannot be performed because the
            associated target address is local to the system.
         invalidControlPlaneOption(134) - The OAM test cannot be performed
            because the control plane send or receive option is not allowed
            with the specified service.
         iomRevisionNotSupported(135) - The OAM test cannot be performed due
            to a mismatch in supported revision with the provisioned IOMs.
         invalidSourceMacOption(136) - The OAM test cannot be performed because
            the source MAC option is not allowed with the specified service.
         sendFailSpbMgdService(137) - The OAM test cannot be performed on a
            service which is managed by SPB.
         useStaticPwParameters(138) - The spoke SDP is configured for static PW.
         type1Fec129PwNotSupported(139) - The OAM test is not supported on
            type 1 FEC129 pseudowires.
         mplsTpLspPathNotOperational(140) - The OAM test cannot be performed
            because the MPLS-TP LSP path is not operational.
         invalidStaticMplsTpLsp(141)- The OAM test only supports static MPLS-TP
            LSPs.
         controlWordNotValid(142) - The control-word for the spoke-sdp is not
            valid for this OAM test.
         pwPathIdNotConfigured(143) - The pw-path-id provisioning is not
            complete.
         notSupportedOnVcSwitchService(144) - The OAM test is not supported on a
            vc-switching service.
         sdpFarEndNotSupported(145) - The OAM test does not support the SDP far
            end value.
         mplsTpLspPathShutdown(146) - The MPLS-TP path is currently shutdown.
         forceOptionIsBlocked(147) - The force option is currently blocked
            because of the configuration of a related entity.
         intfForLspPathIsNotOperational(148) - The interface for the LSP path is
            not operational
         ttlExpired(149) - The destination could not be reached because the
            time-to-live (IPv4) or hop limit (IPv6) was too small. This
            results from an ICMPv4 type 11 code 0 or ICMPv6 type 3 code 0
            message.
         networkUnreachable(150) - The network specified by the destination
            address is unreachable. This results from an ICMPv4 type 3 code 0
            or ICMPv6 type 1 code 0 message.
         hostUnreachable(151) - The host specified by the destination address is
            unreachable. This results from an ICMPv4 type 3 code 1 or ICMPv6
            type 1 code 3 message.
         bgpLabelPrefixIsLocal(152) - The OAM test cannot be performed because
            the associated BGP Label Route prefix is local to the system.
         bgpLabelPrefixUnknown(153) - The OAM test cannot be performed because
            the BGP Target FEC prefix entry is not found in the Routing Table.
         ldpPrefixUnknown(154) - The OAM test cannot be performed because the
            LDP Target FEC prefix entry is not found in the Routing Table.
         l2tpv3DeliveryTypeUnsupported(155) - The OAM test cannot be performed
            because the l2TPv3 delivery type is unsupported.
         vPingPeerCvNoLspPing(156) - The OAM test cannot be performed because
            the peer CV bits do not support lsp ping.
         vPingPeerCcNoCtrlWord(157) - The OAM test cannot be performed because
            the peer CC bits do not support control word.
         sendFailEvpnCfgdService(158) - The OAM test cannot be performed on a
            VPLS service that has EVPN configured.
         sendFailed(159) - The OAM test cannot send the test packet.
         minimumPacketSizeNotMet(160) - The OAM test cannot send the test packet
            as the minimum required packet size exceeds the user supplied packet
            size.
         invalidTargetFecType(161) - The OAM test does not support this FEC
            type.
         p2mpLspPingNotSupportedOnMgmtRtr(162) - The OAM p2mpLspPing test is not
            supported on the management router.
         ipv4SdpFarEndsOnly(163) - The OAM test only supports bindings and SDPs
            using an IPv4 far end.
         vxlanEgrBndSvcMismatch(164) - The OAM test cannot send packets to a
            VXLAN egress binding not owned by the same service as the one
            sending.
         vxlanNoMatchingTep(165) - The OAM test can only send to VTEPs that have
            been configured.
         vxlanEvpnUnconfigured(166) - The OAM test can only send on a service
            with EVPN configured.
         ipv6SdpFarEndsNotSupported(167) - The OAM test does not support
            bindings and SDPs using an IPv6 far end.
         oamTestOverSRTunNotSupported(168) - The OAM test is not supported on SR
            tunnels.
         sendFailEvpnCfgdPbbService(169) - The OAM test cannot be performed on a
            VPLS/Epipe service that is associated with a b-vpls that has EVPN
            configured.
         txPortDown(170) - The transmit port is operationally down.
         noTxPort(171) - No transmit port.
         parentAdminDown(172) - The parent (SPOKE, SAP, service or port) of the
            MEP is administratively down.
         destMacResolveFail(173) - Unable to resolve the remote-mepid to a
            unicast layer2 MAC address.
         vxlanIpV6TermUnsupported(174) - The OAM test does not support IPv6
            tunnel termination points.
         ipPrefixIsLocal(175) - The OAM test cannot be performed because
            the associated Ip prefix is local to the system.
         ipPrefixUnknown(176) - The OAM test cannot be performed because the
            Target FEC prefix entry is not found in the Routing Table.
         greEthBrdgdDelvryTypeUnsupported(177) - The OAM test cannot be
            performed because the GRE Ethernet Bridged delivery type is unsupported."
    SYNTAX      INTEGER {
        responseReceived                 (1),
        unknown                          (2),
        internalError                    (3),
        maxConcurrentLimitReached        (4),
        requestTimedOut                  (5),
        unknownOrigSdpId                 (6),
        downOrigSdpId                    (7),
        requestTerminated                (8),
        invalidOriginatorId              (9),
        invalidResponderId               (10),
        unknownRespSdpId                 (11),
        downRespSdpId                    (12),
        invalidServiceId                 (13),
        invalidSdp                       (14),
        downServiceSdp                   (15),
        noServiceEgressLabel             (16),
        invalidHostAddress               (17),
        invalidMacAddress                (18),
        invalidLspName                   (19),
        macIsLocal                       (20),
        farEndUnreachable                (21),
        downOriginatorId                 (22),
        downResponderId                  (23),
        changedResponderId               (24),
        downOrigSvcId                    (25),
        downRespSvcId                    (26),
        noServiceIngressLabel            (27),
        mismatchCustId                   (28),
        mismatchSvcType                  (29),
        mismatchSvcMtu                   (30),
        mismatchSvcLabel                 (31),
        noSdpBoundToSvc                  (32),
        downOrigSdpBinding               (33),
        invalidLspPathName               (34),
        noLspEndpointAddr                (35),
        invalidLspId                     (36),
        downLspPath                      (37),
        invalidLspProtocol               (38),
        invalidLspLabel                  (39),
        routeIsLocal                     (40),
        noRouteToDest                    (41),
        localExtranetRoute               (42),
        srcIpInBgpVpnRoute               (43),
        srcIpInvalid                     (44),
        bgpDaemonBusy                    (45),
        mcastNotEnabled                  (46),
        mTraceNoSGFlow                   (47),
        mTraceSysIpNotCfg                (48),
        noFwdEntryInMfib                 (49),
        dnsNameNotFound                  (50),
        noSocket                         (51),
        socketOptVprnIdFail              (52),
        socketOptIfInexFail              (53),
        socketOptNextHopFail             (54),
        socketOptMtuDiscFail             (55),
        socketOptSndbufFail              (56),
        socketOptHdrincFail              (57),
        socketOptTosFail                 (58),
        socketOptTtlFail                 (59),
        bindSocketFail                   (60),
        noRouteByIntf                    (61),
        noIntf                           (62),
        noLocalIp                        (63),
        sendtoFail                       (64),
        rcvdWrongType                    (65),
        noDirectInterface                (66),
        nexthopUnreachable               (67),
        socketOptHwTimeStampFail         (68),
        noSpokeSdpInVll                  (69),
        farEndVccvNotSupported           (70),
        noVcEgressLabel                  (71),
        socketOptIpSessionFail           (72),
        rcvdWrongSize                    (73),
        dnsLookupFail                    (74),
        noIpv6SrcAddrOnIntf              (75),
        multipathNotSupported            (76),
        nhIntfNameNotFound               (77),
        msPwInvalidReplyMode             (78),
        ancpNoAncpString                 (79),
        ancpNoSubscriber                 (80),
        ancpNoAncpStringForSubscriber    (81),
        ancpNoAccessNodeforAncpString    (82),
        ancpNoAncpCapabilityNegotiated   (83),
        ancpOtherTestInProgress          (84),
        ancpMaxNbrAncpTestsInProgress    (85),
        spokeSdpOperDown                 (86),
        noMsPwVccvInReplyDir             (87),
        p2mpLspNameOrInstInvalid         (88),
        p2mpLspS2LPathDown               (89),
        p2mpLspS2LAddressInvalid         (90),
        p2mpLspNotOperational            (91),
        p2mpLspTrMultipleReplies         (92),
        invalidMepId                     (93),
        multipleReplies                  (94),
        packetSizeTooBig                 (95),
        gtpPingError                     (96),
        gtpPingRsrcUnavailable           (97),
        gtpPingDupRequest                (98),
        gtpPingCleanUpInProg             (99),
        invalidInterface                 (100),
        p2mpLspNotFound                  (101),
        ethCfmSlmInLoss                  (102),
        ethCfmSlmOutLoss                 (103),
        ethCfmSlmUnacknowledged          (104),
        spokeSdpFecNoBndFound            (105),
        mtraceNotSupportedP2mp           (106),
        useFec129Parameters              (107),
        dnsServerUnexpectedResponse      (108),
        dnsServerResponseFormErr         (109),
        dnsServerResponseServFail        (110),
        dnsServerResponseNotImp          (111),
        dnsServerResponseRefused         (112),
        sendFailUndefinedServiceId       (113),
        sendFailWrongServiceType         (114),
        sendFailSubnettedService         (115),
        invalidRespServiceId             (116),
        adminDownOrigSdpBind             (117),
        operDownRespSdpBind              (118),
        adminDownRespSdpBind             (119),
        sdpBindVcidMismatch              (120),
        sdpBindTypeMismatch              (121),
        sdpBindVcTypeMismatch            (122),
        sdpBindVlanVcTagMismatch         (123),
        adminDownOrigSvc                 (124),
        adminDownRespSvc                 (125),
        adminDownOrigSdpId               (126),
        adminDownRespSdpId               (127),
        mTraceSourceIsNotRemote          (128),
        invalidVirtualRouterId           (129),
        ldpPrefixIsLocal                 (130),
        sourceIpIsNotLocal               (131),
        nextHopIpIsLocal                 (132),
        targetIpIsLocal                  (133),
        invalidControlPlaneOption        (134),
        iomRevisionNotSupported          (135),
        invalidSourceMacOption           (136),
        sendFailSpbMgdService            (137),
        useStaticPwParameters            (138),
        type1Fec129PwNotSupported        (139),
        mplsTpLspPathNotOperational      (140),
        invalidStaticMplsTpLsp           (141),
        controlWordNotValid              (142),
        pwPathIdNotConfigured            (143),
        notSupportedOnVcSwitchService    (144),
        sdpFarEndNotSupported            (145),
        mplsTpLspPathShutdown            (146),
        forceOptionIsBlocked             (147),
        intfForLspPathIsNotOperational   (148),
        ttlExpired                       (149),
        networkUnreachable               (150),
        hostUnreachable                  (151),
        bgpLabelPrefixIsLocal            (152),
        bgpLabelPrefixUnknown            (153),
        ldpPrefixUnknown                 (154),
        l2tpv3DeliveryTypeUnsupported    (155),
        vPingPeerCvNoLspPing             (156),
        vPingPeerCcNoCtrlWord            (157),
        sendFailEvpnCfgdService          (158),
        sendFailed                       (159),
        minimumPacketSizeNotMet          (160),
        invalidTargetFecType             (161),
        p2mpLspPingNotSupportedOnMgmtRtr (162),
        ipv4SdpFarEndsOnly               (163),
        vxlanEgrBndSvcMismatch           (164),
        vxlanNoMatchingTep               (165),
        vxlanEvpnUnconfigured            (166),
        ipv6SdpFarEndsNotSupported       (167),
        oamTestOverSRTunNotSupported     (168),
        sendFailEvpnCfgdPbbService       (169),
        txPortDown                       (170),
        noTxPort                         (171),
        parentAdminDown                  (172),
        destMacResolveFail               (173),
        vxlanIpV6TermUnsupported         (174),
        ipPrefixIsLocal                  (175),
        ipPrefixUnknown                  (176),
        greEthBrdgdDelvryTypeUnsupported (177)
    }

TmnxOamSignalProtocol            ::= TEXTUAL-CONVENTION
    STATUS      current
    DESCRIPTION
        "A value of type TmnxOamSignalProtocol indicates the type of label
         signaling protocol used by a router in a specific Layer 2 mapping
         entry.

         Code Points
         unknown - protocol is unknown
         static  - statically configured Label Switched Path (LSP)
         bgp     - Border Gateway Protocol
         ldp     - Label Distribution Protocol
         rsvpTe  - Resource Reservation Protocol, Traffic Engineering
         ospf    - Open Shortest Path First
         isis    - Intermediate System to Intermediate System"
    REFERENCE
        "IETF draft-kumarkini-mpls-spring-lsp-ping, 'Label Switched Path (LSP)
         Ping/Trace for Segment Routing Networks Using MPLS Dataplane', v02,
         1-Dec-2016, Section 6, 'Extension to Downstream Detailed Mapping TLV'."
    SYNTAX      INTEGER {
        unknown (0),
        static  (1),
        bgp     (2),
        ldp     (3),
        rsvpTe  (4),
        ospf    (5),
        isis    (6)
    }

TmnxOamTestResponsePlane         ::= TEXTUAL-CONVENTION
    STATUS      current
    DESCRIPTION
        "The value of TmnxOamTestResponsePlane is an enumerated integer that
         indicates the response plane from which the OAM ping or traceroute
         response was received."
    SYNTAX      INTEGER {
        controlPlane (1),
        dataPlane    (2),
        none         (3)
    }

TmnxOamSaaThreshold              ::= TEXTUAL-CONVENTION
    STATUS      current
    DESCRIPTION
        "The value of TmnxOamSaaThreshold is a enumerated integer that
         indicates which type of thresholds should be monitored upon completion
         of an OAM ping test run. When the corresponding threshold is crossed,
         a tmnxOamSaaThreshold notification will be generated.

         noThreshold(0) No threshold type is configured.
         inJitter   (1) Monitor the value of jitter calculated for the
                        inbound, one-way, OAM ping responses received
                        for an OAM ping test run.
         outJitter  (2) Monitor the value of jitter calculated for the
                        outbound, one-way, OAM ping requests sent for an
                        OAM ping test run.
         rtJitter   (3) Monitor the value of jitter calculated for the
                        round trip, two-way, OAM ping requests and replies
                        for an OAM ping test run.
         inLoss     (4) Monitor the number of inbound OAM ping responses not
                        received for an OAM ping test run.
         outLoss    (5) Monitor the number of outbound OAM ping requests that
                        could not be sent for an OAM ping test run.
         rtLoss     (6) Monitor the amount of packet loss for a round-trip
                        OAM ping test run.
         inLatency  (7) Monitor the average amount of latency of inbound
                        OAM ping responses for an OAM ping test run.
         outLatency (8) Monitor the average amount of latency of outbound
                        OAM ping requests for an OAM ping test run.
         rtLatency  (9) Monitor the average amount of round-trip latency
                        for an OAM ping test run."
    SYNTAX      INTEGER {
        noThreshold (0),
        inJitter    (1),
        outJitter   (2),
        rtJitter    (3),
        inLoss      (4),
        outLoss     (5),
        rtLoss      (6),
        inLatency   (7),
        outLatency  (8),
        rtLatency   (9)
    }

TmnxOamVccvAssocChannel          ::= TEXTUAL-CONVENTION
    STATUS      current
    DESCRIPTION
        "A value of type TmnxOamVccvAssocChannel specifies the launched echo
         request's usage of the Associated Channel (ACH) mechanism, when
         performing an MPLS-TP VCCV test.

         Values:
            notApplicable(1)
                Used when the test is not an MPLS-TP VCCV test.
            nonIp(2)
                Use the Associated Channel mechanism described in RFC 6426,
                Section 3.3.
            ipv4(3)
                Use the Associated Channel mechanism described in RFC 6426,
                Section 3.2."
    REFERENCE
        "RFC 6426, 'MPLS On-Demand Connectivity Verification and Route Tracing',
         Section 3.2, 'On-Demand CV with IP Encapsulation, over ACH',
         Section 3.3, 'Non-IP-Based On-Demand CV, Using ACH'."
    SYNTAX      INTEGER {
        notApplicable (1),
        nonIp         (2),
        ipv4          (3)
    }

TmnxOamVccvTestSubMode           ::= TEXTUAL-CONVENTION
    STATUS      current
    DESCRIPTION
        "A value of type TmnxOamVccvTestSubMode specifies the type of VCCV ping
         or VCCV trace route test to perform.

         VCCV test types:
             static(2)
                 Perform a VCCV ping or VCCV trace route test using the RFC
                 6426 'Target FEC Stack' code point 'Static Pseudowire'.
             unspecified(1)
                 Perform any other supported type of VCCV ping or trace route
                 test.  Examples:  a VCCV ping or VCCV trace route test using
                 the RFC 4379 'Target FEC Stack' code point 'FEC 128
                 Pseudowire'; a VCCV ping or VCCV trace route test using the RFC
                 4379 'Target FEC Stack' code point 'FEC 129 Pseudowire'."
    REFERENCE
        "RFC 4379, 'Detecting Multi-Protocol Label Switched (MPLS) Data Plane
         Failures', Section 3.2 ('Target FEC Stack').
         RFC 6426, 'MPLS On-Demand Connectivity Verification and Route Tracing',
         Section 2.3.2 ('Static Pseudowire Sub-TLV')."
    SYNTAX      INTEGER {
        unspecified (1),
        static      (2)
    }

TmnxOamVccvSwitTgtFecType        ::= TEXTUAL-CONVENTION
    STATUS      current
    DESCRIPTION
        "An object of type TmnxOamVccvSwitTgtFecType specifies the type of
         downstream FEC (Forward Equivalence Class) segment to be tested during
         a VCCV ping or trace route test.  The path to be tested starts with a
         FEC segment, and switches to a FEC segment with the specified
         (different) type.

         Values:
             none(1)
                 The path to be tested does not switch FEC types.
             fec128(2)
                 Switch to a segment with FEC type 'FEC 128 Pseudowire'.
             static(3)
                 Switch to a segment with FEC type 'Static Pseudowire'."
    REFERENCE
        "RFC 4379, 'Detecting Multi-Protocol Label Switched (MPLS) Data Plane
         Failures', Section 3.2.9 ('FEC 128 Pseudowire (Current)').
         RFC 6426, 'MPLS On-Demand Connectivity Verification and Route Tracing',
         Section 2.3.2 ('Static Pseudowire Sub-TLV')."
    SYNTAX      INTEGER {
        none   (1),
        fec128 (2),
        static (3)
    }

TmnxOamVcType                    ::= TEXTUAL-CONVENTION
    STATUS      current
    DESCRIPTION
        "The value of TmnxOamVcType is an enumerated integer that
         indicates the type of SDP binding, mesh or spoke,  associated
         with a VC ID.

         NOTE: In releases of this MIB prior to R4.0, the textual convention
         TmnxVcType was used to indicate either a mesh, 'ethernet (5)',
         or spoke, 'vpls (11)', type of SDP binding for a VC ID.  In
         release 4.0, the TmnxVcType enumeration 'vpls (11)' is changed to
         'ipipe (11)' and can no longer can be used to represent a spoke SDP
         binding.  This new enumerated textual convention, TmnxOamVcType, has
         been created for use in this MIB.  The same enumerated values used in
         previous releases are still used to indicate a mesh or spoke VC ID."
    SYNTAX      INTEGER {
        meshSdp  (5),
        spokeSdp (11)
    }

TmnxOamLTtraceDisStatusBits      ::= TEXTUAL-CONVENTION
    STATUS      current
    DESCRIPTION
        "The value of TmnxOamLTtraceDisStatusBits is an enumerated integer that
         describes the LDP tree trace discovery status in BITS. This indicates
         different reason values when the tree discovery of an IP Address FEC
         is not completely successful.

         Code points:
            timeout (0)        - one or more trace requests for an IP address
                                 FEC timed out
            maxPath (1)        - reached the maximum allowed path limit for an
                                 IP address FEC
            maxHop (2)         - reached the maximum allowed hop limit
            unexploredPath (3) - could not discover all possible paths
            noResource (4)     - the internal resources required to complete the
                                 discovery were unavailable"
    SYNTAX      BITS {
        timeout        (0),
        maxPath        (1),
        maxHop         (2),
        unexploredPath (3),
        noResource     (4)
    }

TmnxOamTestResult                ::= TEXTUAL-CONVENTION
    STATUS      current
    DESCRIPTION
        "The value of TmnxOamTestResult is an enumerated integer that describes
         the result of a ping or trace test run.
             undetermined      (0) The result is, as yet, unknown.
             success           (1) The test was successful.
             failed            (2) The test failed.
             aborted           (3) The test was terminated before completion.
             txResourcesUnavail(4) The test did not start because transmit
                                   resources are unavailable."
    SYNTAX      INTEGER {
        undetermined       (0),
        success            (1),
        failed             (2),
        aborted            (3),
        txResourcesUnavail (4)
    }

tmnxOamTestObjs                  OBJECT IDENTIFIER ::= { tmnxSRObjs 11 }

tmnxOamPingObjs                  OBJECT IDENTIFIER ::= { tmnxOamTestObjs 1 }

tmnxOamPingNotificationObjects   OBJECT IDENTIFIER ::= { tmnxOamPingObjs 1 }

tmnxOamPingMaxConcurrentTests    OBJECT-TYPE
    SYNTAX      Unsigned32
    UNITS       "tests"
    MAX-ACCESS  read-write
    STATUS      current
    DESCRIPTION
        "The maximum number of concurrent active OAM ping tests
         that are allowed within an agent implementation.  A value of
         zero (0) for this object implies that there is no limit for
         the number of concurrent active tests in effect."
    DEFVAL      { 0 }
    ::= { tmnxOamPingObjs 2 }

tmnxOamPingCtlTable              OBJECT-TYPE
    SYNTAX      SEQUENCE OF TmnxOamPingCtlEntry
    MAX-ACCESS  not-accessible
    STATUS      current
    DESCRIPTION
        "Defines the Nokia SROS OAM ping Control Table for providing,
         via SNMP, the capability of performing Nokia SROS OAM ping
         test operations.  The results of these tests are stored in the
         tmnxOamPingResultsTable and the tmnxOamPingHistoryTable."
    ::= { tmnxOamPingObjs 3 }

tmnxOamPingCtlEntry              OBJECT-TYPE
    SYNTAX      TmnxOamPingCtlEntry
    MAX-ACCESS  not-accessible
    STATUS      current
    DESCRIPTION
        "Defines an entry in the tmnxOamPingCtlTable.  The first index
         element, tmnxOamPingCtlOwnerIndex, is of type SnmpAdminString,
         a textual convention that allows for use of the SNMPv3
         View-Based Access Control Model (RFC 2575 [11], VACM)
         and allows a management application to identify its entries.
         The second index, tmnxOamPingCtlTestIndex, enables the same
         management application to have multiple outstanding requests."
    INDEX       {
        tmnxOamPingCtlOwnerIndex,
        tmnxOamPingCtlTestIndex
    }
    ::= { tmnxOamPingCtlTable 1 }

TmnxOamPingCtlEntry              ::= SEQUENCE
{
    tmnxOamPingCtlOwnerIndex         SnmpAdminString,
    tmnxOamPingCtlTestIndex          SnmpAdminString,
    tmnxOamPingCtlRowStatus          RowStatus,
    tmnxOamPingCtlStorageType        StorageType,
    tmnxOamPingCtlDescr              SnmpAdminString,
    tmnxOamPingCtlTestMode           INTEGER,
    tmnxOamPingCtlAdminStatus        INTEGER,
    tmnxOamPingCtlOrigSdpId          SdpId,
    tmnxOamPingCtlRespSdpId          SdpId,
    tmnxOamPingCtlFcName             TFCName,
    tmnxOamPingCtlProfile            TProfile,
    tmnxOamPingCtlMtuStartSize       Unsigned32,
    tmnxOamPingCtlMtuEndSize         Unsigned32,
    tmnxOamPingCtlMtuStepSize        Unsigned32,
    tmnxOamPingCtlTargetIpAddress    IpAddress,
    tmnxOamPingCtlServiceId          TmnxServId,
    tmnxOamPingCtlLocalSdp           TruthValue,
    tmnxOamPingCtlRemoteSdp          TruthValue,
    tmnxOamPingCtlSize               Unsigned32,
    tmnxOamPingCtlTimeOut            Unsigned32,
    tmnxOamPingCtlProbeCount         Unsigned32,
    tmnxOamPingCtlInterval           Unsigned32,
    tmnxOamPingCtlMaxRows            Unsigned32,
    tmnxOamPingCtlTrapGeneration     BITS,
    tmnxOamPingCtlTrapProbeFailureFilter Unsigned32,
    tmnxOamPingCtlTrapTestFailureFilter Unsigned32,
    tmnxOamPingCtlSAA                TruthValue,
    tmnxOamPingCtlRuns               Counter32,
    tmnxOamPingCtlFailures           Counter32,
    tmnxOamPingCtlLastRunResult      TmnxOamTestResult,
    tmnxOamPingCtlLastChanged        TimeStamp,
    tmnxOamPingCtlVRtrID             TmnxVRtrID,
    tmnxOamPingCtlTgtAddrType        InetAddressType,
    tmnxOamPingCtlTgtAddress         InetAddress,
    tmnxOamPingCtlSrcAddrType        InetAddressType,
    tmnxOamPingCtlSrcAddress         InetAddress,
    tmnxOamPingCtlDnsName            OCTET STRING,
    tmnxOamPingCtlDNSRecord          INTEGER,
    tmnxOamPingCtlIntervalUnits      INTEGER,
    tmnxOamPingCtlSubscriberName     TNamedItemOrEmpty
}

tmnxOamPingCtlOwnerIndex         OBJECT-TYPE
    SYNTAX      SnmpAdminString (SIZE (1..32))
    MAX-ACCESS  not-accessible
    STATUS      current
    DESCRIPTION
        "To facilitate the provisioning of access control by a
         security administrator using the View-Based Access
         Control Model (RFC 2575, VACM) for tables in which
         multiple users may need to independently create or
         modify entries, the initial index is used as an 'owner
         index'.  Such an initial index has a syntax of
         SnmpAdminString, and can thus be trivially mapped to a
         security name or group name as defined in VACM, in
         accordance with a security policy.

         When used in conjunction with such a security policy all
         entries in the table belonging to a particular user (or
         group) will have the same value for this initial index.
         For a given user's entries in a particular table, the
         object identifiers for the information in these entries
         will have the same sub identifiers (except for the 'column'
         sub identifier) up to the end of the encoded owner index.
         To configure VACM to permit access to this portion of the
         table, one would create vacmViewTreeFamilyTable entries
         with the value of vacmViewTreeFamilySubtree including
         the owner index portion, and vacmViewTreeFamilyMask
         'wildcarding' the column sub identifier.  More elaborate
         configurations are possible."
    ::= { tmnxOamPingCtlEntry 1 }

tmnxOamPingCtlTestIndex          OBJECT-TYPE
    SYNTAX      SnmpAdminString (SIZE (1..32))
    MAX-ACCESS  not-accessible
    STATUS      current
    DESCRIPTION
        "The test name index of the Nokia SROS OAM ping test. This is locally
         unique, within the scope of an tmnxOamPingCtlOwnerIndex."
    ::= { tmnxOamPingCtlEntry 2 }

tmnxOamPingCtlRowStatus          OBJECT-TYPE
    SYNTAX      RowStatus
    MAX-ACCESS  read-create
    STATUS      current
    DESCRIPTION
        "This object allows entries to be created and deleted
         in the tmnxOamPingCtlTable.  Deletion of an entry in this
         table results in all corresponding (same
         tmnxOamPingCtlOwnerIndex and tmnxOamPingCtlTestIndex index
         values) tmnxOamPingResultsTable and tmnxOamPingHistoryTable
         entries being deleted.

         Activation of a Nokia SROS OAM ping operation is controlled via
         tmnxOamPingCtlAdminStatus and not by changing this object's value to
         active(1).

         The values for configuration objects required for the type of test
         specified in tmnxOamPingCtlTestMode MUST be specified prior to a
         transition to active(1) state being accepted.

         Transitions in and out of active(1) state are not allowed while an
         entry's tmnxOamPingResultsOperStatus is active(1) with the exception
         that deletion of an entry in this table by setting its RowStatus
         object to destroy(6) will stop an active Nokia SROS OAM ping
         operation.

         The operational state of an Nokia SROS OAM ping operation can be
         determined by examination of its tmnxOamPingResultsOperStatus object."
    REFERENCE
        "See definition of RowStatus in RFC 2579, 'Textual
         Conventions for SMIv2.'"
    ::= { tmnxOamPingCtlEntry 3 }

tmnxOamPingCtlStorageType        OBJECT-TYPE
    SYNTAX      StorageType
    MAX-ACCESS  read-create
    STATUS      obsolete
    DESCRIPTION
        "The storage type for this conceptual row. Conceptual rows having the
         value 'permanent' need not allow write-access to any columnar objects
         in the row.

         This object was marked obsolete in SROS Release 14.0 R1.  There is no
         replacement object."
    DEFVAL      { volatile }
    ::= { tmnxOamPingCtlEntry 4 }

tmnxOamPingCtlDescr              OBJECT-TYPE
    SYNTAX      SnmpAdminString
    MAX-ACCESS  read-create
    STATUS      obsolete
    DESCRIPTION
        "The purpose of this object is to provide a descriptive name of the OAM
         ping test.

         This object was marked obsolete in SROS Release 14.0 R1.  There is no
         replacement object."
    DEFVAL      { ''H }
    ::= { tmnxOamPingCtlEntry 5 }

tmnxOamPingCtlTestMode           OBJECT-TYPE
    SYNTAX      INTEGER {
        none              (0),
        sdpPing           (1),
        mtuPing           (2),
        svcPing           (3),
        macPing           (5),
        macPopulate       (6),
        macPurge          (7),
        lspPing           (8),
        vprnPing          (9),
        atmPing           (10),
        mfibPing          (11),
        cpePing           (12),
        mrInfo            (13),
        vccvPing          (14),
        icmpPing          (15),
        dnsPing           (16),
        ancpLoopback      (17),
        p2mpLspPing       (18),
        ethCfmLoopback    (19),
        ethCfmTwoWayDelay (20),
        mobGtpPing        (21),
        ethCfmTwoWaySlm   (22),
        vxlanPing         (23)
    }
    MAX-ACCESS  read-create
    STATUS      current
    DESCRIPTION
        "The value of tmnxOamPingCtlTestMode specifies the type of OAM ping
         test defined by this row.

         none    -  the test type is unspecified.

         sdpPing -  tests SDP connectivity and round trip time.

         mtuPing -  tests MTU path size.

         svcPing -  determines the existence and operative state of the service
                    ID on the far end ESR.

         macPing -  determines address mappings for the service ID.  See
                    tmnxOamMacPingCtlTable for additional parameters.

         macPopulate - populates an OAM MAC address into the FIBs.  See
                    tmnxOamMacPingCtlTable for additional parameters.

         macPurge - deletes an OAM MAC address from the FIBs.  See
                    tmnxOamMacPingCtlTable for additional parameters.

         lspPing -  tests Label Switched Path (LSP) path connectivity and round
                    trip time.  See tmnxOamLspPingCtlTable for additional
                    parameters.

         vprnPing - tests IP path connectivity and round trip time within a
                    specified VPRN service.  See tmnxOamVprnPingCtlTable for
                    additional parameters.

         atmPing  - tests ATM path connectivity and round trip time on an ATM
                    VCC.  See tmnxOamAtmPingCtlTable for additional parameters.

         mfibPing - tests IP multicast connectivity and round trip time within a
                    specified VPLS service.  See tmnxOamMfibPingCtlTable for
                    additional parameters.

         cpePing  - determines IP connectivity to a CPE within a specified VPLS
                    service.  See tmnxOamCpePingCtlTable for additional
                    parameters.

         mrInfo   - Get multicast router's capabilities and the list of
                    interfaces with neighbors.

         vccvPing - Virtual Circuit Connectivity Verification, testing
                    pseudowire connectivity and round trip time.  See
                    tmnxOamVccvPingCtlTable for additional parameters.

         icmpPing - tests IP connectivity and round trip time.  See
                    tmnxOamIcmpPingCtlTable for additional parameters.

         dnsPing  - tests DNS name resolution connectivity and round trip time.

         ancpLoopback - send an OAM loopback test request to the access node.
                    See tmnxOamAncpTestCtlTable for additional parameters.

         p2mpLspPing - tests P2MP LSP path connectivity and round trip time.
                    See tmnxOamP2mpLspPingCtlTable for additional parameters.

         ethCfmLoopback - performs Ethernet Connectivity Fault Management (CFM)
                    loopback tests.  This MIB supports the SAA form of this
                    test only (the OAM form uses a separate set of objects - see
                    IEEE8021-CFM-MIB).  Additional parameters for the SAA
                    ethCfmLoopback test are in tmnxOamEthCfmPingCtlTable.

         ethCfmTwoWayDelay - performs Ethernet Connectivity Fault Management
                    (CFM) two way delay tests.  This MIB supports the SAA form
                    of this test only (the OAM form uses a separate set of
                    objects - see IEEE8021-CFM-MIB).  Additional parameters for
                    the SAA ethCfmTwoWayDelay test are in
                    tmnxOamEthCfmPingCtlTable.

         mobGtpPing - tests GTP (GPRS Tunnelling Protocol) path connectivity.

         ethCfmTwoWaySlm - performs Ethernet Connectivity Fault Management
                    (CFM) two way Synthetic Loss Measurement (SLM) tests. This
                    MIB supports the SAA form of this test only (the OAM form
                    uses a separate set of objects - see
                    TIMETRA-IEEE8021-CFM-MIB). Additional parameters for the SAA
                    ethCfmTwoWaySlm test are in tmnxOamEthCfmPingCtlTable.

         vxlanPing - tests Virtual Extensible Local Area Network (VXLAN)
                    connectivity, checks the status of configured VXLAN Network
                    IDs (VNIs), and allows validation of connected end systems.
                    See tmnxOamVxlanPingCtlTable for additional parameters.

         The support for Service Assurance Agent (SAA) tests (i.e. tests with
         tmnxOamSaaCtlTable rows) and OAM tests (i.e. tests without
         tmnxOamSaaCtlTable rows) varies with the test type, as shown in the
         following table.

         tmnxOamPingCtlTestMode   SAA Supported   OAM Supported
         ----------------------   -------------   -------------
         'ancpLoopback'                      No             Yes
         'atmPing'                           No             Yes
         'cpePing'                          Yes             Yes
         'dnsPing'                          Yes             Yes
         'ethCfmLoopback'                   Yes              No
         'ethCfmTwoWayDelay'                Yes              No
         'ethCfmTwoWaySlm'                  Yes              No
         'icmpPing'                         Yes             Yes
         'lspPing'                          Yes             Yes
         'macPing'                          Yes             Yes
         'macPopulate'                       No             Yes
         'macPurge'                          No             Yes
         'mfibPing'                          No             Yes
         'mobGtpPing'                        No              No
         'mrInfo'                            No             Yes
         'mtuPing'                           No             Yes
         'p2mpLspPing'                       No             Yes
         'sdpPing'                          Yes             Yes
         'svcPing'                           No             Yes
         'vccvPing'                         Yes             Yes
         'vprnPing'                         Yes             Yes
         'vxlanPing'                         No             Yes"
    DEFVAL      { none }
    ::= { tmnxOamPingCtlEntry 6 }

tmnxOamPingCtlAdminStatus        OBJECT-TYPE
    SYNTAX      INTEGER {
        enabled  (1),
        disabled (2)
    }
    MAX-ACCESS  read-create
    STATUS      current
    DESCRIPTION
        "Reflects the desired state that a tmnxOamPingCtlEntry should be in:

           enabled(1)  - Attempt to activate the test as defined by
                         this tmnxOamPingCtlEntry.
           disabled(2) - Deactivate the test as defined by this
                         tmnxOamPingCtlEntry.

         An attempt to set tmnxOamPingCtlAdminStatus to 'enabled' will fail
         if the parameters required by a particular OAM ping test mode have
         not been previously set.  Upon completion of an OAM ping test,
         the agent will reset the value of this object to 'disabled'.
         When this object has the value 'enabled' an attempt to modify
         any of the test parameters will fail with an inconsistentValue
         error.

         If tmnxOamPingCtlTestMode equals either 'sdpPing' or 'mtuPing',
         tmnxOamPingCtlOrigSdpId must have already been set.

         If tmnxOamPingCtlTestMode equals 'mtuPing', tmnxOamPingCtlMtuStartSize
         and tmnxOamPingCtlMtuEndSize must also have already been set.

         If tmnxOamPingCtlTestMode equals 'svcPing', tmnxOamPingCtlTgtAddress
         and tmnxOamPingCtlServiceId must have already been set.

         If tmnxOamPingCtlTestMode equals 'cpePing', tmnxOamPingCtlServiceId,
         tmnxOamPingCtlTgtAddress, and tmnxOamCpePingCtlSrcAddress are
         required.

         If tmnxOamPingCtlTestMode equals 'icmpPing', tmnxOamPingCtlTgtAddress
         must have already been set.

         If tmnxOamPingCtlTestMode equals 'dnsPing', tmnxOamPingCtlTgtAddress
         must have already been set.

         If tmnxOamPingCtlSAA has the value 'true' and tmnxOamSaaCtlAdminStatus
         has a value 'outOfService', an attempt to set this object to 'enabled'
         will fail with an inconsistentValue error.

         Refer to the corresponding tmnxOamPingResultsOperStatus to determine
         the operational state of the test defined by this entry."
    DEFVAL      { disabled }
    ::= { tmnxOamPingCtlEntry 7 }

tmnxOamPingCtlOrigSdpId          OBJECT-TYPE
    SYNTAX      SdpId
    MAX-ACCESS  read-create
    STATUS      current
    DESCRIPTION
        "Specifies the originating SDP-ID to be used for performing
         a sdp-ping or mtu-ping operation.  This parameter is required
         only if tmnxOamPingCtlTestMode has a value of either 'sdpPing'
         or 'mtuPing'.

         The far-end address of the specified SDP-ID is the expected
         responder-id within each OAM reply message received.  The
         specified SDP-ID defines the encapsulation of the SDP tunnel
         encapsulation used to reach the far-end.  This can be IP/GRE
         or MPLS.  The value of tmnxOamPingCtlFcName is used to define
         the outgoing forwarding class used for the SDP encapsulation.

         If the value of tmnxOamPingCtlOrigSdpId is invalid, or the SDP
         is administratively down, or unavailable, the OAM Echo request
         message probe is not sent and an appropriate error value is
         written to tmnxOamPingHistoryStatus for that probe entry.  Once
         the interval timer expires, the next probe attempt will be made
         if required."
    DEFVAL      { 0 }
    ::= { tmnxOamPingCtlEntry 8 }

tmnxOamPingCtlRespSdpId          OBJECT-TYPE
    SYNTAX      SdpId
    MAX-ACCESS  read-create
    STATUS      current
    DESCRIPTION
        "Specifies the return SDP-ID to be used by the far-end node for
         its message reply.  This parameter is optional and is valid only if
         tmnxOamPingCtlTestMode has a value of 'sdpPing'.

         If this SDP-ID does not exist on the far-end, terminates on another
         node different than the originating node, or some other issue
         prevents the far-end from using the specified SDP-ID, the OAM Echo
         message reply is sent using generic IP/GRE OAM encapsulation.  The
         received forwarding class (as mapped on the ingress network interface
         for the far-end) defines the forwarding class encapsulation for the
         reply message."
    DEFVAL      { 0 }
    ::= { tmnxOamPingCtlEntry 9 }

tmnxOamPingCtlFcName             OBJECT-TYPE
    SYNTAX      TFCName
    MAX-ACCESS  read-create
    STATUS      current
    DESCRIPTION
        "The value of tmnxOamPingCtlFcName specifies the forwarding class to be
         used when launching the probe(s).  The forwarding class name must be
         present in the index column of TIMETRA-QOS-MIB::tFCNameTable.  This
         object is optional.

         As shown in the following table: a) this object is applicable to a
         subset of the test types, and b) this object is configurable for a
         subset of the test types, and c) the default forwarding class depends
         on the test type.

         tmnxOamPingCtlTestMode   Applicable?   Configurable?   Default
         ----------------------   -----------   -------------   -------
         'cpePing'                yes           yes             'be'
         'ethCfmLoopback'         yes           yes             'nc'
         'ethCfmTwoWayDelay'      yes           yes             'nc'
          ethCfmTwoWaySlm'        yes           yes             'nc'
         'icmpPing'               yes           yes             'nc'
         'lspPing'                yes           yes             'be'
         'macPing'                yes           yes             'be'
         'p2mpLspPing'            yes           yes             'be'
         'sdpPing'                yes           yes             'be'
         'svcPing'                yes           no              'nc'
         'vccvPing'               yes           yes             'be'
         'vprnPing'               yes           yes             'be'
         'vxlanPing'              yes           yes             'be'
         otherwise                no            N/A             N/A

         For 'ethCfmLoopback','ethCfmTwoWayDelay', and 'ethCfmTwoWaySlm', the
         forwarding class depends on whether the request is configured to egress
         on a network port or an access port.  In the network port case, the
         forwarding class is the forwarding class of the pseudowire.  In the
         access port case, the forwarding class is that of the SAP's egress
         encapsulation policy.

         For 'lspPing' this is the forwarding class of the LSP tunnel.

         For 'macPing' or 'sdpPing' this is the forwarding class of the SDP
         encapsulation.

         For 'p2mpLspPing' this is the forwarding class of the P2MP LSP tree.

         For 'vccvPing' this is the forwarding class of the pseudowire.

         If forwarding classes are mapped by the applicable QoS policy, the
         probe(s) may be launched using a different forwarding class than the
         forwarding class specified by this object."
    DEFVAL      { "be" }
    ::= { tmnxOamPingCtlEntry 10 }

tmnxOamPingCtlProfile            OBJECT-TYPE
    SYNTAX      TProfile
    MAX-ACCESS  read-create
    STATUS      current
    DESCRIPTION
        "The value of tmnxOamPingCtlProfile specifies the profile to be used
         with the forwarding class specified in tmnxOamPingCtlFcName.  This
         object is optional.

         As shown in the following table: a) this object is applicable to a
         subset of the test types, and b) this object is configurable for a
         subset of the test types, and c) the default profile value depends on
         the test type.

         tmnxOamPingCtlTestMode   Applicable?   Configurable?   Default
         ----------------------   -----------   -------------   -------
         'cpePing'                yes           yes             'out(2)'
         'ethCfmLoopback'         yes           yes             'in(1)'
         'ethCfmTwoWayDelay'      yes           yes             'in(1)'
         'ethCfmTwoWaySlm'        yes           yes             'in(1)'
         'lspPing'                yes           yes             'out(2)'
         'macPing'                yes           yes             'out(2)'
         'p2mpLspPing'            yes           yes             'out(2)'
         'sdpPing'                yes           yes             'out(2)'
         'svcPing'                yes           no              'in(1)'
         'vccvPing'               yes           yes             'out(2)'
         'vprnPing'               yes           yes             'out(2)'
         'vxlanPing'              yes           yes             'in(1)'
         otherwise                no            N/A             N/A"
    DEFVAL      { out }
    ::= { tmnxOamPingCtlEntry 11 }

tmnxOamPingCtlMtuStartSize       OBJECT-TYPE
    SYNTAX      Unsigned32 (0 | 40..9198)
    UNITS       "Octets"
    MAX-ACCESS  read-create
    STATUS      current
    DESCRIPTION
        "The value of tmnxOamPingCtlMtuStartSize specifies the size of the
         first OAM Echo message sent as part of an 'mtuPing' test.

         Setting this object to a non-zero value is a prerequisite for starting
         an 'mtuPing' test.  Its value must be less than or equal to the value
         of tmnxOamPingCtlMtuEndSize.

         An attempt to set this object from a non-zero value to zero will fail
         with a wrongValue error.

         Changing the message size is a method of checking the ability of an
         SDP to support a particular path-mtu value. The size of the message
         does not include the SDP encapsulation, VC-Label (if applied) or any
         DLC headers or trailers."
    DEFVAL      { 0 }
    ::= { tmnxOamPingCtlEntry 12 }

tmnxOamPingCtlMtuEndSize         OBJECT-TYPE
    SYNTAX      Unsigned32 (0 | 40..9198)
    UNITS       "Octets"
    MAX-ACCESS  read-create
    STATUS      current
    DESCRIPTION
        "The value of tmnxOamPingCtlMtuEndSize specifies the size of the last
         OAM Echo message sent as part of an 'mtuPing' test.

         Setting this object to a non-zero value is a prerequisite for starting
         an 'mtuPing' test.  Its value must be greater than or equal to
         the value of tmnxOamPingCtlMtuStartSize.

         An attempt to set this object from a non-zero value to zero will fail
         with a wrongValue error."
    DEFVAL      { 0 }
    ::= { tmnxOamPingCtlEntry 13 }

tmnxOamPingCtlMtuStepSize        OBJECT-TYPE
    SYNTAX      Unsigned32 (1..512)
    UNITS       "Octets"
    MAX-ACCESS  read-create
    STATUS      current
    DESCRIPTION
        "Specifies the number of octets by which to increment the
         OAM Echo message request size for each message request sent
         when tmnxOamPingCtlTestMode is set equal to 'mtuPing'.  If the
         next incremented message size is greater than
         tmnxOamPingCtlMtuEndSize, the last message has already been
         sent.  The next size message is not sent until a reply is
         received or three messages have timed out at the current
         size.

         This parameter is optional."
    DEFVAL      { 32 }
    ::= { tmnxOamPingCtlEntry 14 }

tmnxOamPingCtlTargetIpAddress    OBJECT-TYPE
    SYNTAX      IpAddress
    MAX-ACCESS  read-create
    STATUS      obsolete
    DESCRIPTION
        "Specifies the IPv4 address to be used as the destination for
         performing an OAM ping operation when tmnxOamPingCtlTestMode has
         a value of 'svcPing' or 'vprnPing'.  This parameter is
         required for 'svcPing', 'vprnPing', 'cpePing' and 'mrinfo'.

         This object was obsoleted in release 4.0 and replaced with InetAddress
         objects tmnxOamPingCtlTgtAddrType and tmnxOamPingCtlTgtAddress."
    DEFVAL      { '00000000'h }
    ::= { tmnxOamPingCtlEntry 16 }

tmnxOamPingCtlServiceId          OBJECT-TYPE
    SYNTAX      TmnxServId (0..2147483647)
    MAX-ACCESS  read-create
    STATUS      current
    DESCRIPTION
        "The value of tmnxOamPingCtlServiceId specifies the service ID of the
         service being tested.

         The applicability of tmnxOamPingCtlServiceId varies with the test
         type, as shown in the following table.

         tmnxOamPingCtlTestMode   Applicability    Related Virtual Router Object
         ----------------------   -------------    -----------------------------
         'cpePing'                mandatory        none
         'icmpPing'               optional         tmnxOamPingCtlVRtrID
         'macPing'                mandatory        none
         'macPopulate'            mandatory        none
         'macPurge'               mandatory        none
         'mfibPing'               mandatory        none
         'mrInfo'                 optional         tmnxOamPingCtlVRtrID
         'p2mpLspPing'            optional         tmnxOamPingCtlVRtrID
         'svcPing'                mandatory        none
         'vprnPing'               mandatory        none
         'vxlanPing'              mandatory        none
         otherwise                not applicable   none

         When tmnxOamPingCtlServiceId is mandatory, a non-zero value must be
         provided.

         When tmnxOamPingCtlServiceId is optional, it is used to specify a VPRN
         service.  The test must use the VPRN service's virtual router.

         When a related virtual router object is shown, the interaction is
         described in the DESCRIPTION clause of the listed object.

         Service IDs larger than 2147483647 are internal, so they are excluded
         from the range.

         The default value is the null service ID."
    DEFVAL      { 0 }
    ::= { tmnxOamPingCtlEntry 17 }

tmnxOamPingCtlLocalSdp           OBJECT-TYPE
    SYNTAX      TruthValue
    MAX-ACCESS  read-create
    STATUS      current
    DESCRIPTION
        "When the value of tmnxOamPingCtlLocalSdp is 'true', the 'svcPing' test
         determines an egress SDP-ID that is bound to the service that has
         the far-end IP address specified in tmnxOamPingCtlTgtAddress
         assigned to it.  The far-end address of the specified SDP-ID is
         the expected responder-id within the OAM Echo reply message.  The
         SDP-ID defines the encapsulation of the SDP tunnel encapsulation
         used to reach the far-end.  This can be IP/GRE or MPLS.  On the
         originator egress, the Service-ID must have an associated VC-Label
         to reach the far-end address of the SDP-ID and the SDP-ID must be
         operational for the message to be sent.
         This object is optional and valid only when tmnxOamPingCtlTestMode is
         equal to 'svcPing'."
    DEFVAL      { false }
    ::= { tmnxOamPingCtlEntry 18 }

tmnxOamPingCtlRemoteSdp          OBJECT-TYPE
    SYNTAX      TruthValue
    MAX-ACCESS  read-create
    STATUS      current
    DESCRIPTION
        "The value of tmnxOamPingCtlRemoteSdp specifies the encapsulation of
         the ping reply to be sent by the far end node.

         When tmnxOamPingCtlRemoteSdp is 'false', the far-end node sends the
         reply using the generic IP/GRE OAM encapsulation.

         When tmnxOamPingCtlRemoteSdp is 'true', the far-end node sends the
         reply using the same service tunnel encapsulation labeling used for the
         associated service traffic.  If that labeling cannot be found, the
         generic IP/GRE OAM encapsulation is used.

         This object is optional and is applicable only when
         tmnxOamPingCtlTestMode is equal to 'svcPing'."
    DEFVAL      { false }
    ::= { tmnxOamPingCtlEntry 19 }

tmnxOamPingCtlSize               OBJECT-TYPE
    SYNTAX      Unsigned32 (0..16384)
    UNITS       "octets"
    MAX-ACCESS  read-create
    STATUS      current
    DESCRIPTION
        "The value of tmnxOamPingCtlSize specifies the size of the OAM echo
         request PDU.

         The supported ranges, etc, for each test type are specified in the
         following table.

         tmnxOamPingCtlTestMode  Minimum  Maximum  Default  Auto Adjust
         ----------------------  -------  -------  -------  -----------
         'ethCfmLoopback'              0     1500        0           No
         'ethCfmTwoWaySlm'             0     1500        0           No
         'icmpPing'                    0    16384       56           No
         'lspPing'                     1     9198        1          Yes
         'macPing'                     1     9198       72          Yes
         'mfibPing'                    1     9198       72          Yes
         'p2mpLspPing'                 1     9198        1          Yes
         'sdpPing'                    72     9198       72          Yes
         'vccvPing'                    1     9198        1          Yes
         'vprnPing'                    1     9198       72          Yes
         'vxlanPing'                   0     2000        0           No
         otherwise                tmnxOamPingCtlSize is not significant

         For a test type supporting Auto Adjust, if the tmnxOamPingCtlSize value
         is too small, SROS automatically chooses the next highest supported PDU
         size.  For example, if tmnxOamPingCtlSize is 1 when a 'vccvPing' test
         is started on a FEC 128 pseudowire, an 88 octet echo request PDU is
         sent.

         For a test type which does not support Auto Adjust, the
         tmnxOamPingCtlSize value must lead to a valid echo request PDU size.

         When tmnxOamPingCtlTestMode has a value of 'ethCfmLoopback' or
         'ethCfmTwoWaySlm', tmnxOamPingCtlSize specifies the number of octets in
         the Value field of the Data TLV of the applicable Y.1731 PDU.  If zero
         is specified, the packet has no Data TLV.

         When tmnxOamPingCtlTestMode has a value of 'icmpPing',
         tmnxOamPingCtlSize specifies the payload size following the ICMP
         header.

         When tmnxOamPingCtlTestMode has a value of 'vxlanPing',
         tmnxOamPingCtlSize specifies the total size of the Pad TLV added to the
         launched VXLAN ping request.  tmnxOamPingCtlSize = 0 indicates
         no Pad TLV is added.  The smallest Pad TLV is five bytes, so values in
         the range 1..4 are rejected.

         When the echo request PDU is encapsulated in an IP/GRE SDP, the IP 'DF'
         (Don't Fragment) bit is set.  If any segment of the path between the
         sender and receiver cannot handle the PDU size, the PDU is discarded.
         MPLS LSPs are not expected to fragment the PDU either, as the message
         contained in the LSP is not an IP packet."
    REFERENCE
        "RFC 4379, 'Detecting Multi-Protocol Label Switched (MPLS) Data Plane
         Failures', Section 3.4, 'Pad TLV'.
         ITU-T G.8013/Y.1731, 'OAM functions and mechanisms for Ethernet
         based networks', 07/2011, Section 9, 'OAM PDU types'."
    DEFVAL      { 72 }
    ::= { tmnxOamPingCtlEntry 20 }

tmnxOamPingCtlTimeOut            OBJECT-TYPE
    SYNTAX      Unsigned32 (1..120)
    UNITS       "seconds"
    MAX-ACCESS  read-create
    STATUS      current
    DESCRIPTION
        "The value of tmnxOamPingCtlTimeOut specifies the time-out value, in
         seconds, to be used during a test run.

         Timers (with duration configured using the tmnxOamPingCtlTimeOut value)
         are used in one of two ways during a test run.
         1.  Per Probe:  a timer is started each time a probe is sent.  If the
             timer expires before the probe response arrives, the probe is
             declared failed.  This is the traditional time-out method for a
             sequence of probes.
             OR
         2.  Per Test:  a timer is started once per test run, when the last
             probe of the test run is sent.  ANY probe which does not have a
             response when the timer expires is declared failed.

         SROS chooses 'Per Probe' or 'Per Test' based on the
         tmnxOamPingCtlTestMode value.  The choice is not configurable.

         The accepted minimum, maximum, and default values for
         tmnxOamPingCtlTimeOut depend on tmnxOamPingCtlTestMode, as shown in the
         following table.  The table also shows the timer usage for the test
         mode.

         tmnxOamPingCtlTestMode  Min  Max  Def   Timer Usage
         ----------------------  ---  ---  ---   -----------
         'atmPing'                 1   10    5   Per Probe
         'dnsPing'                 1  120    5   Per Probe
         'ethCfmLoopback'          1   10    5   Per Probe
         'ethCfmTwoWayDelay'       1   10    5   Per Test
         'ethCfmTwoWaySlm'         1   10    5   Per Test
         'icmpPing'                1   10    5   Per Test
         'lspPing'                 1   10    5   Per Probe
         'macPing'                 1   10    5   Per Probe
         'mfibPing'                1  100    5   Per Probe
         'mtuPing'                 1   10    5   Per Probe
         'p2mpLspPing'             1  120   10   Per Probe
         'sdpPing'                 1   10    5   Per Probe
         'vccvPing'                1   10    5   Per Probe
         'vprnPing'                1  100    5   Per Probe
         'vxlanPing'               1   10    5   Per Probe
         otherwise  .........  the value of tmnxOamPingCtlTimeOut is irrelevant"
    DEFVAL      { 5 }
    ::= { tmnxOamPingCtlEntry 21 }

tmnxOamPingCtlProbeCount         OBJECT-TYPE
    SYNTAX      Unsigned32 (1..100000)
    UNITS       "probes"
    MAX-ACCESS  read-create
    STATUS      current
    DESCRIPTION
        "The value of tmnxOamPingCtlProbeCount specifies the number of probes
         to send during the test.

         The maximum probe count depends on the value of
         tmnxOamPingCtlTestMode, as follows.

         tmnxOamPingCtlTestMode   Maximum
         ----------------------   -------
         'ethCfmTwoWayDelay'         1000
         'ethCfmTwoWaySlm'           1000
         'icmpPing'                100000
         'macPopulate'                  1
         'macPurge'                     1
         'p2mpLspPing'                  1
         'svcPing'                      1
         'vxlanPing'                 1024
         otherwise                    100

         For the following tmnxOamPingCtlTestMode values, the value of
         tmnxOamPingCtlProbeCount does not affect the behavior of the test:
         'mrInfo', 'mtuPing'.

         If tmnxOamPingCtlTestMode is 'icmpPing', the default probe count value
         is 5.  Otherwise, the DEFVAL applies."
    DEFVAL      { 1 }
    ::= { tmnxOamPingCtlEntry 22 }

tmnxOamPingCtlInterval           OBJECT-TYPE
    SYNTAX      Unsigned32 (1..10000)
    MAX-ACCESS  read-create
    STATUS      current
    DESCRIPTION
        "The value of tmnxOamPingCtlInterval specifies the time to wait between
         the transmission of one OAM Echo request and the next.  The UNITS are
         specified by tmnxOamPingCtlIntervalUnits.  For example, if
         tmnxOamPingCtlInterval has the value 1, and tmnxOamPingCtlIntervalUnits
         has the value 'centiseconds(2)', the interval between OAM Echo requests
         is 0.01 seconds.

         The applicability, range, and default value of the interval specified
         using the tmnxOamPingCtlInterval and tmnxOamPingCtlIntervalUnits pair
         vary with tmnxOamPingCtlTestMode and tmnxOamIcmpPingCtlRapid, as shown
         in the following table.

         tmnxOamPingCtlTestMode    Supported Values (sec)          Default (sec)
         ------------------------  ------------------------------  -------------
         'ethCfmLoopback'          1, 2, .. 10                              5
         'ethCfmTwoWayDelay'       0.1, 0.2, .. 0.9;  1, 2, .. 10           5
         'ethCfmTwoWaySlm'         0.1, 0.2, .. 0.9;  1, 2, .. 10           5
         'icmpPing' with RAPID     0.01, 0.02, .. 100.00                    0.01
         'icmpPing' without RAPID  1, 2, .. 10000                           1
         'p2mpLspPing'             not applicable
         'vxlanPing'               0.1;  1, 2, .. 10                        1
         otherwise                 1, 2, .. 10                              1"
    DEFVAL      { 1 }
    ::= { tmnxOamPingCtlEntry 23 }

tmnxOamPingCtlMaxRows            OBJECT-TYPE
    SYNTAX      Unsigned32
    UNITS       "rows"
    MAX-ACCESS  read-create
    STATUS      obsolete
    DESCRIPTION
        "The maximum number of entries allowed in the tmnxOamPingHistoryTable
         for this OAM ping test.  The agent will remove the oldest entry in
         the tmnxOamPingHistoryTable to allow the addition of an new entry
         once the number of rows in the tmnxOamPingHistoryTable reaches this
         value.

         Old entries are not removed when a new test is started.  Entries are
         added to the tmnxOamPingHistoryTable until tmnxOamPingCtlMaxRows is
         reached before entries begin to be removed.

         'p2mpLspPing' uses a default value of 400, which is the maximum number
         of leaves per P2MP LSP tree.

         A value of 0 for this object disables creation of
         tmnxOamPingHistoryTable entries.

         This object was obsoleted in release 6.0R17."
    DEFVAL      { 300 }
    ::= { tmnxOamPingCtlEntry 24 }

tmnxOamPingCtlTrapGeneration     OBJECT-TYPE
    SYNTAX      BITS {
        probeFailure   (0),
        testFailure    (1),
        testCompletion (2)
    }
    MAX-ACCESS  read-create
    STATUS      current
    DESCRIPTION
        "The value of tmnxOamPingCtlTrapGeneration specifies the
         notification(s) to send for a test run.

         Each bit enables the transmission of one notification, as follows.
         'probeFailure(0)':  send one tmnxOamPingProbeFailedV3 notification if
            at least M successive probes failed during the test run.  M is
            configured using tmnxOamPingCtlTrapProbeFailureFilter.
         'testFailure(1)':  send one tmnxOamPingTestFailedV3 notification if at
            least N probes failed during the test run.  N is configured using
            tmnxOamPingCtlTrapTestFailureFilter.
         'testCompletion(2)':  send one tmnxOamPingTestCompletedV3 notification
            when the test run is complete."
    DEFVAL      { {} }
    ::= { tmnxOamPingCtlEntry 25 }

tmnxOamPingCtlTrapProbeFailureFilter OBJECT-TYPE
    SYNTAX      Unsigned32 (0..15)
    MAX-ACCESS  read-create
    STATUS      current
    DESCRIPTION
        "The value of tmnxOamPingCtlTrapProbeFailureFilter specifies the
         threshold for generating a tmnxOamPingProbeFailedV3 notification.

         The semantics are explained in the tmnxOamPingProbeFailedV3
         DESCRIPTION clause."
    DEFVAL      { 1 }
    ::= { tmnxOamPingCtlEntry 26 }

tmnxOamPingCtlTrapTestFailureFilter OBJECT-TYPE
    SYNTAX      Unsigned32 (0..15)
    MAX-ACCESS  read-create
    STATUS      current
    DESCRIPTION
        "The value of tmnxOamPingCtlTrapTestFailureFilter specifies the
         threshold for generating a tmnxOamPingTestFailedV3 notification.

         The semantics are explained in the tmnxOamPingTestFailedV3 DESCRIPTION
         clause."
    DEFVAL      { 1 }
    ::= { tmnxOamPingCtlEntry 27 }

tmnxOamPingCtlSAA                OBJECT-TYPE
    SYNTAX      TruthValue
    MAX-ACCESS  read-create
    STATUS      current
    DESCRIPTION
        "The value of tmnxOamPingCtlSAA specifies if this test is an SAA test
         (Service Assurance Agent; 'true'), or an OAM test ('false').  If
         there is a tmnxOamSaaCtlTable row with the specified index values,
         'true' is returned.  Otherwise, 'false' is returned."
    DEFVAL      { false }
    ::= { tmnxOamPingCtlEntry 28 }

tmnxOamPingCtlRuns               OBJECT-TYPE
    SYNTAX      Counter32
    MAX-ACCESS  read-only
    STATUS      current
    DESCRIPTION
        "The value of tmnxOamPingCtlRuns indicates the number of times this OAM
         ping test has been executed."
    ::= { tmnxOamPingCtlEntry 29 }

tmnxOamPingCtlFailures           OBJECT-TYPE
    SYNTAX      Counter32
    MAX-ACCESS  read-only
    STATUS      current
    DESCRIPTION
        "The value of tmnxOamPingCtlFailures indicates the number of times this
         OAM ping test has failed."
    ::= { tmnxOamPingCtlEntry 30 }

tmnxOamPingCtlLastRunResult      OBJECT-TYPE
    SYNTAX      TmnxOamTestResult
    MAX-ACCESS  read-only
    STATUS      current
    DESCRIPTION
        "The value of tmnxOamPingCtlLastRunResult indicates the completion
         status the last time this test was executed.  If this OAM test is
         currently in progress, this object indicates the result of the
         previous test run, if any."
    ::= { tmnxOamPingCtlEntry 31 }

tmnxOamPingCtlLastChanged        OBJECT-TYPE
    SYNTAX      TimeStamp
    MAX-ACCESS  read-only
    STATUS      current
    DESCRIPTION
        "The value of tmnxOamPingCtlLastChanged indicates the time the value of
         a settable object in this row was last changed."
    ::= { tmnxOamPingCtlEntry 32 }

tmnxOamPingCtlVRtrID             OBJECT-TYPE
    SYNTAX      TmnxVRtrID
    MAX-ACCESS  read-create
    STATUS      current
    DESCRIPTION
        "The value of tmnxOamPingCtlVRtrID specifies the virtual router to be
         used for the test.  The value specified must be the index of an active
         row in TIMETRA-VRTR-MIB::vRtrConfTable (i.e. tmnxOamPingCtlVRtrID must
         match a valid TIMETRA-VRTR-MIB::vRtrID value).

         This object is applicable if tmnxOamPingCtlTestMode is 'icmpPing',
         'mrInfo', or 'p2mpLspPing'.

         The table below shows the system-configured vRtrID values, and whether
         or not the vRtrID value can be configured as a tmnxOamPingCtlVRtrID
         value.
                                   Supported for  Supported for  Supported for
         vRtrID   vRtrName         'icmpPing' ?   'mrInfo' ?     'p2mpLspPing' ?
         ------   ---------------  -------------  -------------  ---------------
         1        Base             Yes            Yes            Yes
         4094     vpls-management  Yes            No             No
         4095     management       Yes            No             No

         When directing an 'icmpPing', 'mrInfo', or 'p2mpLspPing' test to use a
         virtual router associated with a VPRN service, the virtual router can
         be specified using tmnxOamPingCtlVRtrID (with the VPRN's virtual router
         number) or tmnxOamPingCtlServiceId (with the VPRN's service number).
         tmnxOamPingCtlServiceId is preferred, because service numbers are
         constant across an SROS reboot (while virtual routers may be
         renumbered).  If non-default values are specified for both
         tmnxOamPingCtlVRtrID and tmnxOamPingCtlServiceId,
         tmnxOamPingCtlServiceId is used.

         Setting this object is optional."
    DEFVAL      { 1 }
    ::= { tmnxOamPingCtlEntry 33 }

tmnxOamPingCtlTgtAddrType        OBJECT-TYPE
    SYNTAX      InetAddressType
    MAX-ACCESS  read-create
    STATUS      current
    DESCRIPTION
        "The value of tmnxOamPingCtlTgtAddrType specifies the address type of
         tmnxOamPingCtlTgtAddress.

         The values which can be used as part of a successful test depend on
         tmnxOamPingCtlTestMode, as follows.

         Test Mode                    tmnxOamPingCtlTgtAddrType Values Supported
         -----------       -----------------------------------------------------
         'cpePing'                      'ipv4(1)'
         'dnsPing'                      'ipv4(1)' 'ipv6(2)'
         'icmpPing'                     'ipv4(1)' 'ipv6(2)' 'ipv6z(4)' 'dns(16)'
         'mfibPing'                     'ipv4(1)' 'ipv6(2)'
         'mrInfo'                       'ipv4(1)'                      'dns(16)'
         'svcPing'                      'ipv4(1)'
         'vccvPing'        'unknown(0)' 'ipv4(1)'
         'vprnPing'                     'ipv4(1)' 'ipv6(2)'
         'vxlanPing'                    'ipv4(1)'
         otherwise         'unknown(0)'"
    DEFVAL      { unknown }
    ::= { tmnxOamPingCtlEntry 34 }

tmnxOamPingCtlTgtAddress         OBJECT-TYPE
    SYNTAX      InetAddress
    MAX-ACCESS  read-create
    STATUS      current
    DESCRIPTION
        "The value of tmnxOamPingCtlTgtAddress specifies the destination host
         address to be used when performing an OAM ping operation.  The
         corresponding address type is configured using
         tmnxOamPingCtlTgtAddrType.

         For 'dnsPing' this is the address of the DNS server host that will be
         asked to resolve the DNS name specified by tmnxOamPingCtlDnsName."
    DEFVAL      { ''H }
    ::= { tmnxOamPingCtlEntry 35 }

tmnxOamPingCtlSrcAddrType        OBJECT-TYPE
    SYNTAX      InetAddressType
    MAX-ACCESS  read-create
    STATUS      current
    DESCRIPTION
        "The value of tmnxOamPingCtlSrcAddrType specifies the address type of
         tmnxOamPingCtlSrcAddress.

         Only 'ipv4' and 'ipv6' address types are supported."
    DEFVAL      { unknown }
    ::= { tmnxOamPingCtlEntry 36 }

tmnxOamPingCtlSrcAddress         OBJECT-TYPE
    SYNTAX      InetAddress (SIZE (0|4|16))
    MAX-ACCESS  read-create
    STATUS      current
    DESCRIPTION
        "The value of tmnxOamPingCtlSrcAddress specifies the source IP host
         address to be used when performing an OAM ping operation.  The
         corresponding address type is configured using
         tmnxOamPingCtlSrcAddrType.

         This is an optional parameter.  It is used when tmnxOamPingCtlTestMode
         is 'icmpPing', 'dnsPing', 'lspPing', 'p2mpLspPing' (LDP), or
         'vccvPing'."
    DEFVAL      { ''H }
    ::= { tmnxOamPingCtlEntry 37 }

tmnxOamPingCtlDnsName            OBJECT-TYPE
    SYNTAX      OCTET STRING (SIZE (0..255))
    MAX-ACCESS  read-create
    STATUS      current
    DESCRIPTION
        "The value of tmnxOamPingCtlDnsName specifies the DNS name to be
         resolved to an IP address.

         This object is required for 'dnsPing'."
    DEFVAL      { ''H }
    ::= { tmnxOamPingCtlEntry 38 }

tmnxOamPingCtlDNSRecord          OBJECT-TYPE
    SYNTAX      INTEGER {
        ipv4Arecord    (1),
        ipv6AAAArecord (2)
    }
    MAX-ACCESS  read-create
    STATUS      current
    DESCRIPTION
        "The value of tmnxOamPingCtlDNSRecord specifies which DNS record is to
         be retrieved in this test."
    DEFVAL      { ipv4Arecord }
    ::= { tmnxOamPingCtlEntry 39 }

tmnxOamPingCtlIntervalUnits      OBJECT-TYPE
    SYNTAX      INTEGER {
        seconds      (1),
        centiseconds (2)
    }
    MAX-ACCESS  read-create
    STATUS      current
    DESCRIPTION
        "The value of tmnxOamPingCtlIntervalUnits specifies the units for
         tmnxOamPingCtlInterval.  For example, if tmnxOamPingCtlIntervalUnits
         has the value 'centiseconds(2)', and tmnxOamPingCtlInterval has the
         value 10, the test's interval is 0.1 seconds.

         The supported combinations of tmnxOamPingCtlIntervalUnits,
         tmnxOamPingCtlInterval, tmnxOamPingCtlTestMode, and
         tmnxOamIcmpPingCtlRapid are specified in the tmnxOamPingCtlInterval
         DESCRIPTION clause.

         The interaction between this object and tmnxOamIcmpPingCtlRapid is
         specified in the tmnxOamIcmpPingCtlRapid DESCRIPTION clause."
    DEFVAL      { seconds }
    ::= { tmnxOamPingCtlEntry 40 }

tmnxOamPingCtlSubscriberName     OBJECT-TYPE
    SYNTAX      TNamedItemOrEmpty
    MAX-ACCESS  read-create
    STATUS      current
    DESCRIPTION
        "The value of tmnxOamPingCtlSubscriberName specifies the name of the
         subscriber to be pinged.

         When a non-default value for this object is specified, a Layer-2-Aware
         Network Address Translation (NAT) ping is requested.  The subscriber
         name and the target IP address (i.e. tmnxOamPingCtlTgtAddress) are used
         together to ping the subscriber's device.

         A valid Layer-2-Aware NAT ping must satisfy all of the following
         conditions.
         1.  tmnxOamPingCtlSubscriberName is a valid subscriber name.
         2.  The test type (i.e. tmnxOamPingCtlTestMode) is 'icmpPing'.
         3.  The test is not an SAA test (as configured using
             tmnxOamSaaCtlRowStatus).
         4.  The target address type (as configured using
             tmnxOamPingCtlTgtAddrType) is 'ipv4(1)'.
         5.  The value of each of the following objects is default:
             tmnxOamIcmpPingCtlBypassRouting,
             tmnxOamIcmpPingCtlEgrIfIndex,
             tmnxOamIcmpPingCtlEgrIfName,
             tmnxOamIcmpPingCtlNhAddrType,
             tmnxOamIcmpPingCtlRapid."
    REFERENCE
        "IETF draft-miles-behave-l2nat-00, 'Layer2-Aware NAT', March 4, 2009"
    DEFVAL      { ''H }
    ::= { tmnxOamPingCtlEntry 41 }

tmnxOamPingResultsTable          OBJECT-TYPE
    SYNTAX      SEQUENCE OF TmnxOamPingResultsEntry
    MAX-ACCESS  not-accessible
    STATUS      current
    DESCRIPTION
        "Defines the OAM Ping Results Table for providing
         the capability of performing OAM ping operations.  The
         results of these operations are stored in the
         tmnxOamPingResultsTable and the tmnxOamPingHistoryTable.

         An entry is added to the tmnxOamPingResultsTable when an
         tmnxOamPingCtlEntry is started by successful transition of its
         tmnxOamPingCtlAdminStatus object to enabled(1).

         An entry is removed from the tmnxOamPingResultsTable when its
         corresponding tmnxOamPingCtlEntry is deleted."
    ::= { tmnxOamPingObjs 4 }

tmnxOamPingResultsEntry          OBJECT-TYPE
    SYNTAX      TmnxOamPingResultsEntry
    MAX-ACCESS  not-accessible
    STATUS      current
    DESCRIPTION
        "Defines an entry in the tmnxOamPingResultsTable.  The
         tmnxOamPingResultsTable has the same indexing as the
         tmnxOamPingCtlTable in order for a tmnxOamPingResultsEntry to
         correspond to the tmnxOamPingCtlEntry that caused it to
         be created.

         An entry in this table summarizes results from multiple invocations of
         the test configured by the corresponding entry in tmnxOamPingCtlTable."
    INDEX       {
        tmnxOamPingCtlOwnerIndex,
        tmnxOamPingCtlTestIndex,
        tmnxOamPingResultsTestRunIndex
    }
    ::= { tmnxOamPingResultsTable 1 }

TmnxOamPingResultsEntry          ::= SEQUENCE
{
    tmnxOamPingResultsOperStatus     INTEGER,
    tmnxOamPingResultsMinRtt         Unsigned32,
    tmnxOamPingResultsMaxRtt         Unsigned32,
    tmnxOamPingResultsAverageRtt     Unsigned32,
    tmnxOamPingResultsRttSumOfSquares Unsigned32,
    tmnxOamPingResultsMtuResponseSize Unsigned32,
    tmnxOamPingResultsSvcPing        INTEGER,
    tmnxOamPingResultsProbeResponses Unsigned32,
    tmnxOamPingResultsSentProbes     Unsigned32,
    tmnxOamPingResultsLastGoodProbe  DateAndTime,
    tmnxOamPingResultsLastRespHeader OCTET STRING,
    tmnxOamPingResultsMinTt          Integer32,
    tmnxOamPingResultsMaxTt          Integer32,
    tmnxOamPingResultsAverageTt      Integer32,
    tmnxOamPingResultsTtSumOfSquares Unsigned32,
    tmnxOamPingResultsMinInTt        Integer32,
    tmnxOamPingResultsMaxInTt        Integer32,
    tmnxOamPingResultsAverageInTt    Integer32,
    tmnxOamPingResultsInTtSumOfSqrs  Unsigned32,
    tmnxOamPingResultsOutJitter      Integer32,
    tmnxOamPingResultsInJitter       Integer32,
    tmnxOamPingResultsRtJitter       Integer32,
    tmnxOamPingResultsProbeTimeouts  Unsigned32,
    tmnxOamPingResultsProbeFailures  Unsigned32,
    tmnxOamPingResultsTestRunIndex   Unsigned32,
    tmnxOamPingResultsRttOFSumSquares Counter32,
    tmnxOamPingResultsRttHCSumSquares Counter64,
    tmnxOamPingResultsTtOFSumSquares Counter32,
    tmnxOamPingResultsTtHCSumSquares Counter64,
    tmnxOamPingResultsInTtOFSumSqrs  Counter32,
    tmnxOamPingResultsInTtHCSumSqrs  Counter64,
    tmnxOamPingResultsTestRunResult  TmnxOamTestResult,
    tmnxOamPingResultsOutOfOrder     Counter32
}

tmnxOamPingResultsOperStatus     OBJECT-TYPE
    SYNTAX      INTEGER {
        enabled  (1),
        disabled (2)
    }
    MAX-ACCESS  read-only
    STATUS      current
    DESCRIPTION
        "Reflects the operational state of a tmnxOamPingCtlEntry:
         enabled(1)   - Test is active.
         disabled(2)  - Test has stopped."
    ::= { tmnxOamPingResultsEntry 1 }

tmnxOamPingResultsMinRtt         OBJECT-TYPE
    SYNTAX      Unsigned32
    UNITS       "microseconds"
    MAX-ACCESS  read-only
    STATUS      current
    DESCRIPTION
        "The minimum OAM ping round-trip-time (RTT) received.

         This value is relevant when tmnxOamPingCtlTestMode has a value of
         'sdpPing', 'ethCfmLoopback', 'ethCfmTwoWayDelay', or
         'ethCfmTwoWaySlm'. Otherwise, this object contains a value of 0."
    ::= { tmnxOamPingResultsEntry 4 }

tmnxOamPingResultsMaxRtt         OBJECT-TYPE
    SYNTAX      Unsigned32
    UNITS       "microseconds"
    MAX-ACCESS  read-only
    STATUS      current
    DESCRIPTION
        "The maximum OAM ping round-trip-time (RTT) received. A value of 0 for
         this object implies that no RTT has been received.

         This value is relevant when tmnxOamPingCtlTestMode has a value of
         'sdpPing', 'ethCfmLoopback', 'ethCfmTwoWayDelay', or
         'ethCfmTwoWaySlm'. Otherwise, this object contains a value of 0."
    ::= { tmnxOamPingResultsEntry 5 }

tmnxOamPingResultsAverageRtt     OBJECT-TYPE
    SYNTAX      Unsigned32
    UNITS       "microseconds"
    MAX-ACCESS  read-only
    STATUS      current
    DESCRIPTION
        "The current average OAM ping round-trip-time (RTT).

         This value is relevant when tmnxOamPingCtlTestMode has a value of
         'sdpPing', 'ethCfmLoopback', 'ethCfmTwoWayDelay', or
         'ethCfmTwoWaySlm'. Otherwise, this object contains a value of 0."
    ::= { tmnxOamPingResultsEntry 6 }

tmnxOamPingResultsRttSumOfSquares OBJECT-TYPE
    SYNTAX      Unsigned32
    UNITS       "microseconds squared"
    MAX-ACCESS  read-only
    STATUS      current
    DESCRIPTION
        "The value of tmnxOamPingResultsRttSumOfSquares indicates the least
         significant 32 bits of tmnxOamPingResultsRttHCSumSquares."
    ::= { tmnxOamPingResultsEntry 7 }

tmnxOamPingResultsMtuResponseSize OBJECT-TYPE
    SYNTAX      Unsigned32
    UNITS       "Octets"
    MAX-ACCESS  read-only
    STATUS      current
    DESCRIPTION
        "This object contains the largest size OAM Echo request message that
         received a valid reply.

         The value of this object MUST be reported as 0 when no ping responses
         have been received or an active test has not yet timed out.  When
         tmnxOamPingCtlTestMode does not have a value of 'mtuPing', this object
         is not relevant and should contain a value of 0."
    ::= { tmnxOamPingResultsEntry 8 }

tmnxOamPingResultsSvcPing        OBJECT-TYPE
    SYNTAX      INTEGER {
        undetermined (0),
        failed       (1),
        success      (2)
    }
    MAX-ACCESS  read-only
    STATUS      current
    DESCRIPTION
        "The object contains the final results of an OAM 'svcPing' test.
         The value of this object MUST be reported as 0 when no ping responses
         have been received or an active test has not yet timed out.  When
         tmnxOamPingCtlTestMode does not have a value of 'svcPing', this object
         is not relevant and should contain a value of 0."
    ::= { tmnxOamPingResultsEntry 9 }

tmnxOamPingResultsProbeResponses OBJECT-TYPE
    SYNTAX      Unsigned32
    UNITS       "responses"
    MAX-ACCESS  read-only
    STATUS      current
    DESCRIPTION
        "Number of responses received for the corresponding
         tmnxOamPingCtlEntry and tmnxOamPingResultsEntry.  The value of
         this object MUST be reported as 0 when no probe responses have
         been received."
    ::= { tmnxOamPingResultsEntry 10 }

tmnxOamPingResultsSentProbes     OBJECT-TYPE
    SYNTAX      Unsigned32
    UNITS       "probes"
    MAX-ACCESS  read-only
    STATUS      current
    DESCRIPTION
        "The value of this object reflects the number of probes sent for the
         corresponding tmnxOamPingCtlEntry and tmnxOamPingResultsEntry. The
         value of this object MUST be reported as 0 when no probes have been
         sent."
    ::= { tmnxOamPingResultsEntry 11 }

tmnxOamPingResultsLastGoodProbe  OBJECT-TYPE
    SYNTAX      DateAndTime
    MAX-ACCESS  read-only
    STATUS      current
    DESCRIPTION
        "Date and time when the last response was received for
         an OAM probe.  If a response has not been received,
         '1970-1-1,0:0:0.0,+0:0' is returned."
    ::= { tmnxOamPingResultsEntry 12 }

tmnxOamPingResultsLastRespHeader OBJECT-TYPE
    SYNTAX      OCTET STRING (SIZE (100))
    MAX-ACCESS  read-only
    STATUS      obsolete
    DESCRIPTION
        "A copy of the OAM header of the last response packet received for
         this OAM ping test.  The value of this object MUST be reported
         as 0 when no probes have been sent.

         This object was obsoleted in release 8.0R1 and replaced with
         tmnxOamPingHistoryRespHdr in tmnxOamPingHistoryTable."
    ::= { tmnxOamPingResultsEntry 13 }

tmnxOamPingResultsMinTt          OBJECT-TYPE
    SYNTAX      Integer32
    UNITS       "microseconds"
    MAX-ACCESS  read-only
    STATUS      current
    DESCRIPTION
        "The minimum OAM ping outbound one-way trip time received. A value of 0
         for this object implies that no one-way trip time measurement is
         available."
    ::= { tmnxOamPingResultsEntry 14 }

tmnxOamPingResultsMaxTt          OBJECT-TYPE
    SYNTAX      Integer32
    UNITS       "microseconds"
    MAX-ACCESS  read-only
    STATUS      current
    DESCRIPTION
        "The maximum OAM ping outbound one-way trip time received. A value of 0
         for this object implies that no one-way trip time measurement is
         available."
    ::= { tmnxOamPingResultsEntry 15 }

tmnxOamPingResultsAverageTt      OBJECT-TYPE
    SYNTAX      Integer32
    UNITS       "microseconds"
    MAX-ACCESS  read-only
    STATUS      current
    DESCRIPTION
        "The current average OAM ping outbound one-way trip time. A value of 0
         for this object implies that no one-way trip time measurement is
         available."
    ::= { tmnxOamPingResultsEntry 16 }

tmnxOamPingResultsTtSumOfSquares OBJECT-TYPE
    SYNTAX      Unsigned32
    UNITS       "microseconds squared"
    MAX-ACCESS  read-only
    STATUS      current
    DESCRIPTION
        "The value of tmnxOamPingResultsTtSumOfSquares indicates the least
         significant 32 bits of tmnxOamPingResultsTtHCSumSquares."
    ::= { tmnxOamPingResultsEntry 17 }

tmnxOamPingResultsMinInTt        OBJECT-TYPE
    SYNTAX      Integer32
    UNITS       "microseconds"
    MAX-ACCESS  read-only
    STATUS      current
    DESCRIPTION
        "The minimum OAM ping inbound one-way trip time received.

         A value of 0 for this object implies that no one-way trip time
         measurement is available."
    ::= { tmnxOamPingResultsEntry 18 }

tmnxOamPingResultsMaxInTt        OBJECT-TYPE
    SYNTAX      Integer32
    UNITS       "microseconds"
    MAX-ACCESS  read-only
    STATUS      current
    DESCRIPTION
        "The maximum OAM ping inbound one-way trip time received.

         A value of 0 for this object implies that no one-way trip time
         measurement is available."
    ::= { tmnxOamPingResultsEntry 19 }

tmnxOamPingResultsAverageInTt    OBJECT-TYPE
    SYNTAX      Integer32
    UNITS       "microseconds"
    MAX-ACCESS  read-only
    STATUS      current
    DESCRIPTION
        "The current average OAM ping inbound one-way trip time.

         A value of 0 for this object implies that no one-way trip time
         measurement is available."
    ::= { tmnxOamPingResultsEntry 20 }

tmnxOamPingResultsInTtSumOfSqrs  OBJECT-TYPE
    SYNTAX      Unsigned32
    UNITS       "microseconds squared"
    MAX-ACCESS  read-only
    STATUS      current
    DESCRIPTION
        "The value of tmnxOamPingResultsInTtSumOfSqrs indicates the least
         significant 32 bits of tmnxOamPingResultsInTtHCSumSqrs."
    ::= { tmnxOamPingResultsEntry 21 }

tmnxOamPingResultsOutJitter      OBJECT-TYPE
    SYNTAX      Integer32
    UNITS       "microseconds"
    MAX-ACCESS  read-only
    STATUS      current
    DESCRIPTION
        "The value of tmnxOamPingResultsOutJitter indicates the amount of
         one-way trip jitter, expressed in microseconds, for a ping probe
         request packet sent for this OAM test.

         A value of 0 for this object implies that no one-way trip jitter
         measurement is available."
    ::= { tmnxOamPingResultsEntry 22 }

tmnxOamPingResultsInJitter       OBJECT-TYPE
    SYNTAX      Integer32
    UNITS       "microseconds"
    MAX-ACCESS  read-only
    STATUS      current
    DESCRIPTION
        "The value of tmnxOamPingResultsInJitter indicates the amount of
         one-way trip jitter, expressed in microseconds, for a ping probe
         response packet received for this OAM test.

         A value of 0 for this object implies that no one-way trip jitter
         measurement is available."
    ::= { tmnxOamPingResultsEntry 23 }

tmnxOamPingResultsRtJitter       OBJECT-TYPE
    SYNTAX      Integer32
    UNITS       "microseconds"
    MAX-ACCESS  read-only
    STATUS      current
    DESCRIPTION
        "The value of tmnxOamPingResultsRtJitter indicates the amount of
         two-way trip jitter, expressed in microseconds, for a ping probe sent
         for this OAM test.

         A value of 0 for this object implies that no two-way-trip jitter
         measurement is available."
    ::= { tmnxOamPingResultsEntry 24 }

tmnxOamPingResultsProbeTimeouts  OBJECT-TYPE
    SYNTAX      Unsigned32
    MAX-ACCESS  read-only
    STATUS      current
    DESCRIPTION
        "The value of tmnxOamPingResultsProbeTimeouts indicates the number of
         probes timed out without receiving a response."
    ::= { tmnxOamPingResultsEntry 25 }

tmnxOamPingResultsProbeFailures  OBJECT-TYPE
    SYNTAX      Unsigned32
    MAX-ACCESS  read-only
    STATUS      current
    DESCRIPTION
        "The value of tmnxOamPingResultsProbeFailures indicates the total
         number of probes that failed to be transmitted plus the number of
         probes that timed out without receiving a response."
    ::= { tmnxOamPingResultsEntry 26 }

tmnxOamPingResultsTestRunIndex   OBJECT-TYPE
    SYNTAX      Unsigned32 (1..4294967295)
    MAX-ACCESS  not-accessible
    STATUS      current
    DESCRIPTION
        "The value of tmnxOamPingResultsTestRunIndex identifies the row entry
         that reports results for a single OAM test run.

         The agent starts assigning tmnxOamPingResultsTestRunIndex values at 1
         and wraps after exceeding the maximum possible value as defined by the
         limit of this object."
    ::= { tmnxOamPingResultsEntry 27 }

tmnxOamPingResultsRttOFSumSquares OBJECT-TYPE
    SYNTAX      Counter32
    MAX-ACCESS  read-only
    STATUS      current
    DESCRIPTION
        "The value of tmnxOamPingResultsRttOFSumSquares indicates the number of
         times tmnxOamPingResultsRttSumOfSquares overflowed."
    ::= { tmnxOamPingResultsEntry 28 }

tmnxOamPingResultsRttHCSumSquares OBJECT-TYPE
    SYNTAX      Counter64
    UNITS       "microseconds squared"
    MAX-ACCESS  read-only
    STATUS      current
    DESCRIPTION
        "The value of tmnxOamPingResultsRttHCSumSquares indicates the sum of
         squares of the round trip times of the ping test.  Its purpose is to
         enable the standard deviation calculation.

         The value of this object will be reported as 0 when one or more of the
         following conditions apply:
         1.  No round trip time measurement is available.
         2.  The test stopped before completion.
         3.  The test type (i.e. tmnxOamPingCtlTestMode) is one of the
             following:
             'ancpLoopback',
             'atmPing',
             'macPopulate',
             'macPurge',
             'mfibPing',
             'mrInfo',
             'mtuPing',
             'p2mpLspPing',
             'svcPing."
    ::= { tmnxOamPingResultsEntry 29 }

tmnxOamPingResultsTtOFSumSquares OBJECT-TYPE
    SYNTAX      Counter32
    MAX-ACCESS  read-only
    STATUS      current
    DESCRIPTION
        "The value of tmnxOamPingResultsTtOFSumSquares indicates the number of
         times tmnxOamPingResultsTtSumOfSquares overflowed."
    ::= { tmnxOamPingResultsEntry 30 }

tmnxOamPingResultsTtHCSumSquares OBJECT-TYPE
    SYNTAX      Counter64
    UNITS       "microseconds squared"
    MAX-ACCESS  read-only
    STATUS      current
    DESCRIPTION
        "The value of tmnxOamPingResultsTtHCSumSquares indicates the sum of
         squares of the outbound one-way trip times of the ping test.  Its
         purpose is to enable the standard deviation calculation.

         The value of this object will be reported as 0 when one or more of the
         following conditions apply:
         1.  No outbound one-way trip time measurement is available.
         2.  The test stopped before completion.
         3.  The test type (i.e. tmnxOamPingCtlTestMode) is one of the
             following:
             'ancpLoopback',
             'atmPing',
             'cpePing' (sum of squares supported for round trip, not outbound),
             'dnsPing' (sum of squares supported for round trip, not outbound),
             'macPopulate',
             'macPurge',
             'mfibPing',
             'mrInfo',
             'mtuPing',
             'p2mpLspPing',
             'svcPing."
    ::= { tmnxOamPingResultsEntry 31 }

tmnxOamPingResultsInTtOFSumSqrs  OBJECT-TYPE
    SYNTAX      Counter32
    MAX-ACCESS  read-only
    STATUS      current
    DESCRIPTION
        "The value of tmnxOamPingResultsInTtOFSumSqrs indicates the number of
         times tmnxOamPingResultsInTtSumOfSqrs overflowed."
    ::= { tmnxOamPingResultsEntry 32 }

tmnxOamPingResultsInTtHCSumSqrs  OBJECT-TYPE
    SYNTAX      Counter64
    UNITS       "microseconds squared"
    MAX-ACCESS  read-only
    STATUS      current
    DESCRIPTION
        "The value of tmnxOamPingResultsInTtHCSumSqrs indicates the sum of
         squares of the inbound one-way trip times of the ping test.  Its
         purpose is to enable the standard deviation calculation.

         The value of this object will be reported as 0 when one or more of the
         following conditions apply:
         1.  No inbound one-way trip time measurement is available.
         2.  The test stopped before completion.
         3.  The test type (i.e. tmnxOamPingCtlTestMode) is one of the
             following:
             'ancpLoopback',
             'atmPing',
             'cpePing' (sum of squares supported for round trip, not inbound),
             'dnsPing' (sum of squares supported for round trip, not inbound),
             'macPopulate',
             'macPurge',
             'mfibPing',
             'mrInfo',
             'mtuPing',
             'p2mpLspPing',
             'svcPing."
    ::= { tmnxOamPingResultsEntry 33 }

tmnxOamPingResultsTestRunResult  OBJECT-TYPE
    SYNTAX      TmnxOamTestResult
    MAX-ACCESS  read-only
    STATUS      current
    DESCRIPTION
        "The object contains the overall state of the ping test."
    ::= { tmnxOamPingResultsEntry 34 }

tmnxOamPingResultsOutOfOrder     OBJECT-TYPE
    SYNTAX      Counter32
    UNITS       "reply PDUs"
    MAX-ACCESS  read-only
    STATUS      current
    DESCRIPTION
        "The value of tmnxOamPingResultsOutOfOrder indicates the number of
         reply PDUs for the specified test run that have arrived out of order.

         For example, if two probes are sent during the test run (as configured
         using tmnxOamPingCtlProbeCount), and the two reply PDUs arrive out of
         order, tmnxOamPingResultsOutOfOrder is 2.

         This value is supported when tmnxOamPingCtlTestMode is 'vxlanPing'.
         Zero is returned for all other test types."
    ::= { tmnxOamPingResultsEntry 35 }

tmnxOamPingHistoryTable          OBJECT-TYPE
    SYNTAX      SEQUENCE OF TmnxOamPingHistoryEntry
    MAX-ACCESS  not-accessible
    STATUS      current
    DESCRIPTION
        "Defines a table for storing the results of an OAM ping
         probe operation. The probe results for all OAM ping test types
         are saved in this table except for 'macPing'.  The 'macPing'
         results are saved in the tmnxOamMacPingHistoryTable.

         For a configured test, this table will hold the results for up to 3
         runs.

         An entry in this table is created when the result of an OAM ping
         probe is determined.  An entry is removed from this table when
         its corresponding tmnxOamPingCtlEntry is deleted."
    ::= { tmnxOamPingObjs 5 }

tmnxOamPingHistoryEntry          OBJECT-TYPE
    SYNTAX      TmnxOamPingHistoryEntry
    MAX-ACCESS  not-accessible
    STATUS      current
    DESCRIPTION
        "Defines an entry in the tmnxOamPingHistoryTable.
         The first two index elements identify the tmnxOamPingCtlEntry
         that a tmnxOamPingHistoryEntry belongs to.  The third index
         identifies a specific OAM test run.  The fourth index
         element selects a single OAM probe result."
    INDEX       {
        tmnxOamPingCtlOwnerIndex,
        tmnxOamPingCtlTestIndex,
        tmnxOamPingResultsTestRunIndex,
        tmnxOamPingHistoryIndex
    }
    ::= { tmnxOamPingHistoryTable 1 }

TmnxOamPingHistoryEntry          ::= SEQUENCE
{
    tmnxOamPingHistoryIndex          Unsigned32,
    tmnxOamPingHistoryResponse       Unsigned32,
    tmnxOamPingHistoryOneWayTime     Integer32,
    tmnxOamPingHistorySize           Unsigned32,
    tmnxOamPingHistoryStatus         TmnxOamResponseStatus,
    tmnxOamPingHistoryTime           DateAndTime,
    tmnxOamPingHistoryReturnCode     TmnxOamPingRtnCode,
    tmnxOamPingHistorySrcIpAddress   IpAddress,
    tmnxOamPingHistAddressType       TmnxOamAddressType,
    tmnxOamPingHistSapId             TmnxStrSapId,
    tmnxOamPingHistoryVersion        Unsigned32,
    tmnxOamPingHistoryCpeMacAddr     MacAddress,
    tmnxOamPingHistoryRespSvcId      TmnxServId,
    tmnxOamPingHistorySequence       Unsigned32,
    tmnxOamPingHistoryIfIndex        InterfaceIndexOrZero,
    tmnxOamPingHistoryDataLen        Unsigned32,
    tmnxOamPingHistoryRespPlane      TmnxOamTestResponsePlane,
    tmnxOamPingHistoryReqHdr         OCTET STRING,
    tmnxOamPingHistoryRespHdr        OCTET STRING,
    tmnxOamPingHistoryDnsAddrType    InetAddressType,
    tmnxOamPingHistoryDnsAddress     InetAddress,
    tmnxOamPingHistorySrcAddrType    InetAddressType,
    tmnxOamPingHistorySrcAddress     InetAddress,
    tmnxOamPingHistoryInOneWayTime   Integer32,
    tmnxOamPingHistoryLspName        TLNamedItemOrEmpty,
    tmnxOamPingHistNextHopAddrType   InetAddressType,
    tmnxOamPingHistNextHopAddress    InetAddress,
    tmnxOamPingHistorySrcGlobalId    TmnxMplsTpGlobalID,
    tmnxOamPingHistorySrcNodeId      TmnxMplsTpNodeID,
    tmnxOamPingHistorySdpBindId      TNamedItemOrEmpty,
    tmnxOamPingHistoryRtrnSubcode    Unsigned32,
    tmnxOamPingHistoryNetworkIfName  TNamedItemOrEmpty
}

tmnxOamPingHistoryIndex          OBJECT-TYPE
    SYNTAX      Unsigned32 (1..4294967295)
    MAX-ACCESS  not-accessible
    STATUS      current
    DESCRIPTION
        "An entry in this table is created when the result of
         a OAM ping probe is determined.  The initial 2 instance
         identifier index values identify the tmnxOamPingCtlEntry
         that a OAM probe result (tmnxOamPingHistoryEntry) belongs
         to.  The tmnxOamPingHistoryIndex element selects a single OAM
         probe result.
         The agent starts assigning tmnxOamPingHistoryIndex values at 1
         and wraps after exceeding the maximum possible value as defined by
         the limit of this object."
    ::= { tmnxOamPingHistoryEntry 1 }

tmnxOamPingHistoryResponse       OBJECT-TYPE
    SYNTAX      Unsigned32
    UNITS       "microseconds"
    MAX-ACCESS  read-only
    STATUS      current
    DESCRIPTION
        "The amount of time measured in microseconds from when
         a OAM probe was sent to when its response was received or
         when it timed out.  The value of this object is reported
         as 0 when it is not possible to transmit an OAM probe."
    ::= { tmnxOamPingHistoryEntry 2 }

tmnxOamPingHistoryOneWayTime     OBJECT-TYPE
    SYNTAX      Integer32
    UNITS       "microseconds"
    MAX-ACCESS  read-only
    STATUS      current
    DESCRIPTION
        "The amount of time measured in microseconds from when a OAM probe was
         sent to when it was received by the replier. The value of this object
         is reported as 0 when it is not possible to transmit an OAM probe or
         the information is not available."
    ::= { tmnxOamPingHistoryEntry 3 }

tmnxOamPingHistorySize           OBJECT-TYPE
    SYNTAX      Unsigned32
    UNITS       "octets"
    MAX-ACCESS  read-only
    STATUS      current
    DESCRIPTION
        "The value of tmnxOamPingHistorySize indicates the size of the OAM echo
         request transmitted for this OAM probe.  Zero is returned if no probe
         has been transmitted.

         When tmnxOamPingCtlTestMode is 'ethCfmLoopback', 'ethCfmTwoWayDelay',
         or 'ethCfmTwoWaySlm' the value returned is the size of the transmitted
         layer 2 frame (including the layer 2 header, but excluding the IEEE
         802.1Q Tag field(s)).

         For other tmnxOamPingCtlTestMode values, the size returned is the
         tmnxOamPingCtlSize value."
    REFERENCE
        "IEEE Std 802.1Q-2011, 'Media Access Control (MAC) Bridges and Virtual
         Bridge Local Area Networks', 31 August 2011, Section 9.3 'Tag format'"
    ::= { tmnxOamPingHistoryEntry 4 }

tmnxOamPingHistoryStatus         OBJECT-TYPE
    SYNTAX      TmnxOamResponseStatus
    MAX-ACCESS  read-only
    STATUS      current
    DESCRIPTION
        "The result of a particular OAM test probe."
    ::= { tmnxOamPingHistoryEntry 5 }

tmnxOamPingHistoryTime           OBJECT-TYPE
    SYNTAX      DateAndTime
    MAX-ACCESS  read-only
    STATUS      current
    DESCRIPTION
        "Time stamp for when this OAM probe result was determined."
    ::= { tmnxOamPingHistoryEntry 6 }

tmnxOamPingHistoryReturnCode     OBJECT-TYPE
    SYNTAX      TmnxOamPingRtnCode
    MAX-ACCESS  read-only
    STATUS      current
    DESCRIPTION
        "The value of tmnxOamPingHistoryReturnCode is an enumerated integer
         that indicates the OAM return code received in the OAM ping response."
    ::= { tmnxOamPingHistoryEntry 7 }

tmnxOamPingHistorySrcIpAddress   OBJECT-TYPE
    SYNTAX      IpAddress
    MAX-ACCESS  read-only
    STATUS      obsolete
    DESCRIPTION
        "Specifies the IPv4 address of the remote node that generated this
         reply to a OAM probe.

         This object was obsoleted in release 4.0 and replaced with InetAddress
         objects tmnxOamPingHistorySrcAddrType and
         tmnxOamPingHistorySrcAddress."
    ::= { tmnxOamPingHistoryEntry 8 }

tmnxOamPingHistAddressType       OBJECT-TYPE
    SYNTAX      TmnxOamAddressType
    MAX-ACCESS  read-only
    STATUS      current
    DESCRIPTION
        "The value of tmnxOamPingHistAddressType indicates the type of binding
         address information returned in response to a 'vprnPing' 'mfibPing',
         or 'cpePing' test."
    ::= { tmnxOamPingHistoryEntry 9 }

tmnxOamPingHistSapId             OBJECT-TYPE
    SYNTAX      TmnxStrSapId
    MAX-ACCESS  read-only
    STATUS      current
    DESCRIPTION
        "The value of tmnxOamPingHistSapId is the name of the access port of
         the SAP supporting the requests returned in response to a 'vprnPing',
         'mfibPing' or 'cpePing' probe.

         If the value of tmnxOamPingHistAddressType is not 'sapId', this object
         is not relevant and MUST have a null string ''."
    ::= { tmnxOamPingHistoryEntry 10 }

tmnxOamPingHistoryVersion        OBJECT-TYPE
    SYNTAX      Unsigned32
    MAX-ACCESS  read-only
    STATUS      current
    DESCRIPTION
        "The value of tmnxOamPingHistoryVersion indicates the protocol version
         for this OAM ping probe reply."
    ::= { tmnxOamPingHistoryEntry 12 }

tmnxOamPingHistoryCpeMacAddr     OBJECT-TYPE
    SYNTAX      MacAddress
    MAX-ACCESS  read-only
    STATUS      current
    DESCRIPTION
        "tmnxOamPingHistoryCpeMacAddr is set to 0 except in case of a
         'cpePing', where it contains the mac address of the replying CPE for
         this OAM ping probe reply."
    ::= { tmnxOamPingHistoryEntry 13 }

tmnxOamPingHistoryRespSvcId      OBJECT-TYPE
    SYNTAX      TmnxServId
    MAX-ACCESS  read-only
    STATUS      current
    DESCRIPTION
        "The value tmnxOamPingHistoryRespSvcId indicates for an 'mfibPing' the
         service id to which the SAP responding to the 'mfibPing' probe
         belongs. If the indicated SAP is part of the same service originating
         the probe, this value is set to 0.

         For other types of probes, this value is insignificant and is also set
         to 0."
    ::= { tmnxOamPingHistoryEntry 14 }

tmnxOamPingHistorySequence       OBJECT-TYPE
    SYNTAX      Unsigned32
    MAX-ACCESS  read-only
    STATUS      current
    DESCRIPTION
        "The value tmnxOamPingHistorySequence indicates this probe's
         sequence number.  If a probe response was received, this object
         indicates the sequence number of the response."
    ::= { tmnxOamPingHistoryEntry 15 }

tmnxOamPingHistoryIfIndex        OBJECT-TYPE
    SYNTAX      InterfaceIndexOrZero
    MAX-ACCESS  read-only
    STATUS      current
    DESCRIPTION
        "The value of tmnxOamPingHistoryIfIndex indicates the ifIndex of the
         interface that this probe was transmitted from.

         This object applies to 'lspPing' and 'vccvPing' tests.  For other test
         modes, this value is not significant and is set to 0."
    ::= { tmnxOamPingHistoryEntry 16 }

tmnxOamPingHistoryDataLen        OBJECT-TYPE
    SYNTAX      Unsigned32
    MAX-ACCESS  read-only
    STATUS      current
    DESCRIPTION
        "The value of tmnxOamPingHistoryDataLen indicates for an 'lspPing'
         the UDP data length of the echo reply, and for 'icmpPing' normally
         the length starting after the IP header of the echo reply.  For
         'ethCfmLoopback' and 'ethCfmTwoWaySlm' the value is the number of
         octets in the Value field of the Data TLV of the Ethernet CFM loopback
         packet (zero if the packet has no Data TLV).

         For other types of probes, this value is not significant and is set to
         0."
    ::= { tmnxOamPingHistoryEntry 17 }

tmnxOamPingHistoryRespPlane      OBJECT-TYPE
    SYNTAX      TmnxOamTestResponsePlane
    MAX-ACCESS  read-only
    STATUS      current
    DESCRIPTION
        "The value of tmnxOamPingHistoryRespPlane indicates the response plane
         from which this ping response was received."
    ::= { tmnxOamPingHistoryEntry 18 }

tmnxOamPingHistoryReqHdr         OBJECT-TYPE
    SYNTAX      OCTET STRING (SIZE (0|1..150))
    MAX-ACCESS  read-only
    STATUS      obsolete
    DESCRIPTION
        "The value of tmnxOamPingHistoryReqHdr is a copy of the OAM header of
         the request packet sent for this OAM ping test probe.

         The request header is reported only when tmnxOamPingCtlTestMode has a
         value of 'svcPing', 'sdpPing' 'mtuPing', 'ethCfmLoopback',
         'ethCfmTwoWayDelay', or 'ethCfmTwoWaySlm'.  Otherwise, a zero length
         OCTET STRING is returned.

         This object was marked obsolete in SROS release 10.0 R1."
    ::= { tmnxOamPingHistoryEntry 19 }

tmnxOamPingHistoryRespHdr        OBJECT-TYPE
    SYNTAX      OCTET STRING (SIZE (0|1..150))
    MAX-ACCESS  read-only
    STATUS      current
    DESCRIPTION
        "The value of tmnxOamPingHistoryRespHdr is a copy of the OAM header of
         the response packet received for this OAM ping test probe.

         The response header is reported only when tmnxOamPingCtlTestMode
         has a value of 'svcPing', 'sdpPing', 'mtuPing', 'icmpPing',
         'ethCfmLoopback', 'ethCfmTwoWayDelay', or 'ethCfmTwoWaySlm'.
         Otherwise, a zero length OCTET STRING is returned.  For 'icmpPing'
         the value reported is the received ICMP message starting from the IP
         header.

         The value of this object MUST be reported as a zero length OCTET
         STRING when no probe response has been received."
    ::= { tmnxOamPingHistoryEntry 20 }

tmnxOamPingHistoryDnsAddrType    OBJECT-TYPE
    SYNTAX      InetAddressType
    MAX-ACCESS  read-only
    STATUS      current
    DESCRIPTION
        "The value of tmnxOamPingHistoryDnsAddrType indicates the Internet
         address type stored in tmnxOamPingHistoryDnsAddress.

         If this was not a 'dnsPing' test or the DNS name specified in
         tmnxOamPingCtlDnsName could not be resolved, the value of this object
         will be reported as 'unknown(0)'."
    ::= { tmnxOamPingHistoryEntry 21 }

tmnxOamPingHistoryDnsAddress     OBJECT-TYPE
    SYNTAX      InetAddress (SIZE (0|4|16))
    MAX-ACCESS  read-only
    STATUS      current
    DESCRIPTION
        "The value of tmnxOamPingHistoryDnsAddress indicates the Internet
         address that was resolved from the name specified in
         tmnxOamPingCtlDnsName by a 'dnsPing' test.

         If this was not a 'dnsPing' test or the dns name specified in
         tmnxOamPingCtlDnsName could not be resolved, the value of this object
         will be reported as ''H (empty string)."
    ::= { tmnxOamPingHistoryEntry 22 }

tmnxOamPingHistorySrcAddrType    OBJECT-TYPE
    SYNTAX      InetAddressType
    MAX-ACCESS  read-only
    STATUS      current
    DESCRIPTION
        "The value of tmnxOamPingHistorySrcAddrType indicates the Internet
         address type of the address stored in tmnxOamPingHistorySrcAddress."
    ::= { tmnxOamPingHistoryEntry 23 }

tmnxOamPingHistorySrcAddress     OBJECT-TYPE
    SYNTAX      InetAddress (SIZE (0|4|16|20))
    MAX-ACCESS  read-only
    STATUS      current
    DESCRIPTION
        "The value of tmnxOamPingHistorySrcAddress indicates the Internet
         address of the remote node that generated this reply to a OAM probe."
    ::= { tmnxOamPingHistoryEntry 24 }

tmnxOamPingHistoryInOneWayTime   OBJECT-TYPE
    SYNTAX      Integer32
    UNITS       "microseconds"
    MAX-ACCESS  read-only
    STATUS      current
    DESCRIPTION
        "The value of tmnxOamPingHistoryInOneWayTime indicates the amount of
         time measured in microseconds from when an OAM probe reply was sent to
         when it was received by this host (in-bound one-way time). The value
         of this object is reported as 0 when the information is not available."
    ::= { tmnxOamPingHistoryEntry 25 }

tmnxOamPingHistoryLspName        OBJECT-TYPE
    SYNTAX      TLNamedItemOrEmpty
    MAX-ACCESS  read-only
    STATUS      current
    DESCRIPTION
        "The value of tmnxOamPingHistoryLspName indicates the name of the LSP
         that this probe was transmitted on.

         The empty string is returned when the test mode is not 'vccvPing'. The
         empty string is returned when the transport tunnel is not RSVP."
    ::= { tmnxOamPingHistoryEntry 26 }

tmnxOamPingHistNextHopAddrType   OBJECT-TYPE
    SYNTAX      InetAddressType
    MAX-ACCESS  read-only
    STATUS      current
    DESCRIPTION
        "The value of tmnxOamPingHistNextHopAddrType indicates the Internet
         address type of the address stored in tmnxOamPingHistNextHopAddress.

         The value 'unknown(0)' is returned when the test mode is not
         'vccvPing'."
    ::= { tmnxOamPingHistoryEntry 27 }

tmnxOamPingHistNextHopAddress    OBJECT-TYPE
    SYNTAX      InetAddress (SIZE (0|4|16|20))
    MAX-ACCESS  read-only
    STATUS      current
    DESCRIPTION
        "The value of tmnxOamPingHistNextHopAddress indicates the next hop
         Internet address that this probe was transmitted to.

         The empty string is returned when the test mode is not 'vccvPing'."
    ::= { tmnxOamPingHistoryEntry 28 }

tmnxOamPingHistorySrcGlobalId    OBJECT-TYPE
    SYNTAX      TmnxMplsTpGlobalID
    MAX-ACCESS  read-only
    STATUS      current
    DESCRIPTION
        "The value of tmnxOamPingHistorySrcGlobalId indicates the source MPLS-TP
         global identifier of the replying node.  The value is copied from the
         reply's RFC 6426 Source Identifier TLV.  If the TLV is absent, zero is
         returned.

         This value is relevant when tmnxOamPingCtlTestMode is 'lspPing' or
         'vccvPing'.  Otherwise, zero is returned."
    REFERENCE
        "RFC 6426, 'MPLS On-Demand Connectivity Verification and Route Tracing',
         Section 2.2.2, 'Source Identifier TLV'."
    ::= { tmnxOamPingHistoryEntry 29 }

tmnxOamPingHistorySrcNodeId      OBJECT-TYPE
    SYNTAX      TmnxMplsTpNodeID
    MAX-ACCESS  read-only
    STATUS      current
    DESCRIPTION
        "The value of tmnxOamPingHistorySrcNodeId indicates the source MPLS-TP
         node identifier of the replying node.  The value is copied from the
         reply's RFC 6426 Source Identifier TLV.  If the TLV is absent, zero is
         returned.

         This value is relevant when tmnxOamPingCtlTestMode is 'lspPing' or
         'vccvPing'.  Otherwise, zero is returned."
    REFERENCE
        "RFC 6426, 'MPLS On-Demand Connectivity Verification and Route Tracing',
         Section 2.2.2, 'Source Identifier TLV'."
    ::= { tmnxOamPingHistoryEntry 30 }

tmnxOamPingHistorySdpBindId      OBJECT-TYPE
    SYNTAX      TNamedItemOrEmpty
    MAX-ACCESS  read-only
    STATUS      current
    DESCRIPTION
        "The value of tmnxOamPingHistorySdpBindId indicates the SDP binding
         provided by the remote system.

         The value of tmnxOamPingHistorySdpBindId is relevant when
         tmnxOamPingHistAddressType is 'sdpBindId(9)'."
    ::= { tmnxOamPingHistoryEntry 31 }

tmnxOamPingHistoryRtrnSubcode    OBJECT-TYPE
    SYNTAX      Unsigned32
    MAX-ACCESS  read-only
    STATUS      current
    DESCRIPTION
        "The value of tmnxOamPingHistoryRtrnSubcode indicates the value present
         in an MPLS echo reply's RFC 4379 Return Subcode (RSC) field.

         A valid value is returned when the test has a tmnxOamPingCtlTestMode
         value of 'lspPing'.  Otherwise, zero is returned."
    REFERENCE
        "RFC 4379, 'Detecting Multi-Protocol Label Switched (MPLS) Data Plane
         Failures', Section 3.1, 'Return Codes'."
    ::= { tmnxOamPingHistoryEntry 32 }

tmnxOamPingHistoryNetworkIfName  OBJECT-TYPE
    SYNTAX      TNamedItemOrEmpty
    MAX-ACCESS  read-only
    STATUS      current
    DESCRIPTION
        "The value of tmnxOamPingHistoryNetworkIfName indicates the network
         interface name provided by the replying node.

         Network interface names are configured using
         TIMETRA-VRTR-MIB::vRtrIfName.

         The value of this object is the empty string when the value of
         tmnxOamPingHistAddressType is not 'networkInterface(11)'."
    ::= { tmnxOamPingHistoryEntry 33 }

tmnxOamMacPingCtlTable           OBJECT-TYPE
    SYNTAX      SEQUENCE OF TmnxOamMacPingCtlEntry
    MAX-ACCESS  not-accessible
    STATUS      current
    DESCRIPTION
        "Defines the Nokia SROS OAM MAC Ping Control Table for
         providing, via SNMP, the capability of performing Nokia SROS
         OAM 'macPing', 'macPopulate', or 'macPurge' test operations.
         The results of these tests are stored in the tmnxOamPingResultsTable
         and the tmnxOamMacPingHistoryTable.  There will be no entries for
         these test in the tmnxOamPingHistoryTable."
    ::= { tmnxOamPingObjs 6 }

tmnxOamMacPingCtlEntry           OBJECT-TYPE
    SYNTAX      TmnxOamMacPingCtlEntry
    MAX-ACCESS  not-accessible
    STATUS      current
    DESCRIPTION
        "Defines an entry in the tmnxOamMacPingCtlTable.  The first index
         element, tmnxOamPingCtlOwnerIndex, is of type SnmpAdminString,
         a textual convention that allows for use of the SNMPv3
         View-Based Access Control Model (RFC 2575 [11], VACM)
         and allows a management application to identify its entries.
         The second index, tmnxOamPingCtlTestIndex, enables the same
         management application to have multiple outstanding requests."
    INDEX       {
        tmnxOamPingCtlOwnerIndex,
        tmnxOamPingCtlTestIndex
    }
    ::= { tmnxOamMacPingCtlTable 1 }

TmnxOamMacPingCtlEntry           ::= SEQUENCE
{
    tmnxOamMacPingCtlTargetMacAddr   MacAddress,
    tmnxOamMacPingCtlSourceMacAddr   MacAddress,
    tmnxOamMacPingCtlSendControl     TruthValue,
    tmnxOamMacPingCtlReplyControl    TruthValue,
    tmnxOamMacPingCtlTtl             Unsigned32,
    tmnxOamMacPingCtlRegister        TruthValue,
    tmnxOamMacPingCtlFlood           TruthValue,
    tmnxOamMacPingCtlForce           TruthValue,
    tmnxOamMacPingCtlAge             Unsigned32,
    tmnxOamMacPingCtlSapPortId       TmnxPortID,
    tmnxOamMacPingCtlSapEncapValue   TmnxEncapVal,
    tmnxOamMacPingCtlFibEntryName    TNamedItemOrEmpty
}

tmnxOamMacPingCtlTargetMacAddr   OBJECT-TYPE
    SYNTAX      MacAddress
    MAX-ACCESS  read-create
    STATUS      current
    DESCRIPTION
        "The value of tmnxOamMacPingCtlTargetMacAddr is a 6-octet value that
         specifies the target MAC address to be used in the query request for
         performing an OAM ping operation.

         This parameter is required."
    REFERENCE
        "IEEE 802.3 Subclause 30.7.1.1.9"
    DEFVAL      { '000000000000'H }
    ::= { tmnxOamMacPingCtlEntry 1 }

tmnxOamMacPingCtlSourceMacAddr   OBJECT-TYPE
    SYNTAX      MacAddress
    MAX-ACCESS  read-create
    STATUS      current
    DESCRIPTION
        "The value of tmnxOamMacPingCtlSourceMacAddr is a 6-octet value
         that  specifies  the  MAC  address to be used as the source in the
         query request for performing an OAM ping operation.  This object
         is optional and is not relevant when tmnxOamPingCtlTestMode has a
         value other than 'macPing'."
    REFERENCE
        "IEEE 802.3 Subclause 30.7.1.1.9"
    DEFVAL      { '000000000000'H }
    ::= { tmnxOamMacPingCtlEntry 2 }

tmnxOamMacPingCtlSendControl     OBJECT-TYPE
    SYNTAX      TruthValue
    MAX-ACCESS  read-create
    STATUS      current
    DESCRIPTION
        "The value of tmnxOamMacPingCtlSendControl specifies whether the
         outbound OAM ping packet will use the data plane or the control plane.

         When the value is 'false', the packet is sent using the data plane.

         As of SROS release 13.0 R1, a test cannot be started if
         tmnxOamMacPingCtlSendControl is 'true'.  A test is started using
         tmnxOamPingCtlAdminStatus.

         This object will be marked obsolete in a future release."
    DEFVAL      { false }
    ::= { tmnxOamMacPingCtlEntry 3 }

tmnxOamMacPingCtlReplyControl    OBJECT-TYPE
    SYNTAX      TruthValue
    MAX-ACCESS  read-create
    STATUS      current
    DESCRIPTION
        "When the value of tmnxOamMacPingCtlReplyControl is 'true', the OAM
         ping response is returned using the control plane. If its value is
         'false', the packet is sent via the data plane. This object is
         optional and is not relevant when tmnxOamPingCtlTestMode has a value
         other than 'macPing'."
    DEFVAL      { false }
    ::= { tmnxOamMacPingCtlEntry 4 }

tmnxOamMacPingCtlTtl             OBJECT-TYPE
    SYNTAX      Unsigned32 (1..255)
    UNITS       "time-to-live value"
    MAX-ACCESS  read-create
    STATUS      current
    DESCRIPTION
        "Specifies the vc-label time-to-live value.

         This object is optional and is not relevant when
         tmnxOamPingCtlTestMode has a value other than 'macPing'.

         While performing the test with a TTL of 1 no responses should ever be
         expected."
    DEFVAL      { 255 }
    ::= { tmnxOamMacPingCtlEntry 5 }

tmnxOamMacPingCtlRegister        OBJECT-TYPE
    SYNTAX      TruthValue
    MAX-ACCESS  read-create
    STATUS      current
    DESCRIPTION
        "When the value of tmnxOamMacPingCtlRegister is 'true', the OAM ping
         request is transmitted that causes each upstream node to delete the
         MAC address only from its forwarding plane but keep it in its control
         plane in order to inhibit dynamic learning. If its value is 'false',
         the MAC address is deleted from both the forwarding and control
         planes.

         This object is optional and is not relevant when
         tmnxOamPingCtlTestMode has a value other than 'macPurge'."
    DEFVAL      { false }
    ::= { tmnxOamMacPingCtlEntry 6 }

tmnxOamMacPingCtlFlood           OBJECT-TYPE
    SYNTAX      TruthValue
    MAX-ACCESS  read-create
    STATUS      current
    DESCRIPTION
        "When the value of tmnxOamMacPingCtlFlood is 'true', the OAM ping
         request is transmitted that causes each upstream node to add or delete
         the MAC address. If its value is 'false', the operation is performed
         locally.

         This object is optional and is not relevant when
         tmnxOamPingCtlTestMode has a value other than 'macPopulate' or
         'macPurge'."
    DEFVAL      { false }
    ::= { tmnxOamMacPingCtlEntry 7 }

tmnxOamMacPingCtlForce           OBJECT-TYPE
    SYNTAX      TruthValue
    MAX-ACCESS  read-create
    STATUS      current
    DESCRIPTION
        "The value of tmnxOamMacPingCtlForce specifies whether or not to add an
         override to the test.

         When tmnxOamPingCtlTestMode is 'macPopulate' and
         tmnxOamMacPingCtlForce is 'true', the MAC type (i.e.
         TIMETRA-SERV-MIB::tlsFdbType) of the FIB entry specified by the test
         parameters is set to 'oam', regardless of its earlier value.

         When tmnxOamPingCtlTestMode is 'macPurge' and tmnxOamMacPingCtlForce
         is 'true', the FIB entry specified by the test parameters is purged,
         even if the requesting node did not populate the entry.

         When tmnxOamPingCtlTestMode is 'macPing', tmnxOamMacPingCtlForce is
         irrelevant."
    DEFVAL      { false }
    ::= { tmnxOamMacPingCtlEntry 8 }

tmnxOamMacPingCtlAge             OBJECT-TYPE
    SYNTAX      Unsigned32 (1..65535)
    UNITS       "seconds"
    MAX-ACCESS  read-create
    STATUS      current
    DESCRIPTION
        "The value of tmnxOamMacPingCtlAge specifies the number of seconds to
         age this OAM MAC address in the FIB.

         This object is optional and is not relevant when
         tmnxOamPingCtlTestMode has a value other than 'macPopulate'."
    DEFVAL      { 3600 }
    ::= { tmnxOamMacPingCtlEntry 9 }

tmnxOamMacPingCtlSapPortId       OBJECT-TYPE
    SYNTAX      TmnxPortID
    MAX-ACCESS  read-create
    STATUS      current
    DESCRIPTION
        "The value of tmnxOamMacPingCtlSapPortId is the ID of the access port
         of the target SAP.

         This object is optional and is not relevant when
         tmnxOamPingCtlTestMode has a value other than 'macPopulate'."
    DEFVAL      { 0 }
    ::= { tmnxOamMacPingCtlEntry 10 }

tmnxOamMacPingCtlSapEncapValue   OBJECT-TYPE
    SYNTAX      TmnxEncapVal
    MAX-ACCESS  read-create
    STATUS      current
    DESCRIPTION
        "The value of tmnxOamMacPingCtlSapEncapValue is the label used to
         identify the target SAP on the port specified in
         tmnxOamMacPingCtlSapPortId.

         This object is optional and is not relevant when
         tmnxOamPingCtlTestMode has a value other than 'macPopulate'."
    DEFVAL      { 0 }
    ::= { tmnxOamMacPingCtlEntry 11 }

tmnxOamMacPingCtlFibEntryName    OBJECT-TYPE
    SYNTAX      TNamedItemOrEmpty
    MAX-ACCESS  read-create
    STATUS      obsolete
    DESCRIPTION
        "The value of tmnxOamMacPingCtlFibEntryName is the fib entry name to
         associate with the target MAC address.

         This object is optional and is not relevant when
         tmnxOamPingCtlTestMode has a value other than 'macPopulate'.

         This object was obsoleted in SROS 11.0 R1."
    DEFVAL      { ''H }
    ::= { tmnxOamMacPingCtlEntry 12 }

tmnxOamMacPingHistoryTable       OBJECT-TYPE
    SYNTAX      SEQUENCE OF TmnxOamMacPingHistoryEntry
    MAX-ACCESS  not-accessible
    STATUS      current
    DESCRIPTION
        "Defines a table for storing the results of an OAM 'macPing' probe
         operation.  The number of entries in this table for a test
         is limited to the results of 3 runs.

         An entry in this table is created when the result of an OAM 'macPing'
         probe is determined.  An entry is removed from this table when its
         corresponding tmnxOamPingCtlEntry is deleted."
    ::= { tmnxOamPingObjs 7 }

tmnxOamMacPingHistoryEntry       OBJECT-TYPE
    SYNTAX      TmnxOamMacPingHistoryEntry
    MAX-ACCESS  not-accessible
    STATUS      current
    DESCRIPTION
        "Defines an entry in the tmnxOamPingHistoryTable.  The first two
         index elements identify the tmnxOamPingCtlEntry that a
         tmnxOamMacPingHistoryEntry belongs to.  The third index identifies
         a specific run of the OAM test.  The fourth index element
         selects the group of responses associated with a specific probe
         attempt.  The fifth index selects a single OAM 'macPing' reply."
    INDEX       {
        tmnxOamPingCtlOwnerIndex,
        tmnxOamPingCtlTestIndex,
        tmnxOamPingResultsTestRunIndex,
        tmnxOamMacPingHistoryIndex,
        tmnxOamMacPingReplyIndex
    }
    ::= { tmnxOamMacPingHistoryTable 1 }

TmnxOamMacPingHistoryEntry       ::= SEQUENCE
{
    tmnxOamMacPingHistoryIndex       Unsigned32,
    tmnxOamMacPingReplyIndex         Unsigned32,
    tmnxOamMacPingHistoryResponse    Unsigned32,
    tmnxOamMacPingHistoryOneWayTime  Integer32,
    tmnxOamMacPingHistoryStatus      TmnxOamResponseStatus,
    tmnxOamMacPingHistoryTime        DateAndTime,
    tmnxOamMacPingHistoryReturnCode  TmnxOamPingRtnCode,
    tmnxOamMacPingHistorySrcIpAddress IpAddress,
    tmnxOamMacPingHistoryAddressType TmnxOamAddressType,
    tmnxOamMacPingHistorySapId       TmnxStrSapId,
    tmnxOamMacPingHistorySdpId       SdpId,
    tmnxOamMacPingHistoryAdminStatus TruthValue,
    tmnxOamMacPingHistoryOperStatus  TruthValue,
    tmnxOamMacPingHistoryResponsePlane TmnxOamTestResponsePlane,
    tmnxOamMacPingHistorySize        Unsigned32,
    tmnxOamMacPingHistoryInOneWayTime Integer32,
    tmnxOamMacPingHistorySrcAddrType InetAddressType,
    tmnxOamMacPingHistorySrcAddress  InetAddress
}

tmnxOamMacPingHistoryIndex       OBJECT-TYPE
    SYNTAX      Unsigned32 (1..4294967295)
    MAX-ACCESS  not-accessible
    STATUS      current
    DESCRIPTION
        "An entry in this table is created when the result of a OAM
         'macPing' probe is determined.  The initial 2 instance identifier
         index values identify the tmnxOamPingCtlEntry that a OAM probe
         result (tmnxOamMacPingHistoryEntry) belongs to.  The
         tmnxOamMacPingHistoryIndex has the value of the sequence number
         of the request probe and identifies a group of replies received
         in response to a specific probe transmission.

         The agent starts assigning tmnxOamMacPingHistoryIndex values at 1 and
         wraps after exceeding the maximum possible value as defined by the
         limit of this object."
    ::= { tmnxOamMacPingHistoryEntry 1 }

tmnxOamMacPingReplyIndex         OBJECT-TYPE
    SYNTAX      Unsigned32 (1..4294967295)
    MAX-ACCESS  not-accessible
    STATUS      current
    DESCRIPTION
        "The tmnxOamMacPingReplyIndex is unique within a group of responses
         received as the result of a OAM 'macPing' probe as specified by having
         the same value for tmnxOamMacPingHistoryIndex.

         The agent starts assigning tmnxOamMacPingReplyIndex values at 1 and
         wraps after exceeding the maximum possible value as defined by the
         limit of this object."
    ::= { tmnxOamMacPingHistoryEntry 2 }

tmnxOamMacPingHistoryResponse    OBJECT-TYPE
    SYNTAX      Unsigned32
    UNITS       "microseconds"
    MAX-ACCESS  read-only
    STATUS      current
    DESCRIPTION
        "The amount of time measured in microseconds from when
         a OAM probe was sent to when its response was received or
         when it timed out.  The value of this object is reported
         as 0 when it is not possible to transmit an OAM probe."
    ::= { tmnxOamMacPingHistoryEntry 3 }

tmnxOamMacPingHistoryOneWayTime  OBJECT-TYPE
    SYNTAX      Integer32
    UNITS       "microseconds"
    MAX-ACCESS  read-only
    STATUS      current
    DESCRIPTION
        "The amount of time measured in microseconds from when an
         OAM probe was sent to when it was received by the replier
         (out-bound one-way time).  The value of this object is
         reported as 0 when it is not possible to transmit an OAM
         probe or the information is not available."
    ::= { tmnxOamMacPingHistoryEntry 4 }

tmnxOamMacPingHistoryStatus      OBJECT-TYPE
    SYNTAX      TmnxOamResponseStatus
    MAX-ACCESS  read-only
    STATUS      current
    DESCRIPTION
        "The value of tmnxOamMacPingHistoryStatus is an enumerated integer that
         indicates the result of a particular OAM probe."
    ::= { tmnxOamMacPingHistoryEntry 5 }

tmnxOamMacPingHistoryTime        OBJECT-TYPE
    SYNTAX      DateAndTime
    MAX-ACCESS  read-only
    STATUS      current
    DESCRIPTION
        "Timestamp for when this OAM probe result was determined."
    ::= { tmnxOamMacPingHistoryEntry 6 }

tmnxOamMacPingHistoryReturnCode  OBJECT-TYPE
    SYNTAX      TmnxOamPingRtnCode
    MAX-ACCESS  read-only
    STATUS      current
    DESCRIPTION
        "The value of tmnxOamMacPingHistoryReturnCode is an enumerated integer
         that indicates the return code received in the OAM ping response."
    ::= { tmnxOamMacPingHistoryEntry 7 }

tmnxOamMacPingHistorySrcIpAddress OBJECT-TYPE
    SYNTAX      IpAddress
    MAX-ACCESS  read-only
    STATUS      obsolete
    DESCRIPTION
        "The value of tmnxOamMacPingHistorySrcIpAddress indicates the IPv4
         address of the remote node that generated this reply to a OAM probe.

         This object was obsoleted in release 4.0 and replaced with InetAddress
         objects tmnxOamMacPingHistorySrcAddrType and
         tmnxOamMacPingHistorySrcAddress."
    ::= { tmnxOamMacPingHistoryEntry 8 }

tmnxOamMacPingHistoryAddressType OBJECT-TYPE
    SYNTAX      TmnxOamAddressType
    MAX-ACCESS  read-only
    STATUS      current
    DESCRIPTION
        "The value of tmnxOamMacPingHistoryAddressType indicates the type of
         binding address information returned in response to a 'macPing' test."
    ::= { tmnxOamMacPingHistoryEntry 9 }

tmnxOamMacPingHistorySapId       OBJECT-TYPE
    SYNTAX      TmnxStrSapId
    MAX-ACCESS  read-only
    STATUS      current
    DESCRIPTION
        "The value of tmnxOamMacPingHistorySapId is the name of the access port
         of the SAP supporting the requested MAC address returned in response
         to a 'macPing' probe.

         If the value of tmnxOamMacPingHistoryAddressType is not 'sapId', this
         object is not relevant and MUST have a null string ''."
    ::= { tmnxOamMacPingHistoryEntry 10 }

tmnxOamMacPingHistorySdpId       OBJECT-TYPE
    SYNTAX      SdpId
    MAX-ACCESS  read-only
    STATUS      current
    DESCRIPTION
        "The value of tmnxOamMacPingHistorySdpId is the ID of the SDP
         supporting the requested MAC address returned in response to a
         'macPing' probe.

         If the value of tmnxOamMacPingHistoryAddressType is not 'sdpId', this
         object is not relevant and MUST return a value of '0'."
    ::= { tmnxOamMacPingHistoryEntry 12 }

tmnxOamMacPingHistoryAdminStatus OBJECT-TYPE
    SYNTAX      TruthValue
    MAX-ACCESS  read-only
    STATUS      current
    DESCRIPTION
        "The value of tmnxOamMacPingHistoryAdminStatus indicates the current
         administrative state of the SAP or SDP ID returned in response to a
         'macPing' test.  A value of 'true' indicates the SAP or SDP is
         administratively 'up'.

         The value of this object MUST be reported as 'false' when no ping
         responses have been received or an active test has not yet timed out."
    ::= { tmnxOamMacPingHistoryEntry 13 }

tmnxOamMacPingHistoryOperStatus  OBJECT-TYPE
    SYNTAX      TruthValue
    MAX-ACCESS  read-only
    STATUS      current
    DESCRIPTION
        "The value of tmnxOamMacPingHistoryOperStatus indicates the current
         operational state of the SAP or SDP ID returned in response to a
         'macPing' test.  A value of 'true' indicates the SAP or SDP is
         operationally 'up'.

         The value of this object MUST be reported as 'false' when no ping
         responses have been received or an active test has not yet timed out."
    ::= { tmnxOamMacPingHistoryEntry 14 }

tmnxOamMacPingHistoryResponsePlane OBJECT-TYPE
    SYNTAX      TmnxOamTestResponsePlane
    MAX-ACCESS  read-only
    STATUS      current
    DESCRIPTION
        "The value of tmnxOamMacPingHistoryResponsePlane indicates the response
         plane from which this ping response was received."
    ::= { tmnxOamMacPingHistoryEntry 15 }

tmnxOamMacPingHistorySize        OBJECT-TYPE
    SYNTAX      Unsigned32
    UNITS       "octets"
    MAX-ACCESS  read-only
    STATUS      current
    DESCRIPTION
        "The value of tmnxOamMacPingHistorySize indicates the size in octets
         of the user payload in a ping request packet.  It does not include
         the service encapsulation."
    ::= { tmnxOamMacPingHistoryEntry 16 }

tmnxOamMacPingHistoryInOneWayTime OBJECT-TYPE
    SYNTAX      Integer32
    UNITS       "microseconds"
    MAX-ACCESS  read-only
    STATUS      current
    DESCRIPTION
        "The amount of time measured in microseconds from when an OAM
         probe reply was sent to when it was received by this host
         (in-bound one-way time).  The value of this object is reported
         as 0 when the information is not available."
    ::= { tmnxOamMacPingHistoryEntry 17 }

tmnxOamMacPingHistorySrcAddrType OBJECT-TYPE
    SYNTAX      InetAddressType
    MAX-ACCESS  read-only
    STATUS      current
    DESCRIPTION
        "The value of tmnxOamMacPingHistorySrcAddrType indicates the Internet
         address type stored in tmnxOamMacPingHistorySrcAddress."
    ::= { tmnxOamMacPingHistoryEntry 18 }

tmnxOamMacPingHistorySrcAddress  OBJECT-TYPE
    SYNTAX      InetAddress (SIZE (0|4|16))
    MAX-ACCESS  read-only
    STATUS      current
    DESCRIPTION
        "The value of tmnxOamMacPingHistorySrcAddress indicates the Internet
         address of the remote node that generated this reply to a OAM probe."
    ::= { tmnxOamMacPingHistoryEntry 19 }

tmnxOamMacPingL2MapTable         OBJECT-TYPE
    SYNTAX      SEQUENCE OF TmnxOamMacPingL2MapEntry
    MAX-ACCESS  not-accessible
    STATUS      obsolete
    DESCRIPTION
        "Defines a table for storing the results of an OAM 'macQuery'
         probe operation where a L2 mapping TLV is returned.  Only one
         downstream and one upstream L2 mapping entry is returned if the
         'macQuery' replier has no egress mapping for the requested MAC
         address but it does have an SDP binding.  Multiple downstream L2
         mappings that specify the replier's flooding domain may be returned
         if the replier has no bindings for the MAC address.

         An entry in this table is created when the result of an OAM 'macQuery'
         probe is determined.

         An entry is removed from this table when its corresponding
         tmnxOamPingCtlEntry is deleted."
    ::= { tmnxOamPingObjs 8 }

tmnxOamMacPingL2MapEntry         OBJECT-TYPE
    SYNTAX      TmnxOamMacPingL2MapEntry
    MAX-ACCESS  not-accessible
    STATUS      obsolete
    DESCRIPTION
        "Defines an entry in the tmnxOamMacPingL2MapTable.  The first two
         index elements identify the tmnxOamPingCtlEntry that a
         tmnxOamMacPingL2MapEntry belongs to.  The third index element
         identifies a specific OAM test run.  The fourth index element
         selects the group of responses associated with a specific probe
         attempt.  The fifth index selects a single OAM 'macQuery' reply.
         Note that in the case of a successful 'macQuery' reply there will
         be only two row entries created per test run.  However there may
         also be one or more error replies.  The sixth index selects a
         single L2 mapping entry within a specific probe reply."
    INDEX       {
        tmnxOamPingCtlOwnerIndex,
        tmnxOamPingCtlTestIndex,
        tmnxOamPingResultsTestRunIndex,
        tmnxOamMacPingHistoryIndex,
        tmnxOamMacPingReplyIndex,
        tmnxOamMacPingL2MapIndex
    }
    ::= { tmnxOamMacPingL2MapTable 1 }

TmnxOamMacPingL2MapEntry         ::= SEQUENCE
{
    tmnxOamMacPingL2MapIndex         Unsigned32,
    tmnxOamMacPingL2MapRouterID      IpAddress,
    tmnxOamMacPingL2MapLabel         MplsLabel,
    tmnxOamMacPingL2MapProtocol      TmnxOamSignalProtocol,
    tmnxOamMacPingL2MapVCType        TmnxOamVcType,
    tmnxOamMacPingL2MapVCID          TmnxVcId,
    tmnxOamMacPingL2MapDirection     INTEGER
}

tmnxOamMacPingL2MapIndex         OBJECT-TYPE
    SYNTAX      Unsigned32 (1..4294967295)
    MAX-ACCESS  not-accessible
    STATUS      obsolete
    DESCRIPTION
        "An entry in this table is created when the result of a OAM
         'macQuery' probe is determined.  The initial 2 instance identifier
         index values identify the tmnxOamPingCtlEntry that a OAM probe result
         (tmnxOamMacPingHistoryEntry) belongs to. The tmnxOamMacPingHistoryIndex
         identifies a group of replies received in response to a specific
         probe transmission.  The tmnxOamMacPingReplyIndex selects a single
         OAM 'macQuery' reply.

         The tmnxOamMacPingL2MapIndex selects a single L2 mapping entry within
         a specific 'macQuery' probe reply.

         The agent starts assigning tmnxOamMacPingL2MapIndex values at 1."
    ::= { tmnxOamMacPingL2MapEntry 1 }

tmnxOamMacPingL2MapRouterID      OBJECT-TYPE
    SYNTAX      IpAddress
    MAX-ACCESS  read-only
    STATUS      obsolete
    DESCRIPTION
        "The value of tmnxOamMacPingL2MapRouterID is the router ID for this L2
         mapping entry."
    ::= { tmnxOamMacPingL2MapEntry 2 }

tmnxOamMacPingL2MapLabel         OBJECT-TYPE
    SYNTAX      MplsLabel
    MAX-ACCESS  read-only
    STATUS      obsolete
    DESCRIPTION
        "The value of tmnxOamMacPingL2MapLabel is the label used by the router
         for the L2FEC or VC ID specified by this L2 mapping entry."
    ::= { tmnxOamMacPingL2MapEntry 3 }

tmnxOamMacPingL2MapProtocol      OBJECT-TYPE
    SYNTAX      TmnxOamSignalProtocol
    MAX-ACCESS  read-only
    STATUS      obsolete
    DESCRIPTION
        "The value of tmnxOamMacPingL2MapProtocol is the signaling protocol
         used by the router for the L2FEC or VC ID specified by this L2 mapping
         entry."
    ::= { tmnxOamMacPingL2MapEntry 4 }

tmnxOamMacPingL2MapVCType        OBJECT-TYPE
    SYNTAX      TmnxOamVcType
    MAX-ACCESS  read-only
    STATUS      obsolete
    DESCRIPTION
        "The value of tmnxOamMacPingL2MapVCType specifies the class of VC ID
         given in tmnxOamMacPingL2MapVCID."
    ::= { tmnxOamMacPingL2MapEntry 5 }

tmnxOamMacPingL2MapVCID          OBJECT-TYPE
    SYNTAX      TmnxVcId
    MAX-ACCESS  read-only
    STATUS      obsolete
    DESCRIPTION
        "The value of tmnxOamMacPingL2MapVCID is the VC ID associated with the
         label used by the L2FEC specified by this L2 mapping entry."
    ::= { tmnxOamMacPingL2MapEntry 6 }

tmnxOamMacPingL2MapDirection     OBJECT-TYPE
    SYNTAX      INTEGER {
        upstream   (1),
        downstream (2)
    }
    MAX-ACCESS  read-only
    STATUS      obsolete
    DESCRIPTION
        "The value of tmnxOamMacPingL2MapDirection specifies the direction that
         this L2 mapping entry is in relation to the node that returned the
         'macQuery' reply."
    ::= { tmnxOamMacPingL2MapEntry 7 }

tmnxOamLspPingCtlTable           OBJECT-TYPE
    SYNTAX      SEQUENCE OF TmnxOamLspPingCtlEntry
    MAX-ACCESS  not-accessible
    STATUS      current
    DESCRIPTION
        "Each row in tmnxOamLspPingCtlTable contains the LSP-specific
         configuration information needed to launch an LSP (Label Switched Path)
         ping test.  The rest of the configuration information needed to launch
         the test resides in the corresponding row of tmnxOamPingCtlTable.

         Results of LSP ping tests are stored in tmnxOamPingResultsTable and
         tmnxOamPingHistoryTable.

         Seven types of LSP ping tests are supported.  An abbreviated name for
         each test type is defined in the following table (for use in a
         subsequent table).  The test type's tmnxOamLspPingCtlTestSubMode code
         point is shown as well.

         Test Sub Mode           Abbreviated Test Type Name(s)
         ---------------------   -------------------------------
         'unspecified     (1)'   LDP, RSVP
         'static          (2)'   TPST (Transport Profile Static)
         'bgpLabeledPrefix(3)'   BGP
         'srIsis          (4)'   ISIS
         'srOspf          (5)'   OSPF
         'srTe            (6)'   SRTE

         The following table has a row for each LSP ping test type, showing the
         mandatory and optional objects applicable to the test type.

         Test
         Type   Mandatory Objects               Optional Objects
         ---- -------------------------------- ---------------------------------
         BGP  tmnxOamLspPingCtlLdpPrefixType   *tmnxOamLspPingCtlNhAddressType
              tmnxOamLspPingCtlLdpPrefix       *tmnxOamLspPingCtlNhAddress
              tmnxOamLspPingCtlLdpPrefixLen     tmnxOamLspPingCtlNhIntfName
              tmnxOamLspPingCtlTestSubMode     #tmnxOamLspPingCtlPathDestType
                                               #tmnxOamLspPingCtlPathDest

         ISIS tmnxOamLspPingCtlLdpPrefixType    tmnxOamLspPingCtlIgpInstance
              tmnxOamLspPingCtlLdpPrefix       *tmnxOamLspPingCtlNhAddressType
              tmnxOamLspPingCtlLdpPrefixLen    *tmnxOamLspPingCtlNhAddress
              tmnxOamLspPingCtlTestSubMode      tmnxOamLspPingCtlNhIntfName
                                               #tmnxOamLspPingCtlPathDestType
                                               #tmnxOamLspPingCtlPathDest

         LDP  tmnxOamLspPingCtlLdpPrefixType   *tmnxOamLspPingCtlNhAddressType
              tmnxOamLspPingCtlLdpPrefix       *tmnxOamLspPingCtlNhAddress
              tmnxOamLspPingCtlLdpPrefixLen     tmnxOamLspPingCtlNhIntfName
                                               #tmnxOamLspPingCtlPathDestType
                                               #tmnxOamLspPingCtlPathDest

         OSPF tmnxOamLspPingCtlLdpPrefixType    tmnxOamLspPingCtlIgpInstance
              tmnxOamLspPingCtlLdpPrefix       *tmnxOamLspPingCtlNhAddressType
              tmnxOamLspPingCtlLdpPrefixLen    *tmnxOamLspPingCtlNhAddress
              tmnxOamLspPingCtlTestSubMode      tmnxOamLspPingCtlNhIntfName
                                               #tmnxOamLspPingCtlPathDestType
                                               #tmnxOamLspPingCtlPathDest

         RSVP tmnxOamLspPingCtlLspName          tmnxOamLspPingCtlPathName

         SRTE tmnxOamLspPingCtlLspName         *tmnxOamLspPingCtlNhAddressType
              tmnxOamLspPingCtlTestSubMode     *tmnxOamLspPingCtlNhAddress
                                                tmnxOamLspPingCtlNhIntfName
                                               #tmnxOamLspPingCtlPathDestType
                                               #tmnxOamLspPingCtlPathDest
                                                tmnxOamLspPingCtlPathName

         TPST tmnxOamLspPingCtlLspName          tmnxOamLspPingCtlAssocChannel
              tmnxOamLspPingCtlTestSubMode      tmnxOamLspPingCtlForce
                                               *tmnxOamLspPingCtlMplsTpGlobalId
                                               *tmnxOamLspPingCtlMplsTpNodeId
                                                tmnxOamLspPingCtlMplsTpPathType

         ALL  none                              tmnxOamLspPingCtlTtl
                                                tmnxOamPingCtlFcName
                                                tmnxOamPingCtlInterval
                                                tmnxOamPingCtlProbeCount
                                                tmnxOamPingCtlProfile
                                                tmnxOamPingCtlSize
                                               *tmnxOamPingCtlSrcAddrType
                                               *tmnxOamPingCtlSrcAddress
                                                tmnxOamPingCtlTimeOut
         ---- -------------------------------- ---------------------------------

         In the table above,
         1.  The optional objects in the ALL row apply to all LSP ping test
             types.
         2.  Asterisks (*) mark a set of optional objects which must all be
             specified, or must all be unspecified.
         3.  Octothorpes (#) mark a separate set of optional objects which must
             all be specified, or must all be unspecified.
         4.  There are four supported combinations of
             tmnxOamLspPingCtlNhAddressType, tmnxOamLspPingCtlNhAddress,
             tmnxOamLspPingCtlNhIntfName, tmnxOamLspPingCtlPathDestType, and
             tmnxOamLspPingCtlPathDest, as follows:
             a) all unspecified
             b) tmnxOamLspPingCtlPathDestType and tmnxOamLspPingCtlPathDest
             c) tmnxOamLspPingCtlPathDestType, tmnxOamLspPingCtlPathDest, and
                tmnxOamLspPingCtlNhIntfName
             d) tmnxOamLspPingCtlPathDestType, tmnxOamLspPingCtlPathDest,
                tmnxOamLspPingCtlNhAddressType, and tmnxOamLspPingCtlNhAddress

         When an object combination other than a combination listed above is
         specified, values will be rejected or ignored, or the test will fail."
    REFERENCE
        "IETF draft-ietf-mpls-spring-lsp-ping-00, 'Label Switched Path (LSP)
         Ping/Trace for Segment Routing Networks Using MPLS Dataplane'.
         RFC 4379, 'Detecting Multi-Protocol Label Switched (MPLS) Data Plane
         Failures'.
         RFC 6426, 'MPLS On-Demand Connectivity Verification and Route Tracing'"
    ::= { tmnxOamPingObjs 9 }

tmnxOamLspPingCtlEntry           OBJECT-TYPE
    SYNTAX      TmnxOamLspPingCtlEntry
    MAX-ACCESS  not-accessible
    STATUS      current
    DESCRIPTION
        "The system creates a row in tmnxOamLspPingCtlTable when a row is
         created in tmnxOamPingCtlTable with tmnxOamPingCtlTestMode set to
         'lspPing'.

         The system deletes a row in tmnxOamLspPingCtlTable when the
         corresponding row in tmnxOamPingCtlTable is deleted."
    INDEX       {
        tmnxOamPingCtlOwnerIndex,
        tmnxOamPingCtlTestIndex
    }
    ::= { tmnxOamLspPingCtlTable 1 }

TmnxOamLspPingCtlEntry           ::= SEQUENCE
{
    tmnxOamLspPingCtlVRtrID          TmnxVRtrID,
    tmnxOamLspPingCtlLspName         TLNamedItemOrEmpty,
    tmnxOamLspPingCtlReturnLsp       TNamedItemOrEmpty,
    tmnxOamLspPingCtlTtl             Unsigned32,
    tmnxOamLspPingCtlPathName        TNamedItemOrEmpty,
    tmnxOamLspPingCtlLdpIpPrefix     IpAddress,
    tmnxOamLspPingCtlLdpIpPrefixLen  IpAddressPrefixLength,
    tmnxOamLspPingCtlLdpPrefixType   InetAddressType,
    tmnxOamLspPingCtlLdpPrefix       InetAddress,
    tmnxOamLspPingCtlLdpPrefixLen    InetAddressPrefixLength,
    tmnxOamLspPingCtlPathDestType    InetAddressType,
    tmnxOamLspPingCtlPathDest        InetAddress,
    tmnxOamLspPingCtlNhIntfName      TNamedItemOrEmpty,
    tmnxOamLspPingCtlNhAddressType   InetAddressType,
    tmnxOamLspPingCtlNhAddress       InetAddress,
    tmnxOamLspPingCtlTestSubMode     TmnxOamLspTestSubMode,
    tmnxOamLspPingCtlMplsTpPathType  TmnxOamMplsTpPathType,
    tmnxOamLspPingCtlMplsTpGlobalId  TmnxMplsTpGlobalID,
    tmnxOamLspPingCtlMplsTpNodeId    TmnxMplsTpNodeID,
    tmnxOamLspPingCtlAssocChannel    TmnxOamLspAssocChannel,
    tmnxOamLspPingCtlForce           TruthValue,
    tmnxOamLspPingCtlIgpInstance     TmnxIgpInstance
}

tmnxOamLspPingCtlVRtrID          OBJECT-TYPE
    SYNTAX      TmnxVRtrID
    MAX-ACCESS  read-create
    STATUS      obsolete
    DESCRIPTION
        "This object was obsoleted in release 6.0R15 and replaced with
         tmnxOamPingCtlVRtrID in tmnxOamPingCtlTable."
    DEFVAL      { 1 }
    ::= { tmnxOamLspPingCtlEntry 1 }

tmnxOamLspPingCtlLspName         OBJECT-TYPE
    SYNTAX      TLNamedItemOrEmpty
    MAX-ACCESS  read-create
    STATUS      current
    DESCRIPTION
        "The value of tmnxOamLspPingCtlLspName specifies the name of the LSP
         for this LSP ping test.

         When the test is started, if this name is not empty, there must be a
         TIMETRA-MPLS-MIB::vRtrMplsLspTable row with:
         1.  tmnxOamLspPingCtlLspName equal to
             TIMETRA-MPLS-MIB::vRtrMplsLspName, AND
         2.  TIMETRA-VRTR-MIB::vRtrID equal to 1, AND
         3.  TIMETRA-MPLS-MIB::vRtrMplsLspType equal to 'dynamic(2)',
             'bypassOnly(4)', or 'mplsTp(7)'.
         Otherwise, the test will fail.

         The supported object combinations for LSP ping tests are listed in the
         tmnxOamLspPingCtlTable DESCRIPTION clause."
    DEFVAL      { ''H }
    ::= { tmnxOamLspPingCtlEntry 2 }

tmnxOamLspPingCtlReturnLsp       OBJECT-TYPE
    SYNTAX      TNamedItemOrEmpty
    MAX-ACCESS  read-create
    STATUS      obsolete
    DESCRIPTION
        "This object was obsoleted in release 4.0."
    DEFVAL      { ''H }
    ::= { tmnxOamLspPingCtlEntry 3 }

tmnxOamLspPingCtlTtl             OBJECT-TYPE
    SYNTAX      Unsigned32 (1..255)
    UNITS       "time-to-live value"
    MAX-ACCESS  read-create
    STATUS      current
    DESCRIPTION
        "The value of tmnxOamLspPingCtlTtl specifies the outermost label time-
         to-live value.

         The supported object combinations for LSP ping tests are listed in the
         tmnxOamLspPingCtlTable DESCRIPTION clause."
    DEFVAL      { 255 }
    ::= { tmnxOamLspPingCtlEntry 4 }

tmnxOamLspPingCtlPathName        OBJECT-TYPE
    SYNTAX      TNamedItemOrEmpty
    MAX-ACCESS  read-create
    STATUS      current
    DESCRIPTION
        "The value of tmnxOamLspPingCtlPathName specifies the name of the Path
         (LSP) for this LSP ping test.

         When the test is started, if this name is not empty, there must be a
         matching name in the column MPLS-TE-MIB::mplsTunnelName.  Otherwise,
         the test will fail.

         The supported object combinations for LSP ping tests are listed in the
         tmnxOamLspPingCtlTable DESCRIPTION clause."
    DEFVAL      { ''H }
    ::= { tmnxOamLspPingCtlEntry 5 }

tmnxOamLspPingCtlLdpIpPrefix     OBJECT-TYPE
    SYNTAX      IpAddress
    MAX-ACCESS  read-create
    STATUS      obsolete
    DESCRIPTION
        "This object was obsoleted in release 4.0 and replaced with InetAddress
         objects tmnxOamLspPingCtlLdpPrefixType and tmnxOamLspPingCtlLdpPrefix."
    DEFVAL      { '00000000'H }
    ::= { tmnxOamLspPingCtlEntry 6 }

tmnxOamLspPingCtlLdpIpPrefixLen  OBJECT-TYPE
    SYNTAX      IpAddressPrefixLength
    MAX-ACCESS  read-create
    STATUS      obsolete
    DESCRIPTION
        "This object was obsoleted in release 4.0 and replaced with the
         InetAddress object tmnxOamLspPingCtlLdpPrefixLen."
    DEFVAL      { 32 }
    ::= { tmnxOamLspPingCtlEntry 7 }

tmnxOamLspPingCtlLdpPrefixType   OBJECT-TYPE
    SYNTAX      InetAddressType
    MAX-ACCESS  read-create
    STATUS      current
    DESCRIPTION
        "The value of tmnxOamLspPingCtlLdpPrefixType specifies the type of
         Internet address stored in tmnxOamLspPingCtlLdpPrefix.

         The supported object combinations for LSP ping tests are listed in the
         tmnxOamLspPingCtlTable DESCRIPTION clause."
    DEFVAL      { unknown }
    ::= { tmnxOamLspPingCtlEntry 8 }

tmnxOamLspPingCtlLdpPrefix       OBJECT-TYPE
    SYNTAX      InetAddress (SIZE (0|4|16))
    MAX-ACCESS  read-create
    STATUS      current
    DESCRIPTION
        "The value of tmnxOamLspPingCtlLdpPrefix, along with
         tmnxOamLspPingCtlLdpPrefixType and tmnxOamLspPingCtlLdpPrefixLen,
         specifies the destination prefix for this LSP ping test.

         The supported object combinations for LSP ping tests are listed in the
         tmnxOamLspPingCtlTable DESCRIPTION clause."
    DEFVAL      { ''H }
    ::= { tmnxOamLspPingCtlEntry 9 }

tmnxOamLspPingCtlLdpPrefixLen    OBJECT-TYPE
    SYNTAX      InetAddressPrefixLength
    UNITS       "bits"
    MAX-ACCESS  read-create
    STATUS      current
    DESCRIPTION
        "The value of tmnxOamLspPingCtlLdpPrefixLen specifies the Internet
         address prefix length of tmnxOamLspPingCtlLdpPrefix.

         The supported object combinations for LSP ping tests are listed in the
         tmnxOamLspPingCtlTable DESCRIPTION clause."
    DEFVAL      { 32 }
    ::= { tmnxOamLspPingCtlEntry 10 }

tmnxOamLspPingCtlPathDestType    OBJECT-TYPE
    SYNTAX      InetAddressType
    MAX-ACCESS  read-create
    STATUS      current
    DESCRIPTION
        "The value of tmnxOamLspPingCtlPathDestType specifies the type of
         Internet address stored in tmnxOamLspPingCtlPathDest.

         The supported object combinations for LSP ping tests are listed in the
         tmnxOamLspPingCtlTable DESCRIPTION clause."
    DEFVAL      { unknown }
    ::= { tmnxOamLspPingCtlEntry 11 }

tmnxOamLspPingCtlPathDest        OBJECT-TYPE
    SYNTAX      InetAddress (SIZE (0|4|16))
    MAX-ACCESS  read-create
    STATUS      current
    DESCRIPTION
        "The value of tmnxOamLspPingCtlPathDest specifies a unique path for
         this LSP ping to traverse. This address is used as part of a hash key
         to select the appropriate ECMP path to the destination of an LSP ping
         test.

         The supported object combinations for LSP ping tests are listed in the
         tmnxOamLspPingCtlTable DESCRIPTION clause."
    DEFVAL      { ''H }
    ::= { tmnxOamLspPingCtlEntry 12 }

tmnxOamLspPingCtlNhIntfName      OBJECT-TYPE
    SYNTAX      TNamedItemOrEmpty
    MAX-ACCESS  read-create
    STATUS      current
    DESCRIPTION
        "The value of tmnxOamLspPingCtlNhIntfName specifies the name of the
         next hop interface to be used when transmitting an LSP ping.

         When the test is started, if this name is not empty, there must be a
         TIMETRA-VRTR-MIB::vRtrIfTable row with:
         1.  tmnxOamLspPingCtlNhIntfName equal to TIMETRA-VRTR-MIB::vRtrIfName,
             AND
         2.  TIMETRA-VRTR-MIB::vRtrID equal to 1.
         Otherwise, the test will fail.

         The supported object combinations for LSP ping tests are listed in the
         tmnxOamLspPingCtlTable DESCRIPTION clause."
    DEFVAL      { ''H }
    ::= { tmnxOamLspPingCtlEntry 13 }

tmnxOamLspPingCtlNhAddressType   OBJECT-TYPE
    SYNTAX      InetAddressType
    MAX-ACCESS  read-create
    STATUS      current
    DESCRIPTION
        "The value of tmnxOamLspPingCtlNhAddressType specifies the type of
         Internet address stored in tmnxOamLspPingCtlNhAddress.

         The supported object combinations for LSP ping tests are listed in the
         tmnxOamLspPingCtlTable DESCRIPTION clause."
    DEFVAL      { unknown }
    ::= { tmnxOamLspPingCtlEntry 14 }

tmnxOamLspPingCtlNhAddress       OBJECT-TYPE
    SYNTAX      InetAddress (SIZE (0|4|16))
    MAX-ACCESS  read-create
    STATUS      current
    DESCRIPTION
        "The value of tmnxOamLspPingCtlNhAddress specifies the interface
         address to the next hop which will be used to transmit the LSP ping.

         The supported object combinations for LSP ping tests are listed in the
         tmnxOamLspPingCtlTable DESCRIPTION clause."
    DEFVAL      { ''H }
    ::= { tmnxOamLspPingCtlEntry 15 }

tmnxOamLspPingCtlTestSubMode     OBJECT-TYPE
    SYNTAX      TmnxOamLspTestSubMode
    MAX-ACCESS  read-create
    STATUS      current
    DESCRIPTION
        "The value of tmnxOamLspPingCtlTestSubMode specifies the type of LSP
         ping test to perform.

         When this object is 'unspecified(1)', the type of LSP ping test to be
         performed is determined when the test is started, from the set of
         tmnxOamLspPingCtlTable objects configured with non-default values.

         If there is a mismatch between tmnxOamLspPingCtlTestSubMode and the
         type of the LSP to be tested, the test will fail.  For example, if
         tmnxOamLspPingCtlTestSubMode is 'static(2)', and
         tmnxOamLspPingCtlLspName refers to an LSP with
         TIMETRA-MPLS-MIB::vRtrMplsLspType not equal to 'mplsTp(7)', the test
         will fail.

         The supported object combinations for LSP ping tests are listed in the
         tmnxOamLspPingCtlTable DESCRIPTION clause."
    DEFVAL      { unspecified }
    ::= { tmnxOamLspPingCtlEntry 16 }

tmnxOamLspPingCtlMplsTpPathType  OBJECT-TYPE
    SYNTAX      TmnxOamMplsTpPathType
    MAX-ACCESS  read-create
    STATUS      current
    DESCRIPTION
        "The value of tmnxOamLspPingCtlMplsTpPathType specifies the type of the
         MPLS-TP path to be tested.

         The supported object combinations for LSP ping tests are listed in the
         tmnxOamLspPingCtlTable DESCRIPTION clause."
    DEFVAL      { active }
    ::= { tmnxOamLspPingCtlEntry 17 }

tmnxOamLspPingCtlMplsTpGlobalId  OBJECT-TYPE
    SYNTAX      TmnxMplsTpGlobalID
    MAX-ACCESS  read-create
    STATUS      current
    DESCRIPTION
        "The value of tmnxOamLspPingCtlMplsTpGlobalId specifies the target
         MPLS-TP Global Identifier to be used for the test.

         The supported object combinations for LSP ping tests are listed in the
         tmnxOamLspPingCtlTable DESCRIPTION clause."
    DEFVAL      { 0 }
    ::= { tmnxOamLspPingCtlEntry 18 }

tmnxOamLspPingCtlMplsTpNodeId    OBJECT-TYPE
    SYNTAX      TmnxMplsTpNodeID
    MAX-ACCESS  read-create
    STATUS      current
    DESCRIPTION
        "The value of tmnxOamLspPingCtlMplsTpNodeId specifies the target
         MPLS-TP Node Identifier to be used for the test.

         A value of zero indicates that no Node Identifier has been configured.

         The supported object combinations for LSP ping tests are listed in the
         tmnxOamLspPingCtlTable DESCRIPTION clause."
    DEFVAL      { 0 }
    ::= { tmnxOamLspPingCtlEntry 19 }

tmnxOamLspPingCtlAssocChannel    OBJECT-TYPE
    SYNTAX      TmnxOamLspAssocChannel
    MAX-ACCESS  read-create
    STATUS      current
    DESCRIPTION
        "The value of tmnxOamLspPingCtlAssocChannel specifies the launched echo
         request's usage of the Associated Channel (ACH) mechanism, when
         testing an MPLS-TP LSP.

         When tmnxOamLspPingCtlTestSubMode is 'static(2)', the default value
         for tmnxOamLspPingCtlAssocChannel is 'nonIp(2)'.

         The supported object combinations for LSP ping tests are listed in the
         tmnxOamLspPingCtlTable DESCRIPTION clause."
    DEFVAL      { notApplicable }
    ::= { tmnxOamLspPingCtlEntry 20 }

tmnxOamLspPingCtlForce           OBJECT-TYPE
    SYNTAX      TruthValue
    MAX-ACCESS  read-create
    STATUS      current
    DESCRIPTION
        "The value of tmnxOamLspPingCtlForce specifies whether or not to force
         the transmission of the 'lspPing' request PDU(s).

         If tmnxOamLspPingCtlForce is 'true(1)', the test will proceed and
         request PDU(s) will be sent regardless of the local operational status
         of the tested LSP path.

         If tmnxOamLspPingCtlForce is 'false(2)',  the test will fail
         immediately when the local operational status of the tested LSP path is
         down.

         The supported object combinations for LSP ping tests are listed in the
         tmnxOamLspPingCtlTable DESCRIPTION clause."
    DEFVAL      { false }
    ::= { tmnxOamLspPingCtlEntry 21 }

tmnxOamLspPingCtlIgpInstance     OBJECT-TYPE
    SYNTAX      TmnxIgpInstance
    MAX-ACCESS  read-create
    STATUS      current
    DESCRIPTION
        "The value of tmnxOamLspPingCtlIgpInstance specifies the Interior
         Gateway Protocol (IGP) instance to be used for the test.

         The supported object combinations for LSP ping tests are listed in the
         tmnxOamLspPingCtlTable DESCRIPTION clause."
    DEFVAL      { 0 }
    ::= { tmnxOamLspPingCtlEntry 22 }

tmnxOamVprnPingCtlTable          OBJECT-TYPE
    SYNTAX      SEQUENCE OF TmnxOamVprnPingCtlEntry
    MAX-ACCESS  not-accessible
    STATUS      current
    DESCRIPTION
        "Defines the Nokia SROS OAM VPRN Ping Control Table for providing, via
         SNMP, the capability of performing Nokia SROS OAM 'vprnPing' test
         operations.

         The results of these tests are stored in the tmnxOamPingResultsTable
         and the tmnxOamTrProbeHistoryTable.  There will be no entries for
         these test in the tmnxOamPingHistoryTable."
    ::= { tmnxOamPingObjs 10 }

tmnxOamVprnPingCtlEntry          OBJECT-TYPE
    SYNTAX      TmnxOamVprnPingCtlEntry
    MAX-ACCESS  not-accessible
    STATUS      current
    DESCRIPTION
        "Defines an entry in the tmnxOamVprnPingCtlTable.  The first index
         element, tmnxOamPingCtlOwnerIndex, is of type SnmpAdminString,
         a textual convention that allows for use of the SNMPv3
         View-Based Access Control Model (RFC 2575 [11], VACM)
         and allows a management application to identify its entries.
         The second index, tmnxOamPingCtlTestIndex, enables the same
         management application to have multiple outstanding requests."
    INDEX       {
        tmnxOamPingCtlOwnerIndex,
        tmnxOamPingCtlTestIndex
    }
    ::= { tmnxOamVprnPingCtlTable 1 }

TmnxOamVprnPingCtlEntry          ::= SEQUENCE
{
    tmnxOamVprnPingCtlSourceIpAddr   IpAddress,
    tmnxOamVprnPingCtlReplyControl   TruthValue,
    tmnxOamVprnPingCtlTtl            Unsigned32,
    tmnxOamVprnPingCtlSrcAddrType    InetAddressType,
    tmnxOamVprnPingCtlSrcAddress     InetAddress
}

tmnxOamVprnPingCtlSourceIpAddr   OBJECT-TYPE
    SYNTAX      IpAddress
    MAX-ACCESS  read-create
    STATUS      obsolete
    DESCRIPTION
        "Specifies the IPv4 address to be used as the source for
         performing an OAM ping operation when tmnxOamPingCtlTestMode has
         a value of 'vprnPing'.   This parameter is required.

         This object was obsoleted in release 4.0 and replaced with InetAddress
         objects tmnxOamVprnPingCtlSrcAddrType and
         tmnxOamVprnPingCtlSrcAddress."
    DEFVAL      { '00000000'h }
    ::= { tmnxOamVprnPingCtlEntry 1 }

tmnxOamVprnPingCtlReplyControl   OBJECT-TYPE
    SYNTAX      TruthValue
    MAX-ACCESS  read-create
    STATUS      current
    DESCRIPTION
        "When the value of tmnxOamVprnPingCtlReplyControl is 'true', the
         OAM ping response is returned using the control plane.  If its value
         is 'false', the packet is sent via the data plane.

         This object is optional and is not relevant when
         tmnxOamPingCtlTestMode has a value other than 'vprnPing'."
    DEFVAL      { false }
    ::= { tmnxOamVprnPingCtlEntry 2 }

tmnxOamVprnPingCtlTtl            OBJECT-TYPE
    SYNTAX      Unsigned32 (1..255)
    UNITS       "time-to-live value"
    MAX-ACCESS  read-create
    STATUS      current
    DESCRIPTION
        "Specifies the vc-label time-to-live value.

         This object is optional and is not relevant when
         tmnxOamPingCtlTestMode has a value other than 'vprnPing'.

         While performing the test with a TTL of 1 no responses should ever be
         expected."
    DEFVAL      { 255 }
    ::= { tmnxOamVprnPingCtlEntry 3 }

tmnxOamVprnPingCtlSrcAddrType    OBJECT-TYPE
    SYNTAX      InetAddressType
    MAX-ACCESS  read-create
    STATUS      current
    DESCRIPTION
        "The value of tmnxOamVprnPingCtlSrcAddrType specifies the Internet
         address type stored in tmnxOamVprnPingCtlSrcAddress."
    DEFVAL      { unknown }
    ::= { tmnxOamVprnPingCtlEntry 4 }

tmnxOamVprnPingCtlSrcAddress     OBJECT-TYPE
    SYNTAX      InetAddress (SIZE (0|4|16))
    MAX-ACCESS  read-create
    STATUS      current
    DESCRIPTION
        "The value of tmnxOamVprnPingCtlSrcAddress specifies the Internet
         address to be used as the source for performing an OAM ping operation
         when tmnxOamPingCtlTestMode has a value of 'vprnPing'.

         This parameter is required."
    DEFVAL      { ''H }
    ::= { tmnxOamVprnPingCtlEntry 5 }

tmnxOamAtmPingCtlTable           OBJECT-TYPE
    SYNTAX      SEQUENCE OF TmnxOamAtmPingCtlEntry
    MAX-ACCESS  not-accessible
    STATUS      current
    DESCRIPTION
        "Defines the Nokia SROS OAM ATM Ping Control Table for providing, via
         SNMP, the capability of performing Nokia SROS OAM 'atmPing' test
         operations.

         The results of these tests are stored in the tmnxOamPingResultsTable
         and the tmnxOamPingHistoryTable."
    ::= { tmnxOamPingObjs 11 }

tmnxOamAtmPingCtlEntry           OBJECT-TYPE
    SYNTAX      TmnxOamAtmPingCtlEntry
    MAX-ACCESS  not-accessible
    STATUS      current
    DESCRIPTION
        "Defines an entry in the tmnxOamAtmPingCtlTable.  The first index
         element, tmnxOamPingCtlOwnerIndex, is of type SnmpAdminString,
         a textual convention that allows for use of the SNMPv3
         View-Based Access Control Model (RFC 2575 [11], VACM)
         and allows a management application to identify its entries.
         The second index, tmnxOamPingCtlTestIndex, enables the same
         management application to have multiple outstanding requests."
    INDEX       {
        tmnxOamPingCtlOwnerIndex,
        tmnxOamPingCtlTestIndex
    }
    ::= { tmnxOamAtmPingCtlTable 1 }

TmnxOamAtmPingCtlEntry           ::= SEQUENCE
{
    tmnxOamAtmPingCtlPortId          TmnxPortID,
    tmnxOamAtmPingCtlVpi             AtmVpIdentifier,
    tmnxOamAtmPingCtlVci             AtmVcIdentifier,
    tmnxOamAtmPingCtlLpbkLocation    OCTET STRING,
    tmnxOamAtmPingCtlSegment         INTEGER
}

tmnxOamAtmPingCtlPortId          OBJECT-TYPE
    SYNTAX      TmnxPortID
    MAX-ACCESS  read-create
    STATUS      current
    DESCRIPTION
        "The value of tmnxOamAtmPingCtlPortId is the ID of the access port of
         the target VC. This parameter is required."
    DEFVAL      { 0 }
    ::= { tmnxOamAtmPingCtlEntry 1 }

tmnxOamAtmPingCtlVpi             OBJECT-TYPE
    SYNTAX      AtmVpIdentifier
    MAX-ACCESS  read-create
    STATUS      current
    DESCRIPTION
        "The value of tmnxOamAtmPingCtlVpi is the VPI of the VC used to
         send the OAM ATM ping.  This is a required parameter."
    DEFVAL      { 0 }
    ::= { tmnxOamAtmPingCtlEntry 2 }

tmnxOamAtmPingCtlVci             OBJECT-TYPE
    SYNTAX      AtmVcIdentifier
    MAX-ACCESS  read-create
    STATUS      current
    DESCRIPTION
        "The value of tmnxOamAtmPingCtlVci is the VCI of the VC used to
         send the OAM ATM ping.  This is a required parameter."
    DEFVAL      { 0 }
    ::= { tmnxOamAtmPingCtlEntry 3 }

tmnxOamAtmPingCtlLpbkLocation    OBJECT-TYPE
    SYNTAX      OCTET STRING (SIZE (16))
    MAX-ACCESS  read-create
    STATUS      current
    DESCRIPTION
        "The value of tmnxOamAtmPingCtlLpbkLocation specifies the Loopback
         Location ID used in the ATM OAM loopback cell.  If all bits in the
         Loopback Location ID are '1', the destination of the OAM ATM ping
         is the far-end destination of the VC.  Otherwise the cell is destined
         to a specific ATM node in the ATM network.

         This is an optional parameter."
    DEFVAL      { 'FFFFFFFFFFFFFFFFFFFFFFFFFFFFFFFF'H }
    ::= { tmnxOamAtmPingCtlEntry 4 }

tmnxOamAtmPingCtlSegment         OBJECT-TYPE
    SYNTAX      INTEGER {
        endToEnd (1),
        segment  (2)
    }
    MAX-ACCESS  read-create
    STATUS      current
    DESCRIPTION
        "The value of tmnxOamAtmPingCtlSegment determines if the ATM OAM
         loopback cell is destined to the first segment going in the line
         direction or the PVCC's connection endpoint."
    DEFVAL      { endToEnd }
    ::= { tmnxOamAtmPingCtlEntry 5 }

tmnxOamMfibPingCtlTable          OBJECT-TYPE
    SYNTAX      SEQUENCE OF TmnxOamMfibPingCtlEntry
    MAX-ACCESS  not-accessible
    STATUS      current
    DESCRIPTION
        "Defines the Nokia SROS OAM  MFIB  Ping Control Table for
         providing, via SNMP, the capability of performing Nokia SROS
         OAM 'mfibPing' test operations.

         The results of these tests are stored in the tmnxOamPingResultsTable
         and the tmnxOamPingHistoryTable. Rows are created in the
         tmnxOamMfibPingCtlTable only for those entries in the
         tmnxOamPingCtlTable where tmnxOamPingCtlTestMode has a value of
         'mfibPing'."
    ::= { tmnxOamPingObjs 12 }

tmnxOamMfibPingCtlEntry          OBJECT-TYPE
    SYNTAX      TmnxOamMfibPingCtlEntry
    MAX-ACCESS  not-accessible
    STATUS      current
    DESCRIPTION
        "Defines an entry in the tmnxOamMfibPingCtlTable.  The
         first index element, tmnxOamPingCtlOwnerIndex, is of
         type SnmpAdminString, a textual convention that allows
         for use of the SNMPv3 View-Based Access Control Model
         (RFC 2575 [11], VACM) and allows a management
         application to identify its entries. The second index,
         tmnxOamPingCtlTestIndex, enables the same management
         application to have multiple outstanding requests."
    INDEX       {
        tmnxOamPingCtlOwnerIndex,
        tmnxOamPingCtlTestIndex
    }
    ::= { tmnxOamMfibPingCtlTable 1 }

TmnxOamMfibPingCtlEntry          ::= SEQUENCE
{
    tmnxOamMfibPingCtlSourceIpAddr   IpAddress,
    tmnxOamMfibPingCtlDestIpAddr     IpAddress,
    tmnxOamMfibPingCtlReplyControl   TruthValue,
    tmnxOamMfibPingCtlTtl            Unsigned32,
    tmnxOamMfibPingCtlSrcAddrType    InetAddressType,
    tmnxOamMfibPingCtlSrcAddress     InetAddress,
    tmnxOamMfibPingCtlDestAddrType   InetAddressType,
    tmnxOamMfibPingCtlDestAddress    InetAddress,
    tmnxOamMfibPingCtlDestMacAddr    MacAddress
}

tmnxOamMfibPingCtlSourceIpAddr   OBJECT-TYPE
    SYNTAX      IpAddress
    MAX-ACCESS  read-write
    STATUS      obsolete
    DESCRIPTION
        "Specifies the IPv4 address to be used as the source for performing
         an OAM ping operation when tmnxOamPingCtlTestMode has a value of
         'mfibPing' in which case this parameter is required.  If
         tmnxOamPingCtlTestMode is different from 'mfibPing' this field is
         ignored.

         This object was obsoleted in release 4.0 and replaced with InetAddress
         objects tmnxOamMfibPingCtlSrcAddrType and
         tmnxOamMfibPingCtlSrcAddress."
    DEFVAL      { '00000000'h }
    ::= { tmnxOamMfibPingCtlEntry 1 }

tmnxOamMfibPingCtlDestIpAddr     OBJECT-TYPE
    SYNTAX      IpAddress
    MAX-ACCESS  read-write
    STATUS      obsolete
    DESCRIPTION
        "Specifies the IPv4 multicast address to be used as the destination for
         performing an OAM ping operation when tmnxOamPingCtlTestMode has a
         value of 'mfibPing' in which case this parameter is required. If
         tmnxOamPingCtlTestMode is different from 'mfibPing' this field is
         ignored.

         This object was obsoleted in release 4.0 and replaced with InetAddress
         objects tmnxOamMfibPingCtlDestAddrType and
         tmnxOamMfibPingCtlDestAddress."
    DEFVAL      { '00000000'h }
    ::= { tmnxOamMfibPingCtlEntry 2 }

tmnxOamMfibPingCtlReplyControl   OBJECT-TYPE
    SYNTAX      TruthValue
    MAX-ACCESS  read-write
    STATUS      current
    DESCRIPTION
        "When the value of tmnxOamMfibPingCtlReplyControl is 'true', the OAM
         ping response is returned using the control plane. If its value is
         'false', the packet is sent via the data plane.

         This object is optional and is not relevant when
         tmnxOamPingCtlTestMode has a value other than 'mfibPing'."
    DEFVAL      { false }
    ::= { tmnxOamMfibPingCtlEntry 3 }

tmnxOamMfibPingCtlTtl            OBJECT-TYPE
    SYNTAX      Unsigned32 (1..255)
    UNITS       "time-to-live value"
    MAX-ACCESS  read-write
    STATUS      current
    DESCRIPTION
        "Specifies the vc-label time-to-live value. This object is optional and
         is not relevant when tmnxOamPingCtlTestMode has a value other than
         'mfibPing'. While performing the test with a TTL of 1 no responses
         should ever be expected."
    DEFVAL      { 255 }
    ::= { tmnxOamMfibPingCtlEntry 4 }

tmnxOamMfibPingCtlSrcAddrType    OBJECT-TYPE
    SYNTAX      InetAddressType
    MAX-ACCESS  read-write
    STATUS      current
    DESCRIPTION
        "The value of tmnxOamMfibPingCtlSrcAddrType specifies the Internet
         address type stored in tmnxOamMfibPingCtlSrcAddress."
    DEFVAL      { unknown }
    ::= { tmnxOamMfibPingCtlEntry 5 }

tmnxOamMfibPingCtlSrcAddress     OBJECT-TYPE
    SYNTAX      InetAddress (SIZE (0|4|16))
    MAX-ACCESS  read-write
    STATUS      current
    DESCRIPTION
        "The value of tmnxOamMfibPingCtlSrcAddress specifies the Internet
         address to be used as the source for performing an OAM ping
         operation when tmnxOamPingCtlTestMode has a value of 'mfibPing'
         and the value of tmnxOamMfibPingCtlDestMacAddr is all zeros, in
         which case this parameter is required.  If tmnxOamPingCtlTestMode is
         different from 'mfibPing' this field is ignored."
    DEFVAL      { ''H }
    ::= { tmnxOamMfibPingCtlEntry 6 }

tmnxOamMfibPingCtlDestAddrType   OBJECT-TYPE
    SYNTAX      InetAddressType
    MAX-ACCESS  read-write
    STATUS      current
    DESCRIPTION
        "The value of tmnxOamMfibPingCtlDestAddrType specifies the Internet
         multicast address type stored in tmnxOamMfibPingCtlDestAddress."
    DEFVAL      { unknown }
    ::= { tmnxOamMfibPingCtlEntry 7 }

tmnxOamMfibPingCtlDestAddress    OBJECT-TYPE
    SYNTAX      InetAddress (SIZE (0|4|16))
    MAX-ACCESS  read-write
    STATUS      current
    DESCRIPTION
        "The value of tmnxOamMfibPingCtlDestAddress specifies the Internet
         multicast address to be used as the destination for performing an
         OAM ping operation when tmnxOamPingCtlTestMode has a value of
         'mfibPing' and the value of tmnxOamMfibPingCtlDestMacAddr is all zeros,
         in which case this parameter is required.  If tmnxOamPingCtlTestMode is
         different from 'mfibPing' this field is ignored."
    DEFVAL      { ''H }
    ::= { tmnxOamMfibPingCtlEntry 8 }

tmnxOamMfibPingCtlDestMacAddr    OBJECT-TYPE
    SYNTAX      MacAddress
    MAX-ACCESS  read-write
    STATUS      current
    DESCRIPTION
        "The value of tmnxOamMfibPingCtlDestMacAddr specifies the IPv6
         multicast MAC address to be used as the destination for performing an
         OAM ping operation when tmnxOamPingCtlTestMode has a value of
         'mfibPing' and objects tmnxOamMfibPingCtlSrcAddrType and
         tmnxOamMfibPingCtlDestAddrType have a value of 'unknown (0)',
         in which case this parameter is required.  If tmnxOamPingCtlTestMode is
         different from 'mfibPing' this field is ignored."
    DEFVAL      { '000000000000'H }
    ::= { tmnxOamMfibPingCtlEntry 9 }

tmnxOamCpePingCtlTable           OBJECT-TYPE
    SYNTAX      SEQUENCE OF TmnxOamCpePingCtlEntry
    MAX-ACCESS  not-accessible
    STATUS      current
    DESCRIPTION
        "Defines the Nokia SROS OAM CPE Ping Control Table for providing, via
         SNMP, the capability of performing Nokia SROS OAM 'cpePing' test
         operations.

         The results of these tests are stored in the tmnxOamPingResultsTable
         and the tmnxOamPingHistoryTable. Rows are created in the
         tmnxOamCpePingCtlTable only for those entries in the
         tmnxOamPingCtlTable where tmnxOamPingCtlTestMode has a value of
         'cpePing'."
    ::= { tmnxOamPingObjs 13 }

tmnxOamCpePingCtlEntry           OBJECT-TYPE
    SYNTAX      TmnxOamCpePingCtlEntry
    MAX-ACCESS  not-accessible
    STATUS      current
    DESCRIPTION
        "Defines an entry in the tmnxOamCpePingCtlTable. The first index
         element, tmnxOamPingCtlOwnerIndex, is of type SnmpAdminString, a
         textual convention that allows for use of the SNMPv3 View-Based
         Access Control Model (RFC 2575 [11], VACM) and allows a management
         application to identify its entries.  The second index,
         tmnxOamPingCtlTestIndex, enables the same management application to
         have multiple outstanding requests."
    INDEX       {
        tmnxOamPingCtlOwnerIndex,
        tmnxOamPingCtlTestIndex
    }
    ::= { tmnxOamCpePingCtlTable 1 }

TmnxOamCpePingCtlEntry           ::= SEQUENCE
{
    tmnxOamCpePingCtlSourceIpAddr    IpAddress,
    tmnxOamCpePingCtlSendControl     TruthValue,
    tmnxOamCpePingCtlReplyControl    TruthValue,
    tmnxOamCpePingCtlTtl             Unsigned32,
    tmnxOamCpePingCtlSrceMacAddr     MacAddress,
    tmnxOamCpePingCtlSrcAddrType     InetAddressType,
    tmnxOamCpePingCtlSrcAddress      InetAddress
}

tmnxOamCpePingCtlSourceIpAddr    OBJECT-TYPE
    SYNTAX      IpAddress
    MAX-ACCESS  read-write
    STATUS      obsolete
    DESCRIPTION
        "Specifies the IPv4 address to be used as the source for performing
         an CPE ping operation when tmnxOamPingCtlTestMode has a value of
         'cpePing'.  This parameter is required for 'cpePing' and ignored in
         all other cases.

         This object was obsoleted in release 4.0 and replaced with InetAddress
         objects tmnxOamCpePingCtlSrcAddrType and tmnxOamCpePingCtlSrcAddress."
    DEFVAL      { '00000000'h }
    ::= { tmnxOamCpePingCtlEntry 1 }

tmnxOamCpePingCtlSendControl     OBJECT-TYPE
    SYNTAX      TruthValue
    MAX-ACCESS  read-write
    STATUS      current
    DESCRIPTION
        "The value of tmnxOamCpePingCtlSendControl specifies whether the
         outbound OAM ping packet will use the data plane or the control plane.

         When the value is 'false', the packet is sent using the data plane.

         As of SROS release 13.0 R1, a test cannot be started if
         tmnxOamCpePingCtlSendControl is 'true'.  A test is started using
         tmnxOamPingCtlAdminStatus.

         This object will be marked obsolete in a future release."
    DEFVAL      { false }
    ::= { tmnxOamCpePingCtlEntry 2 }

tmnxOamCpePingCtlReplyControl    OBJECT-TYPE
    SYNTAX      TruthValue
    MAX-ACCESS  read-write
    STATUS      current
    DESCRIPTION
        "When the value of tmnxOamCpePingCtlReplyControl is 'true', the OAM
         ping response is returned using the control plane. If its value is
         'false', the packet is sent via the data plane. This object is
         optional and is not relevant when tmnxOamPingCtlTestMode has a value
         other than 'cpePing'."
    DEFVAL      { false }
    ::= { tmnxOamCpePingCtlEntry 3 }

tmnxOamCpePingCtlTtl             OBJECT-TYPE
    SYNTAX      Unsigned32 (1..255)
    UNITS       "time-to-live value"
    MAX-ACCESS  read-write
    STATUS      current
    DESCRIPTION
        "Specifies the vc-label time-to-live value. This object is optional and
         is not relevant when tmnxOamPingCtlTestMode has a value other than
         'cpePing'. When performing the test with a TTL=1, the cpe-ping is only
         done to the local SAP(s)."
    DEFVAL      { 255 }
    ::= { tmnxOamCpePingCtlEntry 4 }

tmnxOamCpePingCtlSrceMacAddr     OBJECT-TYPE
    SYNTAX      MacAddress
    MAX-ACCESS  read-write
    STATUS      current
    DESCRIPTION
        "When set to a non zero value, the system will use the value as source
         mac address in the ARP request that will be sent to the CPE. If set to
         0, the MAC address configured for the CPM is used. This object is
         optional and is not relevant when tmnxOamPingCtlTestMode has a value
         other than 'cpePing'."
    DEFVAL      { '000000000000'H }
    ::= { tmnxOamCpePingCtlEntry 5 }

tmnxOamCpePingCtlSrcAddrType     OBJECT-TYPE
    SYNTAX      InetAddressType
    MAX-ACCESS  read-write
    STATUS      current
    DESCRIPTION
        "The value of tmnxOamCpePingCtlSrcAddrType specifies the Internet
         address type stored in tmnxOamCpePingCtlSrcAddress."
    DEFVAL      { unknown }
    ::= { tmnxOamCpePingCtlEntry 6 }

tmnxOamCpePingCtlSrcAddress      OBJECT-TYPE
    SYNTAX      InetAddress (SIZE (0|4|16))
    MAX-ACCESS  read-write
    STATUS      current
    DESCRIPTION
        "The value of tmnxOamCpePingCtlSrcAddress specifies the Internet
         address to be used as the source for performing a CPE ping operation
         when tmnxOamPingCtlTestMode has a value of 'cpePing'.  This parameter
         is required for 'cpePing' and ignored in all other cases."
    DEFVAL      { ''H }
    ::= { tmnxOamCpePingCtlEntry 7 }

tmnxOamMRInfoRespTable           OBJECT-TYPE
    SYNTAX      SEQUENCE OF TmnxOamMRInfoRespEntry
    MAX-ACCESS  not-accessible
    STATUS      current
    DESCRIPTION
        "Defines the Nokia SROS OAM Multicast Router Information Response Table
         for providing, via SNMP, the capability of performing Nokia SROS OAM
         'mrinfo' test operations. The results of these tests are stored in the
         tmnxOamPingResultsTable, the tmnxOamPingHistoryTable and the
         tmnxOamMRInfoRespTable."
    ::= { tmnxOamPingObjs 14 }

tmnxOamMRInfoRespEntry           OBJECT-TYPE
    SYNTAX      TmnxOamMRInfoRespEntry
    MAX-ACCESS  not-accessible
    STATUS      current
    DESCRIPTION
        "Defines an entry in the tmnxOamMRInfoRespTable.  The first index
         element, tmnxOamPingCtlOwnerIndex, is of type SnmpAdminString,
         a textual convention that allows for use of the SNMPv3
         View-Based Access Control Model (RFC 2575 [11], VACM)
         and allows a management application to identify its entries.
         The second index, tmnxOamPingCtlTestIndex, enables the same
         management application to have multiple outstanding requests."
    INDEX       {
        tmnxOamPingCtlOwnerIndex,
        tmnxOamPingCtlTestIndex,
        tmnxOamPingResultsTestRunIndex,
        tmnxOamPingHistoryIndex
    }
    ::= { tmnxOamMRInfoRespTable 1 }

TmnxOamMRInfoRespEntry           ::= SEQUENCE
{
    tmnxOamMRInfoRespCapabilities    BITS,
    tmnxOamMRInfoRespMinorVersion    Unsigned32,
    tmnxOamMRInfoRespMajorVersion    Unsigned32,
    tmnxOamMRInfoRespNumInterfaces   Unsigned32
}

tmnxOamMRInfoRespCapabilities    OBJECT-TYPE
    SYNTAX      BITS {
        leaf   (0),
        prune  (1),
        genid  (2),
        mtrace (3),
        snmp   (4)
    }
    MAX-ACCESS  read-only
    STATUS      current
    DESCRIPTION
        "tmnxOamMRInfoRespCapabilities indicates the capabilities of the router
         responding to the mrinfo request:
            leaf(0)     This is a leaf router
            prune(1)    This router understands pruning
            genid(2)    This router sends Generation Id's
            mtrace(3)   This router handles Mtrace requests
            snmp(4)     This router supports the DVMRP MIB"
    ::= { tmnxOamMRInfoRespEntry 1 }

tmnxOamMRInfoRespMinorVersion    OBJECT-TYPE
    SYNTAX      Unsigned32
    MAX-ACCESS  read-only
    STATUS      current
    DESCRIPTION
        "tmnxOamMRInfoRespMinorVersion indicates the minor software version on
         the router responding to the mrinfo request."
    ::= { tmnxOamMRInfoRespEntry 2 }

tmnxOamMRInfoRespMajorVersion    OBJECT-TYPE
    SYNTAX      Unsigned32
    MAX-ACCESS  read-only
    STATUS      current
    DESCRIPTION
        "tmnxOamMRInfoRespMajorVersion indicates the major software version on
         the router responding to the mrinfo request."
    ::= { tmnxOamMRInfoRespEntry 3 }

tmnxOamMRInfoRespNumInterfaces   OBJECT-TYPE
    SYNTAX      Unsigned32
    MAX-ACCESS  read-only
    STATUS      current
    DESCRIPTION
        "tmnxOamMRInfoRespNumInterfaces indicates the number of interfaces in
         the mrinfo response packet. These interfaces are listed in the
         tmnxOamMRInfoRespIfTable."
    ::= { tmnxOamMRInfoRespEntry 4 }

tmnxOamMRInfoRespIfTable         OBJECT-TYPE
    SYNTAX      SEQUENCE OF TmnxOamMRInfoRespIfEntry
    MAX-ACCESS  not-accessible
    STATUS      current
    DESCRIPTION
        "Defines the Nokia SROS OAM Multicast Router Information Interface
         Table for providing, via SNMP, the capability of performing Nokia SROS
         OAM 'mrinfo' test operation. The results of these tests are stored in
         the tmnxOamPingResultsTable, the tmnxOamPingHistoryTable and the
         tmnxOamMRInfoRespIfTable."
    ::= { tmnxOamPingObjs 15 }

tmnxOamMRInfoRespIfEntry         OBJECT-TYPE
    SYNTAX      TmnxOamMRInfoRespIfEntry
    MAX-ACCESS  not-accessible
    STATUS      current
    DESCRIPTION
        "Defines an entry in the tmnxOamMRInfoRespIfTable.  The first index
         element, tmnxOamPingCtlOwnerIndex, is of type SnmpAdminString,
         a textual convention that allows for use of the SNMPv3
         View-Based Access Control Model (RFC 2575 [11], VACM)
         and allows a management application to identify its entries.
         The second index, tmnxOamPingCtlTestIndex, enables the same
         management application to have multiple outstanding requests."
    INDEX       {
        tmnxOamPingCtlOwnerIndex,
        tmnxOamPingCtlTestIndex,
        tmnxOamPingResultsTestRunIndex,
        tmnxOamPingHistoryIndex,
        tmnxOamMRInfoRespIfIndex
    }
    ::= { tmnxOamMRInfoRespIfTable 1 }

TmnxOamMRInfoRespIfEntry         ::= SEQUENCE
{
    tmnxOamMRInfoRespIfIndex         Unsigned32,
    tmnxOamMRInfoRespIfAddress       IpAddress,
    tmnxOamMRInfoRespIfMetric        Unsigned32,
    tmnxOamMRInfoRespIfThreshold     Unsigned32,
    tmnxOamMRInfoRespIfFlags         BITS,
    tmnxOamMRInfoRespIfNbrCount      Unsigned32,
    tmnxOamMRInfoRespIfAddrType      InetAddressType,
    tmnxOamMRInfoRespIfAddr          InetAddress
}

tmnxOamMRInfoRespIfIndex         OBJECT-TYPE
    SYNTAX      Unsigned32
    MAX-ACCESS  not-accessible
    STATUS      current
    DESCRIPTION
        "tmnxOamMRInfoRespIfIndex is the index into the
         tmnxOamMRInfoRespIfTable.  The mrinfo response packet has
         the router's interfaces on which multicast is enabled.
         tmnxOamMRInfoRespIfIndex is used to identify those interfaces."
    ::= { tmnxOamMRInfoRespIfEntry 1 }

tmnxOamMRInfoRespIfAddress       OBJECT-TYPE
    SYNTAX      IpAddress
    MAX-ACCESS  read-only
    STATUS      obsolete
    DESCRIPTION
        "tmnxOamMRInfoRespIfAddress indicates the interface address on the
         router responding to the mrinfo request.

         This object was obsoleted in release 4.0 and replaced with InetAddress
         objects tmnxOamMRInfoRespIfAddrType and tmnxOamMRInfoRespIfAddr."
    ::= { tmnxOamMRInfoRespIfEntry 2 }

tmnxOamMRInfoRespIfMetric        OBJECT-TYPE
    SYNTAX      Unsigned32
    MAX-ACCESS  read-only
    STATUS      current
    DESCRIPTION
        "tmnxOamMRInfoRespIfMetric indicates the metric on the interface."
    ::= { tmnxOamMRInfoRespIfEntry 3 }

tmnxOamMRInfoRespIfThreshold     OBJECT-TYPE
    SYNTAX      Unsigned32
    MAX-ACCESS  read-only
    STATUS      current
    DESCRIPTION
        "tmnxOamMRInfoRespIfThreshold indicates the threshold on the interface."
    ::= { tmnxOamMRInfoRespIfEntry 4 }

tmnxOamMRInfoRespIfFlags         OBJECT-TYPE
    SYNTAX      BITS {
        tunnel    (0),
        srcrt     (1),
        reserved1 (2),
        reserved2 (3),
        down      (4),
        disabled  (5),
        querier   (6),
        leaf      (7)
    }
    MAX-ACCESS  read-only
    STATUS      current
    DESCRIPTION
        "tmnxOamMRInfoRespIfFlags indicates the flags associated with an
         interface:

         tunnel(0)         Neighbor reached via tunnel
         srcrt(1)          Tunnel uses IP source routing
         reserved1(2)      No longer used
         reserved2(3)      No longer used
         down(4)           Operational status down
         disabled(5)       Administrative status down
         querier(6)        Querier for interface
         leaf(7)           No downstream neighbors on interface"
    ::= { tmnxOamMRInfoRespIfEntry 5 }

tmnxOamMRInfoRespIfNbrCount      OBJECT-TYPE
    SYNTAX      Unsigned32
    MAX-ACCESS  read-only
    STATUS      current
    DESCRIPTION
        "tmnxOamMRInfoRespIfNbrCount indicates the number of multicast
         neighbors on the interface. The neighbors are listed in the
         tmnxOamMRInfoRespIfNbrTable."
    ::= { tmnxOamMRInfoRespIfEntry 6 }

tmnxOamMRInfoRespIfAddrType      OBJECT-TYPE
    SYNTAX      InetAddressType
    MAX-ACCESS  read-only
    STATUS      current
    DESCRIPTION
        "tmnxOamMRInfoRespIfAddrType indicates the Internet address type stored
         in tmnxOamMRInfoRespIfAddr."
    ::= { tmnxOamMRInfoRespIfEntry 7 }

tmnxOamMRInfoRespIfAddr          OBJECT-TYPE
    SYNTAX      InetAddress (SIZE (0|4|16))
    MAX-ACCESS  read-only
    STATUS      current
    DESCRIPTION
        "tmnxOamMRInfoRespIfAddr indicates the Internet address of the
         interface on the router responding to the mrinfo request."
    ::= { tmnxOamMRInfoRespIfEntry 8 }

tmnxOamMRInfoRespIfNbrTable      OBJECT-TYPE
    SYNTAX      SEQUENCE OF TmnxOamMRInfoRespIfNbrEntry
    MAX-ACCESS  not-accessible
    STATUS      current
    DESCRIPTION
        "Defines the Nokia SROS OAM Multicast Router Information Interface
         Neighbor Table for providing, via SNMP, the capability of performing
         Nokia SROS OAM 'mrInfo' test operation. This table contains entries
         for neighbors on an interface. The results of the mrinfo test are
         stored in the tmnxOamPingResultsTable, the tmnxOamPingHistoryTable,
         the tmnxOamMRInfoRespTable, the tmnxOamMRInfoRespIfTable and the
         tmnxOamMRInfoRespIfNbrTable."
    ::= { tmnxOamPingObjs 16 }

tmnxOamMRInfoRespIfNbrEntry      OBJECT-TYPE
    SYNTAX      TmnxOamMRInfoRespIfNbrEntry
    MAX-ACCESS  not-accessible
    STATUS      current
    DESCRIPTION
        "Defines an entry in the tmnxOamMRInfoRespIfNbrTable.  The first index
         element, tmnxOamPingCtlOwnerIndex, is of type SnmpAdminString,
         a textual convention that allows for use of the SNMPv3
         View-Based Access Control Model (RFC 2575 [11], VACM)
         and allows a management application to identify its entries.
         The second index, tmnxOamPingCtlTestIndex, enables the same
         management application to have multiple outstanding requests."
    INDEX       {
        tmnxOamPingCtlOwnerIndex,
        tmnxOamPingCtlTestIndex,
        tmnxOamPingResultsTestRunIndex,
        tmnxOamPingHistoryIndex,
        tmnxOamMRInfoRespIfIndex,
        tmnxOamMRInfoRespIfNbrIndex
    }
    ::= { tmnxOamMRInfoRespIfNbrTable 1 }

TmnxOamMRInfoRespIfNbrEntry      ::= SEQUENCE
{
    tmnxOamMRInfoRespIfNbrIndex      Unsigned32,
    tmnxOamMRInfoRespIfNbrAddress    IpAddress,
    tmnxOamMRInfoRespIfNbrAddrType   InetAddressType,
    tmnxOamMRInfoRespIfNbrAddr       InetAddress
}

tmnxOamMRInfoRespIfNbrIndex      OBJECT-TYPE
    SYNTAX      Unsigned32
    MAX-ACCESS  not-accessible
    STATUS      current
    DESCRIPTION
        "tmnxOamMRInfoRespIfNbrIndex is used to identify the multicast neighbor
         on the interface tmnxOamMRInfoRespIfIndex."
    ::= { tmnxOamMRInfoRespIfNbrEntry 1 }

tmnxOamMRInfoRespIfNbrAddress    OBJECT-TYPE
    SYNTAX      IpAddress
    MAX-ACCESS  read-only
    STATUS      obsolete
    DESCRIPTION
        "tmnxOamMRInfoRespIfNbrAddress indicates the address of the neighbor on
         the interface.

         This object was obsoleted in release 4.0 and replaced with InetAddress
         objects tmnxOamMRInfoRespIfNbrAddrType and tmnxOamMRInfoRespIfNbrAddr."
    ::= { tmnxOamMRInfoRespIfNbrEntry 2 }

tmnxOamMRInfoRespIfNbrAddrType   OBJECT-TYPE
    SYNTAX      InetAddressType
    MAX-ACCESS  read-only
    STATUS      current
    DESCRIPTION
        "tmnxOamMRInfoRespIfNbrAddrType indicates the Internet address type
         stored in tmnxOamMRInfoRespIfNbrAddr."
    ::= { tmnxOamMRInfoRespIfNbrEntry 3 }

tmnxOamMRInfoRespIfNbrAddr       OBJECT-TYPE
    SYNTAX      InetAddress (SIZE (0|4|16))
    MAX-ACCESS  read-only
    STATUS      current
    DESCRIPTION
        "tmnxOamMRInfoRespIfNbrAddr indicates the Internet address of the
         neighbor on the interface."
    ::= { tmnxOamMRInfoRespIfNbrEntry 4 }

tmnxOamVccvPingCtlTable          OBJECT-TYPE
    SYNTAX      SEQUENCE OF TmnxOamVccvPingCtlEntry
    MAX-ACCESS  not-accessible
    STATUS      current
    DESCRIPTION
        "Each row in tmnxOamVccvPingCtlTable contains the VCCV-specific
         configuration information needed to launch a VCCV (Virtual Circuit
         Connectivity Verification) ping test.  The rest of the configuration
         information needed to launch the test resides in the corresponding row
         of tmnxOamPingCtlTable.

         Results of VCCV ping tests are stored in tmnxOamPingResultsTable and
         tmnxOamPingHistoryTable.

         Four types of VCCV ping tests are supported:  AII Type 2, FEC-128
         Pseudowire, Spoke SDP FEC, and Transport Profile Static.  AII Type 2
         and Spoke SDP FEC offer two ways to specify a VCCV ping FEC-129
         Pseudowire test.

         In the Transport Profile Static case, the test type is configured
         (using tmnxOamVccvPingCtlTestSubMode).  In the other three cases, the
         test type is not configured (i.e. the default
         tmnxOamVccvPingCtlTestSubMode value 'unspecified(1)' is used).

         The following table has a row for each VCCV ping test type, showing
         the mandatory and optional objects applicable to the test type.
         Abbreviated VCCV ping test type names are used.

         Test
         Type   Mandatory Objects               Optional Objects
         ------ ------------------------------ ---------------------------------
         aiiTY2 tmnxOamVccvPingCtlSaiiAcId     *tmnxOamPingCtlSrcAddrType
                tmnxOamVccvPingCtlSaiiGlobalId *tmnxOamPingCtlSrcAddress
                tmnxOamVccvPingCtlSaiiPrefix   *tmnxOamPingCtlTgtAddrType
                tmnxOamVccvPingCtlTaiiAcId     *tmnxOamPingCtlTgtAddress
                tmnxOamVccvPingCtlTaiiGlobalId  tmnxOamVccvPingCtlReplyMode
                tmnxOamVccvPingCtlTaiiPrefix

         FEC128 tmnxOamVccvPingCtlSdpIdVcId    *tmnxOamPingCtlSrcAddrType
                                               *tmnxOamPingCtlSrcAddress
                                               *tmnxOamPingCtlTgtAddrType
                                               *tmnxOamPingCtlTgtAddress
                                               *tmnxOamVccvPingCtlPwId
                                                tmnxOamVccvPingCtlReplyMode
                                               #tmnxOamVccvPingCtlSwitTgtFecType
                                               #tmnxOamVccvPgTgStaticCtlAgi
                                               #tmnxOamVccvPgTgStaticCtlSaiiGlbl
                                               #tmnxOamVccvPgTgStaticCtlSaiiNode
                                               #tmnxOamVccvPgTgStaticCtlSaiiAcId
                                               #tmnxOamVccvPgTgStaticCtlTaiiGlbl
                                               #tmnxOamVccvPgTgStaticCtlTaiiNode
                                               #tmnxOamVccvPgTgStaticCtlTaiiAcId

         sdpFEC tmnxOamVccvPingCtlSpokeSdpId   *tmnxOamPingCtlSrcAddrType
                                               *tmnxOamPingCtlSrcAddress
                                               *tmnxOamPingCtlTgtAddrType
                                               *tmnxOamPingCtlTgtAddress
                                               #tmnxOamVccvPingCtlSaiiAcId
                                               #tmnxOamVccvPingCtlSaiiGlobalId
                                               #tmnxOamVccvPingCtlSaiiPrefix
                                               #tmnxOamVccvPingCtlTaiiAcId
                                               #tmnxOamVccvPingCtlTaiiGlobalId
                                               #tmnxOamVccvPingCtlTaiiPrefix
                                                tmnxOamVccvPingCtlReplyMode

         TPST   tmnxOamVccvPingCtlSdpIdVcId    *tmnxOamPingCtlSrcAddrType
                tmnxOamVccvPingCtlTestSubMode  *tmnxOamPingCtlSrcAddress
                                                tmnxOamVccvPingCtlAssocChannel
                                               #tmnxOamVccvPingCtlMplsTpGlobalId
                                               #tmnxOamVccvPingCtlMplsTpNodeId
                                               ^tmnxOamVccvPingCtlSwitTgtFecType
                                               ^tmnxOamVccvPgTgFec128CtlSrcAddrT
                                               ^tmnxOamVccvPgTgFec128CtlSrcAddr
                                               ^tmnxOamVccvPgTgFec128CtlDstAddrT
                                               ^tmnxOamVccvPgTgFec128CtlDstAddr
                                               ^tmnxOamVccvPgTgFec128CtlPwId
                                               ^tmnxOamVccvPgTgFec128CtlPwType

         ALL    N/A                             tmnxOamPingCtlFcName
                                                tmnxOamPingCtlInterval
                                                tmnxOamPingCtlProbeCount
                                                tmnxOamPingCtlProfile
                                                tmnxOamPingCtlSize
                                                tmnxOamPingCtlTimeOut
                                                tmnxOamVccvPingCtlTtl
         ------ ------------------------------ ---------------------------------

         In the table above,
         1.  The optional objects in the ALL row apply to all four VCCV ping
             test types.
         2.  The characters '*', '#', and '^' each mark an independent set of
             optional objects which must all be specified, or must all be
             unspecified.

         When an object combination other than a combination listed above is
         specified, values will be rejected or ignored, or the test will fail."
    REFERENCE
        "RFC 5085, 'Pseudowire Virtual Circuit Connectivity Verification (VCCV):
         A Control Channel for Pseudowires'"
    ::= { tmnxOamPingObjs 17 }

tmnxOamVccvPingCtlEntry          OBJECT-TYPE
    SYNTAX      TmnxOamVccvPingCtlEntry
    MAX-ACCESS  not-accessible
    STATUS      current
    DESCRIPTION
        "The system creates a row in tmnxOamVccvPingCtlTable when a row is
         created in tmnxOamPingCtlTable with tmnxOamPingCtlTestMode set to
         'vccvPing'.

         The system deletes a row in tmnxOamVccvPingCtlTable when the
         corresponding row in tmnxOamPingCtlTable is deleted."
    INDEX       {
        tmnxOamPingCtlOwnerIndex,
        tmnxOamPingCtlTestIndex
    }
    ::= { tmnxOamVccvPingCtlTable 1 }

TmnxOamVccvPingCtlEntry          ::= SEQUENCE
{
    tmnxOamVccvPingCtlSdpIdVcId      SdpBindId,
    tmnxOamVccvPingCtlReplyMode      INTEGER,
    tmnxOamVccvPingCtlPwId           TmnxVcIdOrNone,
    tmnxOamVccvPingCtlTtl            Unsigned32,
    tmnxOamVccvPingCtlSpokeSdpId     TmnxSpokeSdpIdOrZero,
    tmnxOamVccvPingCtlSaiiGlobalId   TmnxPwGlobalIdOrZero,
    tmnxOamVccvPingCtlSaiiPrefix     Unsigned32,
    tmnxOamVccvPingCtlSaiiAcId       Unsigned32,
    tmnxOamVccvPingCtlTaiiGlobalId   TmnxPwGlobalIdOrZero,
    tmnxOamVccvPingCtlTaiiPrefix     Unsigned32,
    tmnxOamVccvPingCtlTaiiAcId       Unsigned32,
    tmnxOamVccvPingCtlMplsTpGlobalId TmnxMplsTpGlobalID,
    tmnxOamVccvPingCtlMplsTpNodeId   TmnxMplsTpNodeID,
    tmnxOamVccvPingCtlTestSubMode    TmnxOamVccvTestSubMode,
    tmnxOamVccvPingCtlAssocChannel   TmnxOamVccvAssocChannel,
    tmnxOamVccvPingCtlSwitTgtFecType TmnxOamVccvSwitTgtFecType
}

tmnxOamVccvPingCtlSdpIdVcId      OBJECT-TYPE
    SYNTAX      SdpBindId
    MAX-ACCESS  read-create
    STATUS      current
    DESCRIPTION
        "The value of tmnxOamVccvPingCtlSdpIdVcId specifies the SDP binding of
         the pseudowire to be tested by a VCCV ping test.

         The all-zeros value indicates an unused SDP binding.

         The supported object combinations for VCCV ping tests are listed in
         the tmnxOamVccvPingCtlTable DESCRIPTION clause."
    DEFVAL      { '0000000000000000'h }
    ::= { tmnxOamVccvPingCtlEntry 1 }

tmnxOamVccvPingCtlReplyMode      OBJECT-TYPE
    SYNTAX      INTEGER {
        ip             (2),
        controlChannel (4)
    }
    MAX-ACCESS  read-create
    STATUS      current
    DESCRIPTION
        "The value of tmnxOamVccvPingCtlReplyMode specifies the band to be used
         by the echo reply PDU.
             ip(2)                 out-of-band reply
             controlChannel(4)     inband reply

         The supported object combinations for VCCV ping tests are listed in
         the tmnxOamVccvPingCtlTable DESCRIPTION clause."
    REFERENCE
        "RFC 4379, 'Detecting Multi-Protocol Label Switched (MPLS) Data Plane
         Failures', Section 3, 'Packet Format'."
    DEFVAL      { controlChannel }
    ::= { tmnxOamVccvPingCtlEntry 2 }

tmnxOamVccvPingCtlPwId           OBJECT-TYPE
    SYNTAX      TmnxVcIdOrNone
    MAX-ACCESS  read-create
    STATUS      current
    DESCRIPTION
        "The value of tmnxOamVccvPingCtlPwId specifies the pseudowire
         identifier to be used when performing a VCCV ping test on a FEC 128
         pseudowire. The pseudowire Id is a non-zero 32-bit connection ID
         required by FEC 128, as defined in RFC 4379.

         A value of zero indicates that no pseudowire Id has been configured.

         The supported object combinations for VCCV ping tests are listed in
         the tmnxOamVccvPingCtlTable DESCRIPTION clause."
    DEFVAL      { 0 }
    ::= { tmnxOamVccvPingCtlEntry 3 }

tmnxOamVccvPingCtlTtl            OBJECT-TYPE
    SYNTAX      Unsigned32 (1..255)
    UNITS       "time-to-live value"
    MAX-ACCESS  read-create
    STATUS      current
    DESCRIPTION
        "The value of tmnxOamVccvPingCtlTtl specifies the time-to-live value for
         the vc-label of the echo request message.  The outer label TTL is set
         to 255, regardless of this value.

         The supported object combinations for VCCV ping tests are listed in
         the tmnxOamVccvPingCtlTable DESCRIPTION clause."
    DEFVAL      { 1 }
    ::= { tmnxOamVccvPingCtlEntry 4 }

tmnxOamVccvPingCtlSpokeSdpId     OBJECT-TYPE
    SYNTAX      TmnxSpokeSdpIdOrZero
    MAX-ACCESS  read-create
    STATUS      current
    DESCRIPTION
        "The value of tmnxOamVccvPingCtlSpokeSdpId specifies the spoke SDP
         identifier to be used when performing a VCCV ping test on a FEC 129
         pseudowire.

         A value of zero indicates that no spoke SDP identifier has been
         configured.

         The supported object combinations for VCCV ping tests are listed in
         the tmnxOamVccvPingCtlTable DESCRIPTION clause."
    DEFVAL      { 0 }
    ::= { tmnxOamVccvPingCtlEntry 5 }

tmnxOamVccvPingCtlSaiiGlobalId   OBJECT-TYPE
    SYNTAX      TmnxPwGlobalIdOrZero
    MAX-ACCESS  read-create
    STATUS      current
    DESCRIPTION
        "The value of tmnxOamVccvPingCtlSaiiGlobalId specifies the global
         identifier of the Source Attachment Individual Identifier (SAII) to be
         used when testing a FEC 129 AII Type 2 pseudowire.

         A value of zero indicates that no global identifier has been
         configured.

         The supported object combinations for VCCV ping tests are listed in
         the tmnxOamVccvPingCtlTable DESCRIPTION clause."
    REFERENCE
        "RFC 5003, 'Attachment Individual Identifier (AII) Types for
         Aggregation', Section 3.2, 'AII Type 2'"
    DEFVAL      { 0 }
    ::= { tmnxOamVccvPingCtlEntry 6 }

tmnxOamVccvPingCtlSaiiPrefix     OBJECT-TYPE
    SYNTAX      Unsigned32
    MAX-ACCESS  read-create
    STATUS      current
    DESCRIPTION
        "The value of tmnxOamVccvPingCtlSaiiPrefix specifies the prefix of the
         Source Attachment Individual Identifier (SAII) to be used when testing
         a FEC 129 AII Type 2 pseudowire.

         A value of zero indicates that no prefix has been configured.

         The supported object combinations for VCCV ping tests are listed in
         the tmnxOamVccvPingCtlTable DESCRIPTION clause."
    REFERENCE
        "RFC 5003, 'Attachment Individual Identifier (AII) Types for
         Aggregation', Section 3.2, 'AII Type 2'"
    DEFVAL      { 0 }
    ::= { tmnxOamVccvPingCtlEntry 7 }

tmnxOamVccvPingCtlSaiiAcId       OBJECT-TYPE
    SYNTAX      Unsigned32
    MAX-ACCESS  read-create
    STATUS      current
    DESCRIPTION
        "The value of tmnxOamVccvPingCtlSaiiAcId specifies the attachment
         circuit identifier of the Source Attachment Individual Identifier
         (SAII) to be used when testing a FEC 129 AII Type 2 pseudowire.

         A value of zero indicates that no attachment circuit identifier has
         been configured.

         The supported object combinations for VCCV ping tests are listed in
         the tmnxOamVccvPingCtlTable DESCRIPTION clause."
    REFERENCE
        "RFC 5003, 'Attachment Individual Identifier (AII) Types for
         Aggregation', Section 3.2, 'AII Type 2'"
    DEFVAL      { 0 }
    ::= { tmnxOamVccvPingCtlEntry 8 }

tmnxOamVccvPingCtlTaiiGlobalId   OBJECT-TYPE
    SYNTAX      TmnxPwGlobalIdOrZero
    MAX-ACCESS  read-create
    STATUS      current
    DESCRIPTION
        "The value of tmnxOamVccvPingCtlTaiiGlobalId specifies the global
         identifier of the Target Attachment Individual Identifier (TAII) to be
         used when testing a FEC 129 AII Type 2 pseudowire.

         A value of zero indicates that no global identifier has been
         configured.

         The supported object combinations for VCCV ping tests are listed in
         the tmnxOamVccvPingCtlTable DESCRIPTION clause."
    REFERENCE
        "RFC 5003, 'Attachment Individual Identifier (AII) Types for
         Aggregation', Section 3.2, 'AII Type 2'"
    DEFVAL      { 0 }
    ::= { tmnxOamVccvPingCtlEntry 9 }

tmnxOamVccvPingCtlTaiiPrefix     OBJECT-TYPE
    SYNTAX      Unsigned32
    MAX-ACCESS  read-create
    STATUS      current
    DESCRIPTION
        "The value of tmnxOamVccvPingCtlTaiiPrefix specifies the prefix of the
         Target Attachment Individual Identifier (TAII) to be used when testing
         a FEC 129 AII Type 2 pseudowire.

         A value of zero indicates that no prefix has been configured.

         The supported object combinations for VCCV ping tests are listed in
         the tmnxOamVccvPingCtlTable DESCRIPTION clause."
    REFERENCE
        "RFC 5003, 'Attachment Individual Identifier (AII) Types for
         Aggregation', Section 3.2, 'AII Type 2'"
    DEFVAL      { 0 }
    ::= { tmnxOamVccvPingCtlEntry 10 }

tmnxOamVccvPingCtlTaiiAcId       OBJECT-TYPE
    SYNTAX      Unsigned32
    MAX-ACCESS  read-create
    STATUS      current
    DESCRIPTION
        "The value of tmnxOamVccvPingCtlTaiiAcId specifies the attachment
         circuit identifier of the Target Attachment Individual Identifier
         (TAII) to be used when testing a FEC 129 AII Type 2 pseudowire.

         A value of zero indicates that no attachment circuit identifier has
         been configured.

         The supported object combinations for VCCV ping tests are listed in
         the tmnxOamVccvPingCtlTable DESCRIPTION clause."
    REFERENCE
        "RFC 5003, 'Attachment Individual Identifier (AII) Types for
         Aggregation', Section 3.2, 'AII Type 2'"
    DEFVAL      { 0 }
    ::= { tmnxOamVccvPingCtlEntry 11 }

tmnxOamVccvPingCtlMplsTpGlobalId OBJECT-TYPE
    SYNTAX      TmnxMplsTpGlobalID
    MAX-ACCESS  read-create
    STATUS      current
    DESCRIPTION
        "The value of tmnxOamVccvPingCtlMplsTpGlobalId specifies the target
         MPLS-TP Global Identifier to be used for the test.

         The supported object combinations for VCCV ping tests are listed in
         the tmnxOamVccvPingCtlTable DESCRIPTION clause."
    DEFVAL      { 0 }
    ::= { tmnxOamVccvPingCtlEntry 12 }

tmnxOamVccvPingCtlMplsTpNodeId   OBJECT-TYPE
    SYNTAX      TmnxMplsTpNodeID
    MAX-ACCESS  read-create
    STATUS      current
    DESCRIPTION
        "The value of tmnxOamVccvPingCtlMplsTpNodeId specifies the target
         MPLS-TP Node Identifier to be used for the test.

         A value of zero indicates that no Node Identifier has been configured.

         The supported object combinations for VCCV ping tests are listed in
         the tmnxOamVccvPingCtlTable DESCRIPTION clause."
    DEFVAL      { 0 }
    ::= { tmnxOamVccvPingCtlEntry 13 }

tmnxOamVccvPingCtlTestSubMode    OBJECT-TYPE
    SYNTAX      TmnxOamVccvTestSubMode
    MAX-ACCESS  read-create
    STATUS      current
    DESCRIPTION
        "The value of tmnxOamVccvPingCtlTestSubMode specifies the type of VCCV
         ping test to perform.

         When this object is 'unspecified(1)', the type of VCCV ping test to be
         performed is determined when the test is started, from the set of
         tmnxOamVccvPingCtlTable objects configured with non-default values.

         If there is a mismatch between tmnxOamVccvPingCtlTestSubMode and the
         type of the pseudowire to be tested, the test will fail.  For example,
         if tmnxOamVccvPingCtlTestSubMode is 'static(2)', and there is no
         TIMETRA-SDP-MIB::sdpBindPwPathTable row for the test's SDP binding,
         the test will fail.

         The supported object combinations for VCCV ping tests are listed in
         the tmnxOamVccvPingCtlTable DESCRIPTION clause."
    DEFVAL      { unspecified }
    ::= { tmnxOamVccvPingCtlEntry 14 }

tmnxOamVccvPingCtlAssocChannel   OBJECT-TYPE
    SYNTAX      TmnxOamVccvAssocChannel
    MAX-ACCESS  read-create
    STATUS      current
    DESCRIPTION
        "The value of tmnxOamVccvPingCtlAssocChannel specifies the launched
         echo request's usage of the Associated Channel (ACH) mechanism, when
         performing an MPLS-TP VCCV ping test.

         When tmnxOamVccvPingCtlTestSubMode is 'static(2)', the default value
         for tmnxOamVccvPingCtlAssocChannel is 'nonIp(2)'.

         The supported object combinations for VCCV ping tests are listed in
         the tmnxOamVccvPingCtlTable DESCRIPTION clause."
    DEFVAL      { notApplicable }
    ::= { tmnxOamVccvPingCtlEntry 15 }

tmnxOamVccvPingCtlSwitTgtFecType OBJECT-TYPE
    SYNTAX      TmnxOamVccvSwitTgtFecType
    MAX-ACCESS  read-create
    STATUS      current
    DESCRIPTION
        "The value of tmnxOamVccvPingCtlSwitTgtFecType specifies the type of
         downstream FEC (Forward Equivalence Class) segment to be tested.

         This object must be set to a non-default value when the path to be
         tested starts with a FEC segment, and switches to a FEC segment with a
         different type.  For example, if the path to be tested starts with a
         static FEC, and switches to FEC 128, this object must be set to
         'fec128(2)'."
    DEFVAL      { none }
    ::= { tmnxOamVccvPingCtlEntry 16 }

tmnxOamIcmpPingCtlTable          OBJECT-TYPE
    SYNTAX      SEQUENCE OF TmnxOamIcmpPingCtlEntry
    MAX-ACCESS  not-accessible
    STATUS      current
    DESCRIPTION
        "tmnxOamIcmpPingCtlTable (along with tmnxOamPingCtlTable) contains the
         configuration information for ICMP ping tests.

         Test results are stored in tmnxOamPingResultsTable and
         tmnxOamPingHistoryTable."
    ::= { tmnxOamPingObjs 18 }

tmnxOamIcmpPingCtlEntry          OBJECT-TYPE
    SYNTAX      TmnxOamIcmpPingCtlEntry
    MAX-ACCESS  not-accessible
    STATUS      current
    DESCRIPTION
        "tmnxOamIcmpPingCtlEntry (along with tmnxOamPingCtlEntry) contains the
         configuration information for an ICMP ping test.

         A row is created when the corresponding tmnxOamPingCtlTestMode is set
         to 'icmpPing'.

         A row is destroyed when the corresponding tmnxOamPingCtlTable row is
         destroyed (using tmnxOamPingCtlRowStatus).

         The values in a particular row in this table cannot be changed when
         the corresponding tmnxOamPingCtlAdminStatus is 'enabled(1)'."
    INDEX       {
        tmnxOamPingCtlOwnerIndex,
        tmnxOamPingCtlTestIndex
    }
    ::= { tmnxOamIcmpPingCtlTable 1 }

TmnxOamIcmpPingCtlEntry          ::= SEQUENCE
{
    tmnxOamIcmpPingCtlRapid          TruthValue,
    tmnxOamIcmpPingCtlTtl            Unsigned32,
    tmnxOamIcmpPingCtlDSField        Unsigned32,
    tmnxOamIcmpPingCtlPattern        Integer32,
    tmnxOamIcmpPingCtlNhAddrType     InetAddressType,
    tmnxOamIcmpPingCtlNhAddress      InetAddress,
    tmnxOamIcmpPingCtlEgrIfIndex     InterfaceIndexOrZero,
    tmnxOamIcmpPingCtlBypassRouting  TruthValue,
    tmnxOamIcmpPingCtlDoNotFragment  TruthValue,
    tmnxOamIcmpPingCtlEgrIfName      TNamedItemOrEmpty
}

tmnxOamIcmpPingCtlRapid          OBJECT-TYPE
    SYNTAX      TruthValue
    MAX-ACCESS  read-create
    STATUS      current
    DESCRIPTION
        "The value of tmnxOamIcmpPingCtlRapid specifies whether or not to send
         ICMP ping probes in rapid sequence.

         Changing tmnxOamIcmpPingCtlRapid from 'false(2)' to 'true(1)'
         implicitly sets tmnxOamPingCtlIntervalUnits to 'centiseconds(2)'.  For
         example, if tmnxOamPingCtlInterval is 1, that makes the interval for
         the test 0.01 seconds.

         Changing tmnxOamIcmpPingCtlRapid from 'true(1)' to 'false(2)'
         implicitly sets tmnxOamPingCtlIntervalUnits to 'seconds(1)'.  For
         example, if tmnxOamPingCtlInterval is 1, that makes the interval for
         the test 1 second.

         tmnxOamIcmpPingCtlRapid = 'true(1)' and tmnxOamSaaCtlContinuous =
         'true(1)' is an unsupported combination."
    DEFVAL      { false }
    ::= { tmnxOamIcmpPingCtlEntry 1 }

tmnxOamIcmpPingCtlTtl            OBJECT-TYPE
    SYNTAX      Unsigned32 (1..128)
    MAX-ACCESS  read-create
    STATUS      current
    DESCRIPTION
        "The value of tmnxOamIcmpPingCtlTtl specifies the initial time-to-live
         value for the ICMP ping packets."
    DEFVAL      { 64 }
    ::= { tmnxOamIcmpPingCtlEntry 2 }

tmnxOamIcmpPingCtlDSField        OBJECT-TYPE
    SYNTAX      Unsigned32 (0..255)
    MAX-ACCESS  read-create
    STATUS      current
    DESCRIPTION
        "The value of tmnxOamIcmpPingCtlDSField specifies the value to load in
         the Type of Service (TOS) octet or the Traffic Class (TC) octet of the
         launched ICMP echo request(s).  The TOS octet is a field in the IPv4
         packet header.  The TC octet is a field in the IPv6 packet header.

         The value in the TOS or TC octet may influence the route, latency,
         and/or probability of loss for the echo request (and, by inference,
         for the associated data flow).

         This object is optional."
    REFERENCE
        "RFC  791, 'Internet Protocol', section 3.1.
         RFC 1812, 'Requirements for IP Version 4 Routers', section 5.3.2.
         RFC 2460, 'Internet Protocol, Version 6 (IPv6) Specification',
         section 7.
         RFC 2474, 'Definition of the Differentiated Services Field (DS Field)
         in the IPv4 and IPv6 Headers'."
    DEFVAL      { 0 }
    ::= { tmnxOamIcmpPingCtlEntry 3 }

tmnxOamIcmpPingCtlPattern        OBJECT-TYPE
    SYNTAX      Integer32 (-1 | 0..65535)
    MAX-ACCESS  read-create
    STATUS      current
    DESCRIPTION
        "The value of tmnxOamIcmpPingCtlPattern specifies a pattern to be
         repeated to fill the data field of the ICMP ping packet.  When the
         value -1 is specified, the data field will be filled with positional
         values."
    DEFVAL      { -1 }
    ::= { tmnxOamIcmpPingCtlEntry 4 }

tmnxOamIcmpPingCtlNhAddrType     OBJECT-TYPE
    SYNTAX      InetAddressType
    MAX-ACCESS  read-create
    STATUS      current
    DESCRIPTION
        "The value of tmnxOamIcmpPingCtlNhAddrType specifies the address type
         of the tmnxOamIcmpPingCtlNhAddress Internet address."
    DEFVAL      { unknown }
    ::= { tmnxOamIcmpPingCtlEntry 5 }

tmnxOamIcmpPingCtlNhAddress      OBJECT-TYPE
    SYNTAX      InetAddress (SIZE (0|4|16))
    MAX-ACCESS  read-create
    STATUS      current
    DESCRIPTION
        "The value of tmnxOamIcmpPingCtlNhAddress specifies the Internet
         address of the next-hop.

         Only one of tmnxOamIcmpPingCtlNhAddress, tmnxOamIcmpPingCtlEgrIfIndex,
         tmnxOamIcmpPingCtlEgrIfName, or tmnxOamIcmpPingCtlBypassRouting may be
         set to a non-default value.  Otherwise, 'inconsistentValue' is
         returned."
    DEFVAL      { ''H }
    ::= { tmnxOamIcmpPingCtlEntry 6 }

tmnxOamIcmpPingCtlEgrIfIndex     OBJECT-TYPE
    SYNTAX      InterfaceIndexOrZero
    MAX-ACCESS  read-create
    STATUS      current
    DESCRIPTION
        "The value of tmnxOamIcmpPingCtlEgrIfIndex specifies the ifIndex of the
         interface to use to transmit the ICMP ping packets.

         If a non-zero value is Set, it must be a known ifIndex.  The value
         stored is the corresponding interface name string.  When
         tmnxOamIcmpPingCtlEgrIfIndex is read, the stored interface name string
         is converted to an ifIndex (zero, if the interface no longer exists),
         and the ifIndex is returned.  When tmnxOamIcmpPingCtlEgrIfName is read,
         the stored interface name string is returned.

         If zero is Set, the empty string is stored in the interface name
         string.  When tmnxOamIcmpPingCtlEgrIfIndex is read, zero is returned.
         When tmnxOamIcmpPingCtlEgrIfName is read, the empty string is returned.

         Only one of tmnxOamIcmpPingCtlNhAddress, tmnxOamIcmpPingCtlEgrIfIndex,
         tmnxOamIcmpPingCtlEgrIfName, or tmnxOamIcmpPingCtlBypassRouting may be
         set to a non-default value.  Otherwise, 'inconsistentValue' is
         returned.

         Managers are encouraged to use tmnxOamIcmpPingCtlEgrIfName (instead of
         tmnxOamIcmpPingCtlEgrIfIndex) because tmnxOamIcmpPingCtlEgrIfIndex
         will be deleted in a future release."
    DEFVAL      { 0 }
    ::= { tmnxOamIcmpPingCtlEntry 7 }

tmnxOamIcmpPingCtlBypassRouting  OBJECT-TYPE
    SYNTAX      TruthValue
    MAX-ACCESS  read-create
    STATUS      current
    DESCRIPTION
        "The value of tmnxOamIcmpPingCtlBypassRouting specifies whether or not
         to send the ping request to a host on a directly attached network,
         bypassing the routing table.

         Only one of tmnxOamIcmpPingCtlNhAddress, tmnxOamIcmpPingCtlEgrIfIndex,
         tmnxOamIcmpPingCtlEgrIfName, or tmnxOamIcmpPingCtlBypassRouting may be
         set to a non-default value.  Otherwise, 'inconsistentValue' is
         returned."
    DEFVAL      { false }
    ::= { tmnxOamIcmpPingCtlEntry 8 }

tmnxOamIcmpPingCtlDoNotFragment  OBJECT-TYPE
    SYNTAX      TruthValue
    MAX-ACCESS  read-create
    STATUS      current
    DESCRIPTION
        "The value of tmnxOamIcmpPingCtlDoNotFragment specifies whether or not
         the IPv4 'DF' (Don't Fragment) bit is set in the ICMP ping packet(s)
         launched for the test.

         When tmnxOamIcmpPingCtlDoNotFragment is 'true(1)', the 'DF' bit is
         set.

         This object is significant if:
         1.  The target address type for the test (i.e.
             tmnxOamPingCtlTgtAddrType) is 'ipv4(1)', or
         2.  tmnxOamPingCtlTgtAddrType is 'dns(16)', and the DNS name resolves
             to an IPv4 address.
         Otherwise, this object is ignored."
    DEFVAL      { false }
    ::= { tmnxOamIcmpPingCtlEntry 9 }

tmnxOamIcmpPingCtlEgrIfName      OBJECT-TYPE
    SYNTAX      TNamedItemOrEmpty
    MAX-ACCESS  read-create
    STATUS      current
    DESCRIPTION
        "The value of tmnxOamIcmpPingCtlEgrIfName specifies the name of the
         interface to use to transmit the ICMP ping packets.  The value
         provided is accepted whether or not it is a known interface name
         (validation is done as part of executing the test).

         When tmnxOamIcmpPingCtlEgrIfName is Set, the given interface name
         string is stored.  When tmnxOamIcmpPingCtlEgrIfName is read, the
         interface name string is returned.  When tmnxOamIcmpPingCtlEgrIfIndex
         is read, the interface name string is converted to an ifIndex (zero if
         the interface name string is the empty string, or cannot be converted
         to an ifIndex), and the ifIndex is returned.

         Only one of tmnxOamIcmpPingCtlNhAddress, tmnxOamIcmpPingCtlEgrIfIndex,
         tmnxOamIcmpPingCtlEgrIfName, or tmnxOamIcmpPingCtlBypassRouting may be
         set to a non-default value.  Otherwise, 'inconsistentValue' is
         returned."
    DEFVAL      { ''H }
    ::= { tmnxOamIcmpPingCtlEntry 10 }

tmnxOamAncpTestCtlTable          OBJECT-TYPE
    SYNTAX      SEQUENCE OF TmnxOamAncpTestCtlEntry
    MAX-ACCESS  not-accessible
    STATUS      current
    DESCRIPTION
        "Defines the Nokia SROS OAM ANCP Control Table for providing,
         via SNMP, the capability of performing Nokia SROS OAM
         'ANCP loopback' test operations.
         The results of these tests are stored in the tmnxOamPingResultsTable
         and the tmnxOamAncpTestHistoryTable.  There will be no entries for
         these tests in the tmnxOamPingHistoryTable."
    ::= { tmnxOamPingObjs 19 }

tmnxOamAncpTestCtlEntry          OBJECT-TYPE
    SYNTAX      TmnxOamAncpTestCtlEntry
    MAX-ACCESS  not-accessible
    STATUS      current
    DESCRIPTION
        "Defines an entry in the tmnxOamAncpTestCtlTable.  The first index
         element, tmnxOamPingCtlOwnerIndex, is of type SnmpAdminString,
         a textual convention that allows for use of the SNMPv3
         View-Based Access Control Model (RFC 2575 [11], VACM)
         and allows a management application to identify its entries.
         The second index, tmnxOamPingCtlTestIndex, enables the same
         management application to have multiple outstanding requests."
    INDEX       {
        tmnxOamPingCtlOwnerIndex,
        tmnxOamPingCtlTestIndex
    }
    ::= { tmnxOamAncpTestCtlTable 1 }

TmnxOamAncpTestCtlEntry          ::= SEQUENCE
{
    tmnxOamAncpTestTarget            INTEGER,
    tmnxOamAncpTestTargetId          DisplayString,
    tmnxOamAncpTestcount             Integer32,
    tmnxOamAncpTestTimeout           Integer32
}

tmnxOamAncpTestTarget            OBJECT-TYPE
    SYNTAX      INTEGER {
        none         (0),
        subscriberId (1),
        ancpString   (2)
    }
    MAX-ACCESS  read-create
    STATUS      current
    DESCRIPTION
        "The object tmnxOamAncpTestTarget specifies how to interpret the value
         of the object tmnxOamAncpTestTargetId. If set to 'subscriberId', the
         object tmnxOamAncpTestTargetId is a printable character string which
         contains the subscriber-id. If set to 'ancpString', the object
         tmnxOamAncpTestTargetId is a printable character string which contains
         the ancp-string. If set to 'none', no value is specified, the object
         tmnxOamAncpTestTargetId is an empty string, and no ancp-loopback test
         can be performed."
    DEFVAL      { none }
    ::= { tmnxOamAncpTestCtlEntry 1 }

tmnxOamAncpTestTargetId          OBJECT-TYPE
    SYNTAX      DisplayString (SIZE (0..63))
    MAX-ACCESS  read-create
    STATUS      current
    DESCRIPTION
        "The object tmnxOamAncpTestTargetId contains the ID of the subscriber
         for which the ANCP loopback test must be performed. The content of the
         field is interpreted as being a subscriber-id of max 32 chars (in case
         the object tmnxOamAncpTestTarget is set to 'subscriberId'), or as
         being an acnp-string of max 63 chars (in case the object
         tmnxOamAncpTestTarget is set to 'ancpString')."
    DEFVAL      { "" }
    ::= { tmnxOamAncpTestCtlEntry 2 }

tmnxOamAncpTestcount             OBJECT-TYPE
    SYNTAX      Integer32 (0..32)
    MAX-ACCESS  read-create
    STATUS      current
    DESCRIPTION
        "The value of tmnxOamAncpTestcount specifies the number of messages the
         access node will use to test the circuit.
         If set to 0, the number of messages will be determined by the
         access node. Following settings are allowed:
         tmnxOamAncpTestcount   tmnxOamAncpTestTimeout
                0                   0
                1..32               0
                1..32               1..255"
    DEFVAL      { 0 }
    ::= { tmnxOamAncpTestCtlEntry 3 }

tmnxOamAncpTestTimeout           OBJECT-TYPE
    SYNTAX      Integer32 (0..255)
    UNITS       "seconds"
    MAX-ACCESS  read-create
    STATUS      current
    DESCRIPTION
        "The value of tmnxOamAncpTestTimeout specifies the number of seconds
         the controlling node will wait for a reply. This timeout value is also
         sent to the access node. If set to 0, the access node will pick a
         default value, while the control node will assume a value of 255
         seconds.

         Following settings are allowed:
         tmnxOamAncpTestcount   tmnxOamAncpTestTimeout
               0                   0
               1..32               0
               1..32               1..255"
    DEFVAL      { 0 }
    ::= { tmnxOamAncpTestCtlEntry 4 }

tmnxOamAncpTestHistoryTable      OBJECT-TYPE
    SYNTAX      SEQUENCE OF TmnxOamAncpTestHistoryEntry
    MAX-ACCESS  not-accessible
    STATUS      current
    DESCRIPTION
        "Defines a table for storing the results of an OAM ANCP test. The
         number of entries in this table for a test is limited to the results
         of 3 runs.

         An entry in this table is created when the result of an OAM
         ANCP test is determined.  An entry  is removed from this table when
         its corresponding tmnxOamPingCtlEntry is deleted."
    ::= { tmnxOamPingObjs 20 }

tmnxOamAncpTestHistoryEntry      OBJECT-TYPE
    SYNTAX      TmnxOamAncpTestHistoryEntry
    MAX-ACCESS  not-accessible
    STATUS      current
    DESCRIPTION
        "Defines an entry in the tmnxOamAncpTestHistoryTable. The first two
         index elements identify the tmnxOamPingCtlEntry that a
         tmnxOamAncpTestHistoryTable belongs to. The third index identifies a
         specific run of the OAM test. The fourth index element selects a
         single OAM ANCP test result."
    INDEX       {
        tmnxOamPingCtlOwnerIndex,
        tmnxOamPingCtlTestIndex,
        tmnxOamPingResultsTestRunIndex,
        tmnxOamAncpHistoryIndex
    }
    ::= { tmnxOamAncpTestHistoryTable 1 }

TmnxOamAncpTestHistoryEntry      ::= SEQUENCE
{
    tmnxOamAncpHistoryIndex          Unsigned32,
    tmnxOamAncpHistoryAncpString     DisplayString,
    tmnxOamAncpHistoryAccNodeCode    Unsigned32,
    tmnxOamAncpHistoryAccNodeResult  Unsigned32,
    tmnxOamAncpHistoryAccNodeRspStr  DisplayString
}

tmnxOamAncpHistoryIndex          OBJECT-TYPE
    SYNTAX      Unsigned32 (1..4294967295)
    MAX-ACCESS  not-accessible
    STATUS      current
    DESCRIPTION
        "An entry in this table is created when the result of a OAM
         ANCP test is determined. The initial 2 instance
         identifier index values identify the tmnxOamPingCtlEntry
         that This ANCP test result belongs
         to.  The tmnxOamAncpHistoryIndex element selects a single OAM
         probe result.

         The agent starts assigning tmnxOamAncpHistoryIndex values at 1 and
         wraps after exceeding the maximum possible value as defined by the
         limit of this object."
    ::= { tmnxOamAncpTestHistoryEntry 1 }

tmnxOamAncpHistoryAncpString     OBJECT-TYPE
    SYNTAX      DisplayString (SIZE (0..63))
    MAX-ACCESS  read-only
    STATUS      current
    DESCRIPTION
        "The object tmnxOamAncpHistoryAncpString indicates the value of the
         ancp-string used while running this ANCP test."
    ::= { tmnxOamAncpTestHistoryEntry 2 }

tmnxOamAncpHistoryAccNodeCode    OBJECT-TYPE
    SYNTAX      Unsigned32
    MAX-ACCESS  read-only
    STATUS      current
    DESCRIPTION
        "The object tmnxOamAncpHistoryAccNodeCode indicates, if different
         from 0, the return code received from the ANCP access node.
         The value of this field corresponds to the error codes defined in the
         draft-wadhwa-gsmp-l2control-configuration-01:
         - 0x500 Specified access line does not exist
         - 0x501 Loopback test timed out
         - 0x502 Reserved
         - 0x503 DSL line status showtime
         - 0x504 DSL line status idle
         - 0x505 DSL line status silent
         - 0x506 DSL line status training
         - 0x507 DSL line integrity error
         - 0x508 DSLAM resource not available
         - 0x509 Invalid test parameter"
    ::= { tmnxOamAncpTestHistoryEntry 3 }

tmnxOamAncpHistoryAccNodeResult  OBJECT-TYPE
    SYNTAX      Unsigned32
    MAX-ACCESS  read-only
    STATUS      current
    DESCRIPTION
        "The object tmnxOamAncpHistoryAccNodeResult indicates, if different
         from 0, the return result received from the ANCP access node.
         The value of this field corresponds to the result codes defined in the
         draft-wadhwa-gsmp-l2control-configuration-01:
         {
         - 1: NoSuccessAck
         - 2: AckAll
         - 3: Success
         - 4: Failure
         - 5: More
         - 6: ReturnReceipt
         }"
    ::= { tmnxOamAncpTestHistoryEntry 4 }

tmnxOamAncpHistoryAccNodeRspStr  OBJECT-TYPE
    SYNTAX      DisplayString
    MAX-ACCESS  read-only
    STATUS      current
    DESCRIPTION
        "The object tmnxOamAncpHistoryAccNodeRspStr indicates, if different
         from the empty string, the OAM-loopback-Test-Response-String received
         from the access node, as reply to the requested test."
    ::= { tmnxOamAncpTestHistoryEntry 5 }

tmnxOamP2mpLspPingCtlTable       OBJECT-TYPE
    SYNTAX      SEQUENCE OF TmnxOamP2mpLspPingCtlEntry
    MAX-ACCESS  not-accessible
    STATUS      current
    DESCRIPTION
        "tmnxOamP2mpLspPingCtlTable (along with tmnxOamPingCtlTable) contains
         the configuration information for Point-to-Multipoint (P2MP) Label
         Switched Path (LSP) ping tests."
    REFERENCE
        "RFC 6425, 'Detecting Data-Plane Failures in Point-to-Multipoint MPLS -
         Extensions to LSP Ping'."
    ::= { tmnxOamPingObjs 21 }

tmnxOamP2mpLspPingCtlEntry       OBJECT-TYPE
    SYNTAX      TmnxOamP2mpLspPingCtlEntry
    MAX-ACCESS  not-accessible
    STATUS      current
    DESCRIPTION
        "tmnxOamP2mpLspPingCtlEntry (along with tmnxOamPingCtlEntry) contains
         the configuration information for a P2MP LSP Ping test.

         A row is created when the corresponding tmnxOamPingCtlTestMode is set
         to 'p2mpLspPing'.

         A row is destroyed when the corresponding tmnxOamPingCtlTable row is
         destroyed (using tmnxOamPingCtlRowStatus).

         The values in a particular row in this table cannot be changed when
         the corresponding tmnxOamPingCtlAdminStatus is 'enabled(1)'.

         The results of a 'p2mpLspPing' test are available using
         tmnxOamPingResultsEntry and tmnxOamPingHistoryEntry."
    INDEX       {
        tmnxOamPingCtlOwnerIndex,
        tmnxOamPingCtlTestIndex
    }
    ::= { tmnxOamP2mpLspPingCtlTable 1 }

TmnxOamP2mpLspPingCtlEntry       ::= SEQUENCE
{
    tmnxOamP2mpLspPingCtlLspName     TLNamedItemOrEmpty,
    tmnxOamP2mpLspPingCtlInstName    TNamedItemOrEmpty,
    tmnxOamP2mpLspPingCtlTtl         Unsigned32,
    tmnxOamP2mpLspPingCtlP2MPId      Unsigned32,
    tmnxOamP2mpLspPingCtlSrcAddrType InetAddressType,
    tmnxOamP2mpLspPingCtlSrcAddr     InetAddress,
    tmnxOamP2mpLspPingCtlGrpAddrType InetAddressType,
    tmnxOamP2mpLspPingCtlGrpAddr     InetAddress,
    tmnxOamP2mpLspPingCtlOptionalTLV INTEGER
}

tmnxOamP2mpLspPingCtlLspName     OBJECT-TYPE
    SYNTAX      TLNamedItemOrEmpty
    MAX-ACCESS  read-write
    STATUS      current
    DESCRIPTION
        "The value of tmnxOamP2mpLspPingCtlLspName specifies the administrative
         name of the target RSVP P2MP Labeled Switch Path (LSP) for this OAM
         P2MP LSP Ping test. The LSP name must be unique within the base router
         instance.

         The objects tmnxOamP2mpLspPingCtlLspName and
         tmnxOamP2mpLspPingCtlP2MPId are mutually exclusive.

         An 'inconsistentValue' error is returned when attempting to set the
         value of the tmnxOamP2mpLspPingCtlLspName object to a non default
         value while the value of the tmnxOamP2mpLspPingCtlP2MPId object is
         already set to non default value.

         An 'inconsistentValue' error is returned when the value of
         tmnxOamPingCtlAdminStatus is set to 'enabled' if both the value of
         tmnxOamP2mpLspPingCtlLspName and the value of
         tmnxOamP2mpLspPingCtlP2MPId objects are set to default values."
    DEFVAL      { ''H }
    ::= { tmnxOamP2mpLspPingCtlEntry 1 }

tmnxOamP2mpLspPingCtlInstName    OBJECT-TYPE
    SYNTAX      TNamedItemOrEmpty
    MAX-ACCESS  read-write
    STATUS      current
    DESCRIPTION
        "This parameter identifies an instance of a P2MP LSP, either a primary
         or secondary instance of a RSVP P2MP LSP Tree."
    DEFVAL      { ''H }
    ::= { tmnxOamP2mpLspPingCtlEntry 2 }

tmnxOamP2mpLspPingCtlTtl         OBJECT-TYPE
    SYNTAX      Unsigned32 (1..255)
    UNITS       "time-to-live value"
    MAX-ACCESS  read-write
    STATUS      current
    DESCRIPTION
        "Specifies the outermost label time-to-live value.  This is an optional
         parameter for RSVP P2MP LSP. This parameter is not applicable for LDP
         P2MP LSP"
    DEFVAL      { 255 }
    ::= { tmnxOamP2mpLspPingCtlEntry 3 }

tmnxOamP2mpLspPingCtlP2MPId      OBJECT-TYPE
    SYNTAX      Unsigned32 (0 | 1..4294967295)
    MAX-ACCESS  read-write
    STATUS      current
    DESCRIPTION
        "The value of tmnxOamP2mpLspPingCtlP2MPId specifies the identifier of a
         Point to Multipoint (LDP P2MP) Label Switch Path (LSP) for this OAM
         P2MP LSP ping test.

         The objects tmnxOamP2mpLspPingCtlP2MPId and
         tmnxOamP2mpLspPingCtlLspName are mutually exclusive.

         An 'inconsistentValue' error is returned when attempting to set the
         value of the tmnxOamP2mpLspPingCtlP2MPId object to a non default value
         while the value of the tmnxOamP2mpLspPingCtlLspName object is already
         set to non default value.

         An 'inconsistentValue' error is returned when the value of
         tmnxOamPingCtlAdminStatus is set to 'enabled' if both the value of
         tmnxOamP2mpLspPingCtlP2MPId and the value of
         tmnxOamP2mpLspPingCtlLspName objects are set to default values."
    DEFVAL      { 0 }
    ::= { tmnxOamP2mpLspPingCtlEntry 4 }

tmnxOamP2mpLspPingCtlSrcAddrType OBJECT-TYPE
    SYNTAX      InetAddressType
    MAX-ACCESS  read-write
    STATUS      current
    DESCRIPTION
        "The value of tmnxOamP2mpLspPingCtlSrcAddrType specifies the address
         type of tmnxOamP2mpLspPingCtlSrcAddr.

         When tmnxOamPingCtlAdminStatus is to set to 'enable', objects
         tmnxOamP2mpLspPingCtlSrcAddrType, tmnxOamP2mpLspPingCtlSrcAddr,
         tmnxOamP2mpLspPingCtlGrpAddrType, and tmnxOamP2mpLspPingCtlGrpAddr
         should all have default values or should all have non-default values."
    DEFVAL      { unknown }
    ::= { tmnxOamP2mpLspPingCtlEntry 5 }

tmnxOamP2mpLspPingCtlSrcAddr     OBJECT-TYPE
    SYNTAX      InetAddress (SIZE (0|4|16))
    MAX-ACCESS  read-write
    STATUS      current
    DESCRIPTION
        "The value of tmnxOamP2mpLspPingCtlSrcAddr specifies the source address
         of a Point to Multipoint (LDP P2MP) Label Switch Path (LSP) for this
         OAM P2MP LSP ping test. This IP address must be valid unicast address.

         The objects tmnxOamP2mpLspPingCtlSrcAddr and
         tmnxOamP2mpLspPingCtlP2MPId are mutually exclusive.

         When tmnxOamPingCtlAdminStatus is to set to 'enable', objects
         tmnxOamP2mpLspPingCtlSrcAddrType, tmnxOamP2mpLspPingCtlSrcAddr,
         tmnxOamP2mpLspPingCtlGrpAddrType, and tmnxOamP2mpLspPingCtlGrpAddr
         should all have default values or should all have non-default values."
    DEFVAL      { ''H }
    ::= { tmnxOamP2mpLspPingCtlEntry 6 }

tmnxOamP2mpLspPingCtlGrpAddrType OBJECT-TYPE
    SYNTAX      InetAddressType
    MAX-ACCESS  read-write
    STATUS      current
    DESCRIPTION
        "The value of tmnxOamP2mpLspPingCtlGrpAddrType specifies the address
         type of tmnxOamP2mpLspPingCtlGrpAddr.

         When tmnxOamPingCtlAdminStatus is to set to 'enable', objects
         tmnxOamP2mpLspPingCtlSrcAddrType, tmnxOamP2mpLspPingCtlSrcAddr,
         tmnxOamP2mpLspPingCtlGrpAddrType, and tmnxOamP2mpLspPingCtlGrpAddr
         should all have default values or should all have non-default values."
    DEFVAL      { unknown }
    ::= { tmnxOamP2mpLspPingCtlEntry 7 }

tmnxOamP2mpLspPingCtlGrpAddr     OBJECT-TYPE
    SYNTAX      InetAddress (SIZE (0|4|16))
    MAX-ACCESS  read-write
    STATUS      current
    DESCRIPTION
        "The value of tmnxOamP2mpLspPingCtlGrpAddr specifies the group address
         of a Point to Multipoint (LDP P2MP) Label Switch Path (LSP) for this
         OAM P2MP LSP ping test. This IP address must be valid multicast
         address.

         The objects tmnxOamP2mpLspPingCtlGrpAddr and
         tmnxOamP2mpLspPingCtlP2MPId are mutually exclusive.

         When tmnxOamPingCtlAdminStatus is to set to 'enable', objects
         tmnxOamP2mpLspPingCtlSrcAddrType, tmnxOamP2mpLspPingCtlSrcAddr,
         tmnxOamP2mpLspPingCtlGrpAddrType, and tmnxOamP2mpLspPingCtlGrpAddr
         should all have default values or should all have non-default values."
    DEFVAL      { ''H }
    ::= { tmnxOamP2mpLspPingCtlEntry 8 }

tmnxOamP2mpLspPingCtlOptionalTLV OBJECT-TYPE
    SYNTAX      INTEGER {
        none            (1),
        vpnRecursiveFec (2)
    }
    MAX-ACCESS  read-write
    STATUS      current
    DESCRIPTION
        "The value of tmnxOamP2mpLspPingCtlOptionalTLV specifies which optional
         Type/Length/Value (TLV) structure to include in the MPLS echo request
         launched for the specified test.

         'vpnRecursiveFec(2)' specifies the proprietary inclusion of an RFC
         6512 'VPN-Recursive FEC Element'.

         'vpnRecursiveFec(2)' is required to successfully ping a P2MP leaf with
         the following characteristics:
         1.  The path between the P2MP root and the targeted leaf is a Virtual
             Private Network (VPN), e.g. an SROS Virtual Private Routed Network
             (VPRN) service.  And ..
         2.  The VPN has an RFC 4364 'Option B' boundary between two Border
             Gateway Protocol (BGP) Autonomous Systems.  And ..
         3.  The leaf resides on an SROS node (with support for this object) on
             the far side of the boundary (with respect to the root).

         A leaf residing on a non-SROS node may not respond (or may respond
         with an error) when 'vpnRecursiveFec(2)' is specified.

         'none(1)' specifies the inclusion of none of the optional TLVs
         described above."
    REFERENCE
        "RFC 4364, 'BGP/MPLS IP Virtual Private Networks (VPNs)', Section 10,
         'Multi-AS Backbones'.
         RFC 6512, 'Using Multipoint LDP When the Backbone Has No Route to the
         Root', Section 3.2.1, 'Non-Segmented Inter-AS P-Tunnels'."
    DEFVAL      { none }
    ::= { tmnxOamP2mpLspPingCtlEntry 9 }

tmnxOamP2mpLspPingIPAddressTable OBJECT-TYPE
    SYNTAX      SEQUENCE OF TmnxOamP2mpLspPingIPAddressEntry
    MAX-ACCESS  not-accessible
    STATUS      current
    DESCRIPTION
        "Defines the Nokia SROS OAM P2MP LSP ping IP Address Table for
         providing, via SNMP, the capability of performing Nokia SROS OAM
         'p2mpLspPing' test operations.

         This table provides the ability to add multiple IP Address
         destinations for the 'p2mpLspPing' test.

         The results of these tests are stored in the tmnxOamPingResultsTable
         and the tmnxOamPingHistoryTable."
    ::= { tmnxOamPingObjs 22 }

tmnxOamP2mpLspPingIPAddressEntry OBJECT-TYPE
    SYNTAX      TmnxOamP2mpLspPingIPAddressEntry
    MAX-ACCESS  not-accessible
    STATUS      current
    DESCRIPTION
        "Defines an entry in the tmnxOamP2mpLspPingIPAddressTable. The first
         index element, tmnxOamPingCtlOwnerIndex, is of type SnmpAdminString, a
         textual convention that allows for use of the SNMPv3 View-Based Access
         Control Model (RFC 2575 [11], VACM) and allows a management
         application to identify its entries. The second index,
         tmnxOamPingCtlTestIndex, enables the same management application to
         have multiple outstanding requests. The third and fourth index,
         tmnxOamP2mpLspPingCtlIpAddrType and tmnxOamP2mpLspPingCtlIpAddr
         enables the same management application to have multiple IP address
         destinations."
    INDEX       {
        tmnxOamPingCtlOwnerIndex,
        tmnxOamPingCtlTestIndex,
        tmnxOamP2mpLspPingCtlIpAddrIndex
    }
    ::= { tmnxOamP2mpLspPingIPAddressTable 1 }

TmnxOamP2mpLspPingIPAddressEntry ::= SEQUENCE
{
    tmnxOamP2mpLspPingCtlIpAddrIndex Unsigned32,
    tmnxOamP2mpLspPingCtlIpRowStatus RowStatus,
    tmnxOamP2mpLspPingCtlIpAddrType  InetAddressType,
    tmnxOamP2mpLspPingCtlIpAddr      InetAddress
}

tmnxOamP2mpLspPingCtlIpAddrIndex OBJECT-TYPE
    SYNTAX      Unsigned32 (1..5)
    MAX-ACCESS  not-accessible
    STATUS      current
    DESCRIPTION
        "The object tmnxOamP2mpLspPingCtlIpAddrIndex specifies the numerical
         row-order in the table."
    ::= { tmnxOamP2mpLspPingIPAddressEntry 1 }

tmnxOamP2mpLspPingCtlIpRowStatus OBJECT-TYPE
    SYNTAX      RowStatus
    MAX-ACCESS  read-create
    STATUS      current
    DESCRIPTION
        "The object tmnxOamP2mpLspPingCtlIpRowStatus allows for the creation
         and deletion of rows in the tmnxOamP2mpLspPingIPAddressTable."
    ::= { tmnxOamP2mpLspPingIPAddressEntry 2 }

tmnxOamP2mpLspPingCtlIpAddrType  OBJECT-TYPE
    SYNTAX      InetAddressType
    MAX-ACCESS  read-create
    STATUS      current
    DESCRIPTION
        "The value of tmnxOamP2mpLspPingCtlIpAddrType specifies the type of
         Internet address stored in tmnxOamP2mpLspPingCtlIpAddr."
    ::= { tmnxOamP2mpLspPingIPAddressEntry 3 }

tmnxOamP2mpLspPingCtlIpAddr      OBJECT-TYPE
    SYNTAX      InetAddress (SIZE (0|4|16))
    MAX-ACCESS  read-create
    STATUS      current
    DESCRIPTION
        "The value of tmnxOamP2mpLspPingCtlIpAddr specifies a remote Internet
         address to send P2MP LSP Ping packets for a particular test."
    ::= { tmnxOamP2mpLspPingIPAddressEntry 4 }

tmnxOamEthCfmPingCtlTable        OBJECT-TYPE
    SYNTAX      SEQUENCE OF TmnxOamEthCfmPingCtlEntry
    MAX-ACCESS  not-accessible
    STATUS      current
    DESCRIPTION
        "tmnxOamEthCfmPingCtlTable contains Ethernet CFM-specific configuration
         information for 'ethCfmLoopback', 'ethCfmTwoWayDelay', and
         'ethCfmTwoWaySlm' tests.

         This table extends the tmnxOamPingCtlTable.  A row is automatically
         created in this table when a row is created in tmnxOamPingCtlTable with
         tmnxOamPingCtlTestMode set to 'ethCfmLoopback', 'ethCfmTwoWayDelay', or
         'ethCfmTwoWaySlm'.  Deleting a row in tmnxOamPingCtlTable automatically
         deletes the row (if any) with the same index values in
         tmnxOamEthCfmPingCtlTable.

         Test results are stored in tmnxOamPingResultsTable and
         tmnxOamPingHistoryTable."
    ::= { tmnxOamPingObjs 23 }

tmnxOamEthCfmPingCtlEntry        OBJECT-TYPE
    SYNTAX      TmnxOamEthCfmPingCtlEntry
    MAX-ACCESS  not-accessible
    STATUS      current
    DESCRIPTION
        "tmnxOamEthCfmPingCtlEntry defines an entry in the
         tmnxOamEthCfmPingCtlTable.  Each index is an object in
         tmnxOamPingCtlTable."
    INDEX       {
        tmnxOamPingCtlOwnerIndex,
        tmnxOamPingCtlTestIndex
    }
    ::= { tmnxOamEthCfmPingCtlTable 1 }

TmnxOamEthCfmPingCtlEntry        ::= SEQUENCE
{
    tmnxOamEthCfmPingCtlTgtMacAddr   MacAddress,
    tmnxOamEthCfmPingCtlSrcMdIndex   Unsigned32,
    tmnxOamEthCfmPingCtlSrcMaIndex   Unsigned32,
    tmnxOamEthCfmPingCtlSrcMepId     Dot1agCfmMepIdOrZero,
    tmnxOamEthCfmPingCtlRemoteMepId  Dot1agCfmMepIdOrZero
}

tmnxOamEthCfmPingCtlTgtMacAddr   OBJECT-TYPE
    SYNTAX      MacAddress
    MAX-ACCESS  read-create
    STATUS      current
    DESCRIPTION
        "The value of tmnxOamEthCfmPingCtlTgtMacAddr specifies the destination
         MAC address for the test.

         A non-zero destination MAC address is required in each test frame sent
         for the test.  The destination MAC address can be specified directly
         (using this object) or indirectly (see the DESCRIPTION of
         tmnxOamEthCfmPingCtlRemoteMepId).

         Exactly one of tmnxOamEthCfmPingCtlTgtMacAddr and
         tmnxOamEthCfmPingCtlRemoteMepId must be assigned a non-default value.
         Otherwise, an attempt to administratively enable the test (using
         tmnxOamSaaCtlAdminStatus) will fail."
    DEFVAL      { '000000000000'H }
    ::= { tmnxOamEthCfmPingCtlEntry 1 }

tmnxOamEthCfmPingCtlSrcMdIndex   OBJECT-TYPE
    SYNTAX      Unsigned32
    MAX-ACCESS  read-create
    STATUS      current
    DESCRIPTION
        "The value of tmnxOamEthCfmPingCtlSrcMdIndex specifies the source CFM
         maintenance domain index for the test.  Zero is the null CFM
         maintenance domain index."
    DEFVAL      { 0 }
    ::= { tmnxOamEthCfmPingCtlEntry 2 }

tmnxOamEthCfmPingCtlSrcMaIndex   OBJECT-TYPE
    SYNTAX      Unsigned32
    MAX-ACCESS  read-create
    STATUS      current
    DESCRIPTION
        "The value of tmnxOamEthCfmPingCtlSrcMaIndex specifies the source CFM
         maintenance association index for the test.  Zero is the null CFM
         maintenance association index."
    DEFVAL      { 0 }
    ::= { tmnxOamEthCfmPingCtlEntry 3 }

tmnxOamEthCfmPingCtlSrcMepId     OBJECT-TYPE
    SYNTAX      Dot1agCfmMepIdOrZero
    MAX-ACCESS  read-create
    STATUS      current
    DESCRIPTION
        "The value of tmnxOamEthCfmPingCtlSrcMepId specifies the source
         Maintenance association End Point Identifier (MEP ID) for the test.
         Zero is the null MEP ID."
    DEFVAL      { 0 }
    ::= { tmnxOamEthCfmPingCtlEntry 4 }

tmnxOamEthCfmPingCtlRemoteMepId  OBJECT-TYPE
    SYNTAX      Dot1agCfmMepIdOrZero
    MAX-ACCESS  read-create
    STATUS      current
    DESCRIPTION
        "The value of tmnxOamEthCfmPingCtlRemoteMepId specifies the remote
         Maintenance association End Point Identifier (MEP ID) for the test.

         A non-zero destination MAC address is required in each test frame sent
         for the test.  The destination MAC address can be specified directly
         (using tmnxOamEthCfmPingCtlTgtMacAddr) or indirectly (using this
         object).

         Exactly one of tmnxOamEthCfmPingCtlTgtMacAddr and
         tmnxOamEthCfmPingCtlRemoteMepId must be assigned a non-default value.
         Otherwise, an attempt to administratively enable the test (using
         tmnxOamSaaCtlAdminStatus) will fail.

         Suppose this object is assigned a non-default value.  Then, at the
         start of each test run, SROS reads
         TIMETRA-IEEE8021-CFM-MIB::tmnxDot1agCfmLearnedRmtMacAddr to find the
         destination MAC address to use for the test run.

         The following index values are used for the read:
            tmnxOamEthCfmPingCtlSrcMdIndex,
            tmnxOamEthCfmPingCtlSrcMaIndex,
            tmnxOamEthCfmPingCtlSrcMepId,
            tmnxOamEthCfmPingCtlRemoteMepId.

         If a destination MAC address is not found, no test frames will be sent
         for the test run.  The number of frames to be sent during a test run is
         configured using tmnxOamPingCtlProbeCount.

         Configuring tmnxOamEthCfmPingCtlRemoteMepId (instead of
         tmnxOamEthCfmPingCtlDestMacAddr) has the following advantage: if the
         hardware hosting the test's far end is replaced (meaning a new
         destination MAC address is present), the test does not need to be
         reconfigured."
    DEFVAL      { 0 }
    ::= { tmnxOamEthCfmPingCtlEntry 5 }

tmnxOamVccvPgTgFec128CtlTable    OBJECT-TYPE
    SYNTAX      SEQUENCE OF TmnxOamVccvPgTgFec128CtlEntry
    MAX-ACCESS  not-accessible
    STATUS      current
    DESCRIPTION
        "tmnxOamVccvPgTgFec128CtlTable contains the target information for VCCV
         (Virtual Circuit Connectivity Verification) ping tests which switch to
         downstream FEC (Forward Equivalence Class) 128 segments."
    REFERENCE
        "RFC 4379, 'Detecting Multi-Protocol Label Switched (MPLS) Data Plane
         Failures', Section 3.2.9 ('FEC 128 Pseudowire (Current)')."
    ::= { tmnxOamPingObjs 24 }

tmnxOamVccvPgTgFec128CtlEntry    OBJECT-TYPE
    SYNTAX      TmnxOamVccvPgTgFec128CtlEntry
    MAX-ACCESS  not-accessible
    STATUS      current
    DESCRIPTION
        "tmnxOamVccvPgTgFec128CtlEntry contains the target information for a
         VCCV ping test which switches to a downstream FEC 128 segment.

         The values in a row are used to fill a 'FEC 128 Pseudowire' sub-TLV
         (Type, Length, Value) within the 'Target FEC Stack' TLV within the
         launched VCCV ping request.

         A row is created when the test's tmnxOamVccvPingCtlSwitTgtFecType is
         set to 'fec128(2)'.

         A row is destroyed when the tmnxOamVccvPingCtlTable row is destroyed.

         All the objects in a row must be set in one SNMP Set PDU.  Otherwise,
         the SNMP Set PDU will be rejected."
    REFERENCE
        "RFC 4379, 'Detecting Multi-Protocol Label Switched (MPLS) Data Plane
         Failures', Section 3.2.9 ('FEC 128 Pseudowire (Current)')."
    INDEX       {
        tmnxOamPingCtlOwnerIndex,
        tmnxOamPingCtlTestIndex
    }
    ::= { tmnxOamVccvPgTgFec128CtlTable 1 }

TmnxOamVccvPgTgFec128CtlEntry    ::= SEQUENCE
{
    tmnxOamVccvPgTgFec128CtlSrcAddrT InetAddressType,
    tmnxOamVccvPgTgFec128CtlSrcAddr  InetAddress,
    tmnxOamVccvPgTgFec128CtlDstAddrT InetAddressType,
    tmnxOamVccvPgTgFec128CtlDstAddr  InetAddress,
    tmnxOamVccvPgTgFec128CtlPwId     Unsigned32,
    tmnxOamVccvPgTgFec128CtlPwType   Unsigned32
}

tmnxOamVccvPgTgFec128CtlSrcAddrT OBJECT-TYPE
    SYNTAX      InetAddressType
    MAX-ACCESS  read-write
    STATUS      current
    DESCRIPTION
        "The value of tmnxOamVccvPgTgFec128CtlSrcAddrT specifies the address
         type of tmnxOamVccvPgTgFec128CtlSrcAddr."
    DEFVAL      { unknown }
    ::= { tmnxOamVccvPgTgFec128CtlEntry 1 }

tmnxOamVccvPgTgFec128CtlSrcAddr  OBJECT-TYPE
    SYNTAX      InetAddress (SIZE (0|4|16))
    MAX-ACCESS  read-write
    STATUS      current
    DESCRIPTION
        "The value of tmnxOamVccvPgTgFec128CtlSrcAddr specifies the value to be
         copied into the Sender's PE Address (Sender's Provider Edge Address)
         field of the 'FEC 128 Pseudowire' sub-TLV within the 'Target FEC
         Stack' TLV within the launched VCCV ping request."
    REFERENCE
        "RFC 4379, 'Detecting Multi-Protocol Label Switched (MPLS) Data Plane
         Failures', Section 3.2.9 ('FEC 128 Pseudowire (Current)')."
    DEFVAL      { ''H }
    ::= { tmnxOamVccvPgTgFec128CtlEntry 2 }

tmnxOamVccvPgTgFec128CtlDstAddrT OBJECT-TYPE
    SYNTAX      InetAddressType
    MAX-ACCESS  read-write
    STATUS      current
    DESCRIPTION
        "The value of tmnxOamVccvPgTgFec128CtlDstAddrT specifies the address
         type of tmnxOamVccvPgTgFec128CtlDstAddr."
    DEFVAL      { unknown }
    ::= { tmnxOamVccvPgTgFec128CtlEntry 3 }

tmnxOamVccvPgTgFec128CtlDstAddr  OBJECT-TYPE
    SYNTAX      InetAddress (SIZE (0|4|16))
    MAX-ACCESS  read-write
    STATUS      current
    DESCRIPTION
        "The value of tmnxOamVccvPgTgFec128CtlDstAddr specifies the value to be
         copied into the 'Remote PE Address' (Remote Provider Edge Address)
         field of the 'FEC 128 Pseudowire' sub-TLV within the 'Target FEC
         Stack' TLV within the launched VCCV ping request."
    REFERENCE
        "RFC 4379, 'Detecting Multi-Protocol Label Switched (MPLS) Data Plane
         Failures', Section 3.2.9 ('FEC 128 Pseudowire (Current)')."
    DEFVAL      { ''H }
    ::= { tmnxOamVccvPgTgFec128CtlEntry 4 }

tmnxOamVccvPgTgFec128CtlPwId     OBJECT-TYPE
    SYNTAX      Unsigned32
    MAX-ACCESS  read-write
    STATUS      current
    DESCRIPTION
        "The value of tmnxOamVccvPgTgFec128CtlPwId specifies the value to be
         copied into the 'PW ID' (Pseudowire Identifier) field of the 'FEC 128
         Pseudowire' sub-TLV within the 'Target FEC Stack' TLV within the
         launched VCCV ping request.

         Zero indicates no Pseudowire Identifier has been configured."
    REFERENCE
        "RFC 4379, 'Detecting Multi-Protocol Label Switched (MPLS) Data Plane
         Failures', Section 3.2.9 ('FEC 128 Pseudowire (Current)')."
    DEFVAL      { 0 }
    ::= { tmnxOamVccvPgTgFec128CtlEntry 5 }

tmnxOamVccvPgTgFec128CtlPwType   OBJECT-TYPE
    SYNTAX      Unsigned32 (0..65535)
    MAX-ACCESS  read-write
    STATUS      current
    DESCRIPTION
        "The value of tmnxOamVccvPgTgFec128CtlPwType specifies the value to be
         copied into the 'PW Type' (Pseudowire Type) field of the 'FEC 128
         Pseudowire' sub-TLV within the 'Target FEC Stack' TLV within the
         launched VCCV ping request.  The code points are defined in RFC 4446.

         SROS supports services corresponding to the following RFC 4446 PW Type
         code points.

         PW Type    Description
         -------    ---------------------------------------
          2         ATM AAL5 SDU VCC transport
          3         ATM transparent cell transport
          5         Ethernet
          9         ATM n-to-one VCC cell transport
         10         ATM n-to-one VPC cell transport
         17         Structure-agnostic E1 over packet
         18         Structure-agnostic T1 (DS1) over packet
         21         CES over PSN basic mode
         23         CES over PSN TDM with CAS

         Zero indicates no Pseudowire Type has been configured."
    REFERENCE
        "RFC 4379, 'Detecting Multi-Protocol Label Switched (MPLS) Data Plane
         Failures', Section 3.2.9 ('FEC 128 Pseudowire (Current)').
         RFC 4446, 'IANA Allocations for Pseudowire Edge to Edge Emulation
         (PWE3)', Section 3.2, 'MPLS Pseudowire Type'."
    DEFVAL      { 0 }
    ::= { tmnxOamVccvPgTgFec128CtlEntry 6 }

tmnxOamVccvPgTgStaticCtlTable    OBJECT-TYPE
    SYNTAX      SEQUENCE OF TmnxOamVccvPgTgStaticCtlEntry
    MAX-ACCESS  not-accessible
    STATUS      current
    DESCRIPTION
        "tmnxOamVccvPgTgStaticCtlTable contains the target information for VCCV
         (Virtual Circuit Connectivity Verification) ping tests which switch to
         downstream static (i.e. MPLS-TP) segments."
    REFERENCE
        "RFC 6426, 'MPLS On-Demand Connectivity Verification and Route Tracing',
         section 2.3.2, 'Static Pseudowire Sub-TLV'."
    ::= { tmnxOamPingObjs 25 }

tmnxOamVccvPgTgStaticCtlEntry    OBJECT-TYPE
    SYNTAX      TmnxOamVccvPgTgStaticCtlEntry
    MAX-ACCESS  not-accessible
    STATUS      current
    DESCRIPTION
        "tmnxOamVccvPgTgStaticCtlEntry contains the target information for a
         VCCV ping test which switches to a downstream static (i.e. MPLS-TP)
         segment.

         The values in a row are used to fill a 'Static Pseudowire' sub-TLV
         (Type, Length, Value) within the 'Target FEC Stack' TLV within the
         launched VCCV ping request.

         A row is created when the test's tmnxOamVccvPingCtlSwitTgtFecType is
         set to 'static(3)'.

         A row is destroyed when the tmnxOamVccvPingCtlTable row is destroyed.

         All the objects in a row must be set in one SNMP Set PDU.  Otherwise,
         the SNMP Set PDU will be rejected."
    REFERENCE
        "RFC 6426, 'MPLS On-Demand Connectivity Verification and Route Tracing',
         section 2.3.2, 'Static Pseudowire Sub-TLV'."
    INDEX       {
        tmnxOamPingCtlOwnerIndex,
        tmnxOamPingCtlTestIndex
    }
    ::= { tmnxOamVccvPgTgStaticCtlTable 1 }

TmnxOamVccvPgTgStaticCtlEntry    ::= SEQUENCE
{
    tmnxOamVccvPgTgStaticCtlAgi      TmnxVPNRouteDistinguisher,
    tmnxOamVccvPgTgStaticCtlSaiiGlbl TmnxPwGlobalIdOrZero,
    tmnxOamVccvPgTgStaticCtlSaiiNode TmnxMplsTpNodeID,
    tmnxOamVccvPgTgStaticCtlSaiiAcId Unsigned32,
    tmnxOamVccvPgTgStaticCtlTaiiGlbl TmnxPwGlobalIdOrZero,
    tmnxOamVccvPgTgStaticCtlTaiiNode TmnxMplsTpNodeID,
    tmnxOamVccvPgTgStaticCtlTaiiAcId Unsigned32
}

tmnxOamVccvPgTgStaticCtlAgi      OBJECT-TYPE
    SYNTAX      TmnxVPNRouteDistinguisher
    MAX-ACCESS  read-write
    STATUS      current
    DESCRIPTION
        "The value of tmnxOamVccvPgTgStaticCtlAgi specifies the value to be
         copied into the 'Service Identifier' field of the 'Static Pseudowire'
         sub-TLV within the 'Target FEC Stack' TLV within the launched VCCV ping
         request.  As specified in RFC 6426, the 'Service Identifier' field may
         be filled with an AGI (Attachment Group Identifier).

         The all-zeroes value indicates no Service Identifier has been
         configured."
    REFERENCE
        "RFC 6426, 'MPLS On-Demand Connectivity Verification and Route Tracing',
         section 2.3.2, 'Static Pseudowire Sub-TLV'.
         RFC 4446, 'IANA Allocations for Pseudowire Edge to Edge Emulation
         (PWE3)', section 3.4.2, 'Attachment Group Identifier (AGI) Type'."
    DEFVAL      { '0000000000000000'H }
    ::= { tmnxOamVccvPgTgStaticCtlEntry 1 }

tmnxOamVccvPgTgStaticCtlSaiiGlbl OBJECT-TYPE
    SYNTAX      TmnxPwGlobalIdOrZero
    MAX-ACCESS  read-write
    STATUS      current
    DESCRIPTION
        "The value of tmnxOamVccvPgTgStaticCtlSaiiGlbl specifies the value to
         be copied into the 'Source Global ID' field of the 'Static Pseudowire'
         sub-TLV within the 'Target FEC Stack' TLV within the launched VCCV
         ping request.

         Zero indicates no Source Global ID has been configured."
    REFERENCE
        "RFC 6426, 'MPLS On-Demand Connectivity Verification and Route Tracing',
         section 2.3.2, 'Static Pseudowire Sub-TLV'.
         RFC 6370, 'MPLS Transport Profile (MPLS-TP) Identifiers', section 3,
         'Uniquely Identifying an Operator - the Global_ID'."
    DEFVAL      { 0 }
    ::= { tmnxOamVccvPgTgStaticCtlEntry 2 }

tmnxOamVccvPgTgStaticCtlSaiiNode OBJECT-TYPE
    SYNTAX      TmnxMplsTpNodeID
    MAX-ACCESS  read-write
    STATUS      current
    DESCRIPTION
        "The value of tmnxOamVccvPgTgStaticCtlSaiiNode specifies the value to
         be copied into the 'Source Node ID' field of the 'Static Pseudowire'
         sub-TLV within the 'Target FEC Stack' TLV within the launched VCCV
         ping request.

         Zero indicates no Source Node ID has been configured."
    REFERENCE
        "RFC 6426, 'MPLS On-Demand Connectivity Verification and Route Tracing',
         section 2.3.2, 'Static Pseudowire Sub-TLV'.
         RFC 6370, 'MPLS Transport Profile (MPLS-TP) Identifiers', section 4,
         'Node and Interface Identifiers'."
    DEFVAL      { 0 }
    ::= { tmnxOamVccvPgTgStaticCtlEntry 3 }

tmnxOamVccvPgTgStaticCtlSaiiAcId OBJECT-TYPE
    SYNTAX      Unsigned32
    MAX-ACCESS  read-write
    STATUS      current
    DESCRIPTION
        "The value of tmnxOamVccvPgTgStaticCtlSaiiAcId specifies the value to
         be copied into the 'Source AC-ID' (Source Attachment Circuit
         Identifier) field of the 'Static Pseudowire' sub-TLV within the
         'Target FEC Stack' TLV within the launched VCCV ping request.

         Zero indicates no Source AC-ID has been configured."
    REFERENCE
        "RFC 6426, 'MPLS On-Demand Connectivity Verification and Route Tracing',
         section 2.3.2, 'Static Pseudowire Sub-TLV'.
         RFC 5003, 'Attachment Individual Identifier (AII) Types for
         Aggregation', section 3.2, 'AII Type 2'."
    DEFVAL      { 0 }
    ::= { tmnxOamVccvPgTgStaticCtlEntry 4 }

tmnxOamVccvPgTgStaticCtlTaiiGlbl OBJECT-TYPE
    SYNTAX      TmnxPwGlobalIdOrZero
    MAX-ACCESS  read-write
    STATUS      current
    DESCRIPTION
        "The value of tmnxOamVccvPgTgStaticCtlTaiiGlbl specifies the value to
         be copied into the 'Destination Global ID' field of the 'Static
         Pseudowire' sub-TLV within the 'Target FEC Stack' TLV within the
         launched VCCV ping request.

         Zero indicates no Destination Global ID has been configured."
    REFERENCE
        "RFC 6426, 'MPLS On-Demand Connectivity Verification and Route Tracing',
         section 2.3.2, 'Static Pseudowire Sub-TLV'.
         RFC 6370, 'MPLS Transport Profile (MPLS-TP) Identifiers', section 3,
         'Uniquely Identifying an Operator - the Global_ID'."
    DEFVAL      { 0 }
    ::= { tmnxOamVccvPgTgStaticCtlEntry 5 }

tmnxOamVccvPgTgStaticCtlTaiiNode OBJECT-TYPE
    SYNTAX      TmnxMplsTpNodeID
    MAX-ACCESS  read-write
    STATUS      current
    DESCRIPTION
        "The value of tmnxOamVccvPgTgStaticCtlTaiiNode specifies the value to
         be copied into the 'Destination Node ID' field of the 'Static
         Pseudowire' sub-TLV within the 'Target FEC Stack' TLV within the
         launched VCCV ping request.

         Zero indicates no Destination Node ID has been configured."
    REFERENCE
        "RFC 6426, 'MPLS On-Demand Connectivity Verification and Route Tracing',
         section 2.3.2, 'Static Pseudowire Sub-TLV'.
         RFC 6370, 'MPLS Transport Profile (MPLS-TP) Identifiers', section 4,
         'Node and Interface Identifiers'."
    DEFVAL      { 0 }
    ::= { tmnxOamVccvPgTgStaticCtlEntry 6 }

tmnxOamVccvPgTgStaticCtlTaiiAcId OBJECT-TYPE
    SYNTAX      Unsigned32
    MAX-ACCESS  read-write
    STATUS      current
    DESCRIPTION
        "The value of tmnxOamVccvPgTgStaticCtlTaiiAcId specifies the value to
         be copied into the 'Destination AC-ID' (Destination Attachment Circuit
         Identifier) field of the 'Static Pseudowire' sub-TLV within the
         'Target FEC Stack' TLV within the launched VCCV ping request.

         Zero indicates no Destination AC-ID has been configured."
    REFERENCE
        "RFC 6426, 'MPLS On-Demand Connectivity Verification and Route Tracing',
         section 2.3.2, 'Static Pseudowire Sub-TLV'.
         RFC 5003, 'Attachment Individual Identifier (AII) Types for
         Aggregation', section 3.2, 'AII Type 2'."
    DEFVAL      { 0 }
    ::= { tmnxOamVccvPgTgStaticCtlEntry 7 }

tmnxOamVxlanPingCtlTable         OBJECT-TYPE
    SYNTAX      SEQUENCE OF TmnxOamVxlanPingCtlEntry
    MAX-ACCESS  not-accessible
    STATUS      current
    DESCRIPTION
        "tmnxOamVxlanPingCtlTable (along with tmnxOamPingCtlTable) contains the
         configuration information for VXLAN (Virtual Extensible Local Area
         Network) ping tests."
    REFERENCE
        "IETF draft-jain-nvo3-overlay-oam-02, 'Generic Overlay OAM and Datapath
         Failure Detection', October 22, 2014.
         RFC 7348, 'VXLAN: A Framework for Overlaying Virtualized Layer 2
         Networks over Layer 3 Networks', August 2014."
    ::= { tmnxOamPingObjs 26 }

tmnxOamVxlanPingCtlEntry         OBJECT-TYPE
    SYNTAX      TmnxOamVxlanPingCtlEntry
    MAX-ACCESS  not-accessible
    STATUS      current
    DESCRIPTION
        "tmnxOamVxlanPingCtlEntry (along with tmnxOamPingCtlEntry) contains the
         configuration information for a VXLAN ping test.

         A row is created when the corresponding tmnxOamPingCtlTestMode is set
         to 'vxlanPing'.

         A row is destroyed when the corresponding tmnxOamPingCtlTable row is
         destroyed (using tmnxOamPingCtlRowStatus).

         The values in a particular row in this table cannot be changed when
         the corresponding tmnxOamPingCtlAdminStatus is 'enabled(1)'."
    REFERENCE
        "IETF draft-jain-nvo3-overlay-oam-02, 'Generic Overlay OAM and Datapath
         Failure Detection', October 22, 2014.
         RFC 7348, 'VXLAN: A Framework for Overlaying Virtualized Layer 2
         Networks over Layer 3 Networks', August 2014."
    INDEX       {
        tmnxOamPingCtlOwnerIndex,
        tmnxOamPingCtlTestIndex
    }
    ::= { tmnxOamVxlanPingCtlTable 1 }

TmnxOamVxlanPingCtlEntry         ::= SEQUENCE
{
    tmnxOamVxlanPingCtlNetworkId     Unsigned32,
    tmnxOamVxlanPingCtlReplyMode     INTEGER,
    tmnxOamVxlanPingCtlIFlag         Unsigned32,
    tmnxOamVxlanPingCtlTestId        Unsigned32,
    tmnxOamVxlanPingCtlOutSrcUdpPt   Unsigned32,
    tmnxOamVxlanPingCtlOutIpTtl      Unsigned32,
    tmnxOamVxlanPingCtlInL2DestMac   MacAddress,
    tmnxOamVxlanPingCtlInIpSrcAddrT  InetAddressType,
    tmnxOamVxlanPingCtlInIpSrcAddr   InetAddress,
    tmnxOamVxlanPingCtlInIpDstAddrT  InetAddressType,
    tmnxOamVxlanPingCtlInIpDstAddr   InetAddress,
    tmnxOamVxlanPingCtlEndSysMacAddr MacAddress,
    tmnxOamVxlanPingCtlReflectPad    TruthValue
}

tmnxOamVxlanPingCtlNetworkId     OBJECT-TYPE
    SYNTAX      Unsigned32 (0 | 1..16777215)
    MAX-ACCESS  read-write
    STATUS      current
    DESCRIPTION
        "The value of tmnxOamVxlanPingCtlNetworkId specifies the VXLAN Network
         Identifier (VNI) of the VXLAN network to be tested.  The value is
         copied into the VXLAN Network Identifier field of the VXLAN Header of
         the launched OAM echo request.

         Zero indicates no VXLAN Network Identifier has been configured.  The
         test will fail if tmnxOamVxlanPingCtlNetworkId is zero."
    REFERENCE
        "RFC 7348, 'VXLAN: A Framework for Overlaying Virtualized Layer 2
         Networks over Layer 3 Networks', August 2014, Section 5, 'VXLAN Frame
         Format'."
    DEFVAL      { 0 }
    ::= { tmnxOamVxlanPingCtlEntry 1 }

tmnxOamVxlanPingCtlReplyMode     OBJECT-TYPE
    SYNTAX      INTEGER {
        udp     (2),
        overlay (3)
    }
    MAX-ACCESS  read-write
    STATUS      current
    DESCRIPTION
        "The value of tmnxOamVxlanPingCtlReplyMode specifies the encapsulation
         to be used in the OAM echo reply.  The value is copied into the Reply
         Mode field of the Generic Overlay OAM structure of the launched OAM
         echo request.  The replying node uses the value to choose the
         encapsulation of the OAM echo reply.

         Code points:
             udp(2)     - reply using an IPv4 UDP packet
             overlay(3) - reply via the overlay segment.

         The Jain draft's 'Do Not Reply' option (i.e. the Reply Mode with code
         point 1) is not supported."
    REFERENCE
        "IETF draft-jain-nvo3-overlay-oam-02, 'Generic Overlay OAM and Datapath
         Failure Detection', October 22, 2014, Section 5.3, 'Generic Overlay
         OAM Packet Format'."
    DEFVAL      { udp }
    ::= { tmnxOamVxlanPingCtlEntry 2 }

tmnxOamVxlanPingCtlIFlag         OBJECT-TYPE
    SYNTAX      Unsigned32 (0 | 1)
    MAX-ACCESS  read-write
    STATUS      current
    DESCRIPTION
        "The value of tmnxOamVxlanPingCtlIFlag specifies the I flag value to be
         used for the test.  The value is copied into the I flag field of the
         VXLAN Header of the launched OAM echo request."
    REFERENCE
        "RFC 7348, 'VXLAN: A Framework for Overlaying Virtualized Layer 2
         Networks over Layer 3 Networks', August 2014, Section 5, 'VXLAN Frame
         Format'."
    DEFVAL      { 0 }
    ::= { tmnxOamVxlanPingCtlEntry 3 }

tmnxOamVxlanPingCtlTestId        OBJECT-TYPE
    SYNTAX      Unsigned32 (0..2147483647)
    MAX-ACCESS  read-write
    STATUS      current
    DESCRIPTION
        "The value of tmnxOamVxlanPingCtlTestId specifies a unique identifier
         for the test.  The value is copied into the Originator Handle field of
         the Generic Overlay OAM structure of the launched OAM echo request.

         Zero indicates no VXLAN Test Identifier has been configured.  The test
         will fail if tmnxOamVxlanPingCtlTestId is zero."
    REFERENCE
        "IETF draft-jain-nvo3-overlay-oam-02, 'Generic Overlay OAM and Datapath
         Failure Detection', October 22, 2014, Section 5.3, 'Generic Overlay
         OAM Packet Format'."
    DEFVAL      { 0 }
    ::= { tmnxOamVxlanPingCtlEntry 4 }

tmnxOamVxlanPingCtlOutSrcUdpPt   OBJECT-TYPE
    SYNTAX      Unsigned32 (0 | 1..65535)
    MAX-ACCESS  read-write
    STATUS      current
    DESCRIPTION
        "The value of tmnxOamVxlanPingCtlOutSrcUdpPt specifies the outer source
         UDP port to be used for the test.

         If tmnxOamVxlanPingCtlOutSrcUdpPt is zero, an SROS-computed UDP port
         number is copied into the Source Port field of the Outer UDP Header of
         the launched OAM echo request.

         If tmnxOamVxlanPingCtlOutSrcUdpPt is non-zero, the given value is
         copied into the Source Port field of the Outer UDP Header of the
         launched OAM echo request."
    REFERENCE
        "RFC 7348, 'VXLAN: A Framework for Overlaying Virtualized Layer 2
         Networks over Layer 3 Networks', August 2014, Section 5, 'VXLAN Frame
         Format'."
    DEFVAL      { 0 }
    ::= { tmnxOamVxlanPingCtlEntry 5 }

tmnxOamVxlanPingCtlOutIpTtl      OBJECT-TYPE
    SYNTAX      Unsigned32 (1..255)
    MAX-ACCESS  read-write
    STATUS      current
    DESCRIPTION
        "The value of tmnxOamVxlanPingCtlOutIpTtl specifies the outer IP Time To
         Live value to be used for the test.  The value is copied into the Time
         To Live field of the Outer IPv4 Header of the launched OAM echo
         request."
    REFERENCE
        "RFC 7348, 'VXLAN: A Framework for Overlaying Virtualized Layer 2
         Networks over Layer 3 Networks', August 2014, Section 5, 'VXLAN Frame
         Format'."
    DEFVAL      { 255 }
    ::= { tmnxOamVxlanPingCtlEntry 6 }

tmnxOamVxlanPingCtlInL2DestMac   OBJECT-TYPE
    SYNTAX      MacAddress
    MAX-ACCESS  read-write
    STATUS      current
    DESCRIPTION
        "The value of tmnxOamVxlanPingCtlInL2DestMac specifies the inner
         Destination MAC address to be used for the test.  The value is copied
         into the Inner Destination MAC Address field of the Inner Ethernet
         Header of the launched OAM echo request."
    REFERENCE
        "RFC 7348, 'VXLAN: A Framework for Overlaying Virtualized Layer 2
         Networks over Layer 3 Networks', August 2014, Section 5, 'VXLAN Frame
         Format'."
    DEFVAL      { '000000000000'H }
    ::= { tmnxOamVxlanPingCtlEntry 7 }

tmnxOamVxlanPingCtlInIpSrcAddrT  OBJECT-TYPE
    SYNTAX      InetAddressType
    MAX-ACCESS  read-write
    STATUS      current
    DESCRIPTION
        "The value of tmnxOamVxlanPingCtlInIpSrcAddrT specifies the type of
         address in tmnxOamVxlanPingCtlInIpSrcAddr."
    DEFVAL      { ipv4 }
    ::= { tmnxOamVxlanPingCtlEntry 8 }

tmnxOamVxlanPingCtlInIpSrcAddr   OBJECT-TYPE
    SYNTAX      InetAddress (SIZE (0|4|16))
    MAX-ACCESS  read-write
    STATUS      current
    DESCRIPTION
        "The value of tmnxOamVxlanPingCtlInIpSrcAddr specifies the inner source
         IP address to be used for the test.  The value is copied into the
         Source IP Address field of the Inner IP Header of the launched OAM Echo
         request.

         If this object has its default value when the test is started, SROS
         selects a value to be used as the inner source IP address."
    REFERENCE
        "IETF draft-jain-nvo3-overlay-oam-02, 'Generic Overlay OAM and Datapath
         Failure Detection', October 22, 2014, Section 7.1, 'Encoding of Inner
         Header for Echo Request in Layer 2 Context'."
    DEFVAL      { '00000000'H }
    ::= { tmnxOamVxlanPingCtlEntry 9 }

tmnxOamVxlanPingCtlInIpDstAddrT  OBJECT-TYPE
    SYNTAX      InetAddressType
    MAX-ACCESS  read-write
    STATUS      current
    DESCRIPTION
        "The value of tmnxOamVxlanPingCtlInIpDstAddrT specifies the type of
         address in tmnxOamVxlanPingCtlInIpDstAddr."
    DEFVAL      { ipv4 }
    ::= { tmnxOamVxlanPingCtlEntry 10 }

tmnxOamVxlanPingCtlInIpDstAddr   OBJECT-TYPE
    SYNTAX      InetAddress (SIZE (0|4|16))
    MAX-ACCESS  read-write
    STATUS      current
    DESCRIPTION
        "The value of tmnxOamVxlanPingCtlInIpDstAddr specifies the inner
         destination IP address to be used for the test.  The value is copied
         into the Destination IP Address field of the Inner IP Header of the
         launched OAM Echo request.

         Addresses in the address block 127.0.0.0/8 are accepted.  The default
         address is 127.0.0.1."
    REFERENCE
        "IETF draft-jain-nvo3-overlay-oam-02, 'Generic Overlay OAM and Datapath
         Failure Detection', October 22, 2014, Section 7.1, 'Encoding of Inner
         Header for Echo Request in Layer 2 Context'."
    DEFVAL      { '7f000001'H }
    ::= { tmnxOamVxlanPingCtlEntry 11 }

tmnxOamVxlanPingCtlEndSysMacAddr OBJECT-TYPE
    SYNTAX      MacAddress
    MAX-ACCESS  read-write
    STATUS      current
    DESCRIPTION
        "The value of tmnxOamVxlanPingCtlEndSysMacAddr specifies the end system
         MAC address to be verified by the test.  The value is copied into the
         MAC Address #1 field of the End-System MAC Sub-TLV of the launched OAM
         Echo request."
    REFERENCE
        "IETF draft-jain-nvo3-overlay-oam-02, 'Generic Overlay OAM and Datapath
         Failure Detection', October 22, 2014, Section 9.1.1, 'Sub-TLV for
         Validating End-System MAC Address'."
    DEFVAL      { '000000000000'H }
    ::= { tmnxOamVxlanPingCtlEntry 12 }

tmnxOamVxlanPingCtlReflectPad    OBJECT-TYPE
    SYNTAX      TruthValue
    MAX-ACCESS  read-write
    STATUS      current
    DESCRIPTION
        "The value of tmnxOamVxlanPingCtlReflectPad specifies whether or not to
         copy the pad TLV from the OAM echo request to the OAM echo response.

         The combination of tmnxOamVxlanPingCtlReflectPad='true(1)' and
         tmnxOamPingCtlSize=0 is rejected, because tmnxOamPingCtlSize=0
         indicates there is no pad TLV to be copied.

         The combination of tmnxOamVxlanPingCtlReflectPad='true(1)' and
         tmnxOamVxlanPingCtlReplyMode='udp(2)' is rejected."
    DEFVAL      { false }
    ::= { tmnxOamVxlanPingCtlEntry 13 }

tmnxOamVxlanPingHistoryTable     OBJECT-TYPE
    SYNTAX      SEQUENCE OF TmnxOamVxlanPingHistoryEntry
    MAX-ACCESS  not-accessible
    STATUS      current
    DESCRIPTION
        "tmnxOamVxlanPingHistoryTable (along with tmnxOamPingHistoryTable)
         contains the information obtained from Virtual Extensible Local Area
         Network (VXLAN) Echo Reply PDUs."
    REFERENCE
        "IETF draft-jain-nvo3-overlay-oam-02, 'Generic Overlay OAM and Datapath
         Failure Detection', October 22, 2014.
         RFC 7348, 'VXLAN: A Framework for Overlaying Virtualized Layer 2
         Networks over Layer 3 Networks', August 2014."
    ::= { tmnxOamPingObjs 27 }

tmnxOamVxlanPingHistoryEntry     OBJECT-TYPE
    SYNTAX      TmnxOamVxlanPingHistoryEntry
    MAX-ACCESS  not-accessible
    STATUS      current
    DESCRIPTION
        "tmnxOamVxlanPingHistoryEntry (along with tmnxOamPingHistoryEntry)
         contains the information obtained from one VXLAN Echo Reply PDU.

         A row is created when a VXLAN Echo Reply PDU (associated with a
         managed 'vxlanPing' test) arrives.

         A row is destroyed when the corresponding tmnxOamPingHistoryEntry is
         destroyed.

         The first two indices specify a 'vxlanPing' test.  The third index
         specifies a test run (started using tmnxOamPingCtlAdminStatus).  The
         fourth index specifies a VXLAN Echo Reply PDU."
    REFERENCE
        "IETF draft-jain-nvo3-overlay-oam-02, 'Generic Overlay OAM and Datapath
         Failure Detection', October 22, 2014, Section 7.3.4, 'Receiving VXLAN
         Echo Reply'."
    INDEX       {
        tmnxOamPingCtlOwnerIndex,
        tmnxOamPingCtlTestIndex,
        tmnxOamPingResultsTestRunIndex,
        tmnxOamPingHistoryIndex
    }
    ::= { tmnxOamVxlanPingHistoryTable 1 }

TmnxOamVxlanPingHistoryEntry     ::= SEQUENCE
{
    tmnxOamVxlanPingHistReturnCode   Unsigned32,
    tmnxOamVxlanPingHistRtrnSubCode  Unsigned32,
    tmnxOamVxlanPingHistValidationRC Unsigned32,
    tmnxOamVxlanPingHistNetworkId    Unsigned32,
    tmnxOamVxlanPingHistOutIpTtl     Unsigned32
}

tmnxOamVxlanPingHistReturnCode   OBJECT-TYPE
    SYNTAX      Unsigned32 (0..255)
    MAX-ACCESS  read-only
    STATUS      current
    DESCRIPTION
        "The value of tmnxOamVxlanPingHistReturnCode indicates the value copied
         from the Return Code field of the Generic Overlay OAM Packet structure
         of the VXLAN Echo Reply PDU.

         Code points include (but are not restricted to) the following.

         Value    Interpretation
         -----    -------------------------------
         0        no return code
         1        malformed echo request received
         2        overlay segment not present
         3        overlay segment not operational
         4        OK"
    REFERENCE
        "IETF draft-jain-nvo3-overlay-oam-02, 'Generic Overlay OAM and Datapath
         Failure Detection', October 22, 2014, Section 5.3, 'Generic Overlay
         OAM Packet Format'."
    ::= { tmnxOamVxlanPingHistoryEntry 1 }

tmnxOamVxlanPingHistRtrnSubCode  OBJECT-TYPE
    SYNTAX      Unsigned32 (0..255)
    MAX-ACCESS  read-only
    STATUS      current
    DESCRIPTION
        "The value of tmnxOamVxlanPingHistRtrnSubCode indicates the value
         copied from the Return Subcode field of the Generic Overlay OAM Packet
         structure of the VXLAN Echo Reply PDU."
    REFERENCE
        "IETF draft-jain-nvo3-overlay-oam-02, 'Generic Overlay OAM and Datapath
         Failure Detection', October 22, 2014, Section 5.3, 'Generic Overlay
         OAM Packet Format'."
    ::= { tmnxOamVxlanPingHistoryEntry 2 }

tmnxOamVxlanPingHistValidationRC OBJECT-TYPE
    SYNTAX      Unsigned32 (0..65535)
    MAX-ACCESS  read-only
    STATUS      current
    DESCRIPTION
        "The value of tmnxOamVxlanPingHistValidationRC indicates the value
         copied from the 'Return Code #1' field of the 'Sub-TLV for Validating
         End-System MAC Address' of the VXLAN Echo Reply PDU."
    REFERENCE
        "IETF draft-jain-nvo3-overlay-oam-02, 'Generic Overlay OAM and Datapath
         Failure Detection', October 22, 2014, Section 9.1.1, 'Sub-TLV for
         Validating End-System MAC Address'."
    ::= { tmnxOamVxlanPingHistoryEntry 3 }

tmnxOamVxlanPingHistNetworkId    OBJECT-TYPE
    SYNTAX      Unsigned32 (0..16777215)
    MAX-ACCESS  read-only
    STATUS      current
    DESCRIPTION
        "The value of tmnxOamVxlanPingHistNetworkId indicates the value of the
         VXLAN Network Identifier (VNI) field of the VXLAN Header of the VXLAN
         Echo Reply PDU."
    REFERENCE
        "RFC 7348, 'VXLAN: A Framework for Overlaying Virtualized Layer 2
         Networks over Layer 3 Networks', August 2014, Section 5, 'VXLAN Frame
         Format'."
    ::= { tmnxOamVxlanPingHistoryEntry 4 }

tmnxOamVxlanPingHistOutIpTtl     OBJECT-TYPE
    SYNTAX      Unsigned32 (0..255)
    MAX-ACCESS  read-only
    STATUS      current
    DESCRIPTION
        "The value of tmnxOamVxlanPingHistOutIpTtl indicates the value of the
         Time To Live field of the Outer IPv4 Header of the VXLAN Echo Reply
         PDU."
    REFERENCE
        "RFC 7348, 'VXLAN: A Framework for Overlaying Virtualized Layer 2
         Networks over Layer 3 Networks', August 2014, Section 5, 'VXLAN Frame
         Format'."
    ::= { tmnxOamVxlanPingHistoryEntry 5 }

tmnxOamBfdOnLspPingResultsTable  OBJECT-TYPE
    SYNTAX      SEQUENCE OF TmnxOamBfdOnLspPingResultsEntry
    MAX-ACCESS  not-accessible
    STATUS      current
    DESCRIPTION
        "tmnxOamBfdOnLspPingResultsTable contains the information obtained
         during the RFC 5884 procedures used to bootstrap and periodically
         verify Bidirectional Forwarding Detection (BFD) sessions on Label
         Switched Paths (LSPs).  The bootstrap and verification procedures use
         LSP ping echo request and reply packets."
    REFERENCE
        "RFC 5884, 'Bidirectional Forwarding Detection (BFD) for MPLS Label
         Switched Paths (LSPs)', Section 3.2, 'Using BFD in Conjunction with LSP
         Ping'."
    ::= { tmnxOamPingObjs 28 }

tmnxOamBfdOnLspPingResultsEntry  OBJECT-TYPE
    SYNTAX      TmnxOamBfdOnLspPingResultsEntry
    MAX-ACCESS  not-accessible
    STATUS      current
    DESCRIPTION
        "tmnxOamBfdOnLspPingResultsEntry contains the information obtained
         during the RFC 5884 procedures used to bootstrap and periodically
         verify a BFD session on an LSP.

         A row is created when an RFC 5884 BFD-on-LSP session starts its
         bootstrap procedure.  A row is destroyed when the BFD-on-LSP session
         disconnects."
    REFERENCE
        "RFC 5884, 'Bidirectional Forwarding Detection (BFD) for MPLS Label
         Switched Paths (LSPs)', Section 3.2, 'Using BFD in Conjunction with LSP
         Ping'."
    INDEX       { tmnxOamBfdOnLspLocalBfdDiscrim }
    ::= { tmnxOamBfdOnLspPingResultsTable 1 }

TmnxOamBfdOnLspPingResultsEntry  ::= SEQUENCE
{
    tmnxOamBfdOnLspLocalBfdDiscrim   Unsigned32,
    tmnxOamBfdOnLspRemoteBfdDiscrim  Unsigned32,
    tmnxOamBfdOnLspRemoteAddressType InetAddressType,
    tmnxOamBfdOnLspRemoteAddress     InetAddress,
    tmnxOamBfdOnLspLspName           TLNamedItemOrEmpty,
    tmnxOamBfdOnLspPingReturnCode    TmnxOamPingRtnCode,
    tmnxOamBfdOnLspPingReturnSubcode Unsigned32,
    tmnxOamBfdOnLspPingTxCount       Unsigned32,
    tmnxOamBfdOnLspPingRxCount       Unsigned32,
    tmnxOamBfdOnLspPathState         INTEGER,
    tmnxOamBfdOnLspPingTxInterval    Unsigned32,
    tmnxOamBfdOnLspBootStrRetryCount Unsigned32,
    tmnxOamBfdOnLspFecType           TmnxBfdOnLspSessFecType,
    tmnxOamBfdOnLspPrefixType        InetAddressType,
    tmnxOamBfdOnLspPrefix            InetAddress,
    tmnxOamBfdOnLspPrefixLen         InetAddressPrefixLength,
    tmnxOamBfdOnLspSourceAddressType InetAddressType,
    tmnxOamBfdOnLspSourceAddress     InetAddress,
    tmnxOamBfdOnLspOperState         INTEGER
}

tmnxOamBfdOnLspLocalBfdDiscrim   OBJECT-TYPE
    SYNTAX      Unsigned32 (1..4294967295)
    MAX-ACCESS  not-accessible
    STATUS      current
    DESCRIPTION
        "The value of tmnxOamBfdOnLspLocalBfdDiscrim specifies the local BFD
         discriminator for a BFD-on-LSP session.  The local discriminator is
         this system's identifier of the BFD session."
    REFERENCE
        "RFC 5880, 'Bidirectional Forwarding Detection (BFD)', Section 6.3,
         'Demultiplexing and the Discriminator Fields'."
    ::= { tmnxOamBfdOnLspPingResultsEntry 1 }

tmnxOamBfdOnLspRemoteBfdDiscrim  OBJECT-TYPE
    SYNTAX      Unsigned32
    MAX-ACCESS  read-only
    STATUS      current
    DESCRIPTION
        "The value of tmnxOamBfdOnLspRemoteBfdDiscrim indicates the remote BFD
         discriminator for the BFD-on-LSP session identified by
         tmnxOamBfdOnLspLocalBfdDiscrim.  The remote discriminator is the far
         end system's identifier of the BFD session.

         Zero is returned if the bootstrap has not completed successfully."
    REFERENCE
        "RFC 5880, 'Bidirectional Forwarding Detection (BFD)', Section 6.3,
         'Demultiplexing and the Discriminator Fields'."
    ::= { tmnxOamBfdOnLspPingResultsEntry 2 }

tmnxOamBfdOnLspRemoteAddressType OBJECT-TYPE
    SYNTAX      InetAddressType
    MAX-ACCESS  read-only
    STATUS      current
    DESCRIPTION
        "The value of tmnxOamBfdOnLspRemoteAddressType indicates the type of
         address stored in tmnxOamBfdOnLspRemoteAddress."
    ::= { tmnxOamBfdOnLspPingResultsEntry 3 }

tmnxOamBfdOnLspRemoteAddress     OBJECT-TYPE
    SYNTAX      InetAddress (SIZE (0|4|16))
    MAX-ACCESS  read-only
    STATUS      current
    DESCRIPTION
        "The value of tmnxOamBfdOnLspRemoteAddress (in conjunction with
         tmnxOamBfdOnLspRemoteAddressType) indicates the IP address of the node
         which sent the most recent LSP ping echo reply for the BFD-on-LSP
         session identified by tmnxOamBfdOnLspLocalBfdDiscrim.

         If the LSP is operating correctly, the reply is sent by the far end of
         the BFD-on-LSP session."
    ::= { tmnxOamBfdOnLspPingResultsEntry 4 }

tmnxOamBfdOnLspLspName           OBJECT-TYPE
    SYNTAX      TLNamedItemOrEmpty
    MAX-ACCESS  read-only
    STATUS      current
    DESCRIPTION
        "The value of tmnxOamBfdOnLspLspName indicates the LSP name associated
         with the Resource Reservation Protocol (RSVP) BFD-on-LSP session
         identified by tmnxOamBfdOnLspLocalBfdDiscrim.  LSP names are configured
         using TIMETRA-MPLS-MIB::vRtrMplsLspName.

         When the value of tmnxOamBfdOnLspFecType is not 'rsvp(1)', the value
         of this object is the empty string."
    ::= { tmnxOamBfdOnLspPingResultsEntry 5 }

tmnxOamBfdOnLspPingReturnCode    OBJECT-TYPE
    SYNTAX      TmnxOamPingRtnCode
    MAX-ACCESS  read-only
    STATUS      current
    DESCRIPTION
        "The value of tmnxOamBfdOnLspPingReturnCode indicates the status of the
         most recent LSP ping echo reply received for the BFD-on-LSP session
         identified by tmnxOamBfdOnLspLocalBfdDiscrim."
    REFERENCE
        "RFC 4379, 'Detecting Multi-Protocol Label Switched (MPLS) Data Plane
         Failures', Section 3.1, 'Return Codes'."
    ::= { tmnxOamBfdOnLspPingResultsEntry 6 }

tmnxOamBfdOnLspPingReturnSubcode OBJECT-TYPE
    SYNTAX      Unsigned32
    MAX-ACCESS  read-only
    STATUS      current
    DESCRIPTION
        "The value of tmnxOamBfdOnLspPingReturnSubcode indicates the value
         present in the RFC 4379 Return Subcode (RSC) field of the most recent
         LSP ping echo reply for the BFD-on-LSP session identified by
         tmnxOamBfdOnLspLocalBfdDiscrim."
    REFERENCE
        "RFC 4379, 'Detecting Multi-Protocol Label Switched (MPLS) Data Plane
         Failures', Section 3.1, 'Return Codes'."
    ::= { tmnxOamBfdOnLspPingResultsEntry 7 }

tmnxOamBfdOnLspPingTxCount       OBJECT-TYPE
    SYNTAX      Unsigned32
    MAX-ACCESS  read-only
    STATUS      current
    DESCRIPTION
        "The value of tmnxOamBfdOnLspPingTxCount indicates the number of LSP
         ping echo request packets sent for the BFD-on-LSP session identified
         by tmnxOamBfdOnLspLocalBfdDiscrim."
    ::= { tmnxOamBfdOnLspPingResultsEntry 8 }

tmnxOamBfdOnLspPingRxCount       OBJECT-TYPE
    SYNTAX      Unsigned32
    MAX-ACCESS  read-only
    STATUS      current
    DESCRIPTION
        "The value of tmnxOamBfdOnLspPingRxCount indicates the number of LSP
         ping echo reply packets received for the BFD-on-LSP session identified
         by tmnxOamBfdOnLspLocalBfdDiscrim."
    ::= { tmnxOamBfdOnLspPingResultsEntry 9 }

tmnxOamBfdOnLspPathState         OBJECT-TYPE
    SYNTAX      INTEGER {
        unknown  (1),
        active   (2),
        inactive (3)
    }
    MAX-ACCESS  read-only
    STATUS      current
    DESCRIPTION
        "The value of tmnxOamBfdOnLspPathState indicates the state of the path
         hosting the RSVP BFD-on-LSP session identified by
         tmnxOamBfdOnLspLocalBfdDiscrim.

         Code points:
         unknown  (1) - the state of the path hosting the BFD-on-LSP session is
                        unknown
         active   (2) - the BFD-on-LSP session is running on the active path
         inactive (3) - the BFD-on-LSP session is running on the inactive path

         When the value of tmnxOamBfdOnLspFecType is not 'rsvp(1)', the value
         of this object is 'unknown(1)'."
    REFERENCE
        "RFC 4090, 'Fast Reroute Extensions to RSVP-TE for LSP Tunnels', Section
         3.2, 'Facility Backup'."
    ::= { tmnxOamBfdOnLspPingResultsEntry 10 }

tmnxOamBfdOnLspPingTxInterval    OBJECT-TYPE
    SYNTAX      Unsigned32
    UNITS       "seconds"
    MAX-ACCESS  read-only
    STATUS      current
    DESCRIPTION
        "The value of tmnxOamBfdOnLspPingTxInterval indicates the transmission
         interval for LSP ping request PDUs sent during periodic verification
         of the BFD-on-LSP session identified by
         tmnxOamBfdOnLspLocalBfdDiscrim.

         This value is configured using
         TIMETRA-MPLS-MIB::vRtrMplsLspBfdPingIntvl.  A read-only copy of the
         value is available here for the convenience of a manager wishing to
         read the value using a local BFD discriminator as the index."
    REFERENCE
        "RFC 5884, 'Bidirectional Forwarding Detection (BFD) for MPLS Label
         Switched Paths (LSPs)', Section 4, 'Theory of Operation'"
    ::= { tmnxOamBfdOnLspPingResultsEntry 11 }

tmnxOamBfdOnLspBootStrRetryCount OBJECT-TYPE
    SYNTAX      Unsigned32
    MAX-ACCESS  read-only
    STATUS      current
    DESCRIPTION
        "The value of tmnxOamBfdOnLspBootStrRetryCount indicates the current
         number of retries started while attempting to bootstrap the BFD-on-LSP
         session identified by tmnxOamBfdOnLspLocalBfdDiscrim.

         If the bootstrap completed successfully on the first attempt, zero is
         returned."
    ::= { tmnxOamBfdOnLspPingResultsEntry 12 }

tmnxOamBfdOnLspFecType           OBJECT-TYPE
    SYNTAX      TmnxBfdOnLspSessFecType
    MAX-ACCESS  read-only
    STATUS      current
    DESCRIPTION
        "The value of tmnxOamBfdOnLspFecType indicates the Forwarding
         Equivalence Class (FEC) type of the BFD-on-LSP session identified by
         tmnxOamBfdOnLspLocalBfdDiscrim.

         This release supports code points 'rsvp(1)' and 'ldp(2)'."
    ::= { tmnxOamBfdOnLspPingResultsEntry 13 }

tmnxOamBfdOnLspPrefixType        OBJECT-TYPE
    SYNTAX      InetAddressType
    MAX-ACCESS  read-only
    STATUS      current
    DESCRIPTION
        "The value of tmnxOamBfdOnLspPrefixType indicates the type of address
         stored in tmnxOamBfdOnLspPrefix."
    ::= { tmnxOamBfdOnLspPingResultsEntry 14 }

tmnxOamBfdOnLspPrefix            OBJECT-TYPE
    SYNTAX      InetAddress (SIZE (0|4|16))
    MAX-ACCESS  read-only
    STATUS      current
    DESCRIPTION
        "The value of tmnxOamBfdOnLspPrefix indicates (in conjunction with
         tmnxOamBfdOnLspPrefixType and tmnxOamBfdOnLspPrefixLen) the prefix
         which identifies the Label Distribution Protocol (LDP) LSP which hosts
         the BFD-on-LSP session identified by tmnxOamBfdOnLspLocalBfdDiscrim.

         When tmnxOamBfdOnLspFecType is 'rsvp(1)', the three prefix objects
         have the following values.
            tmnxOamBfdOnLspPrefixType : 'unknown(0)'
            tmnxOamBfdOnLspPrefix     : empty
            tmnxOamBfdOnLspPrefixLen  : 0."
    REFERENCE
        "RFC 5036, 'LDP Specification', Section 3.4.1, 'FEC TLV'."
    ::= { tmnxOamBfdOnLspPingResultsEntry 15 }

tmnxOamBfdOnLspPrefixLen         OBJECT-TYPE
    SYNTAX      InetAddressPrefixLength (0..128)
    UNITS       "bits"
    MAX-ACCESS  read-only
    STATUS      current
    DESCRIPTION
        "The value of tmnxOamBfdOnLspPrefixLen indicates the number of
         significant bits in the prefix defined by tmnxOamBfdOnLspPrefixType,
         tmnxOamBfdOnLspPrefix, and tmnxOamBfdOnLspPrefixLen."
    ::= { tmnxOamBfdOnLspPingResultsEntry 16 }

tmnxOamBfdOnLspSourceAddressType OBJECT-TYPE
    SYNTAX      InetAddressType
    MAX-ACCESS  read-only
    STATUS      current
    DESCRIPTION
        "The value of tmnxOamBfdOnLspSourceAddressType indicates the type of
         address stored in tmnxOamBfdOnLspSourceAddress."
    ::= { tmnxOamBfdOnLspPingResultsEntry 17 }

tmnxOamBfdOnLspSourceAddress     OBJECT-TYPE
    SYNTAX      InetAddress (SIZE (0|4|16))
    MAX-ACCESS  read-only
    STATUS      current
    DESCRIPTION
        "The value of tmnxOamBfdOnLspSourceAddress (in conjunction with
         tmnxOamBfdOnLspSourceAddressType) indicates the source IP address of
         the BFD-on-LSP session identified by tmnxOamBfdOnLspLocalBfdDiscrim."
    ::= { tmnxOamBfdOnLspPingResultsEntry 18 }

tmnxOamBfdOnLspOperState         OBJECT-TYPE
    SYNTAX      INTEGER {
        bootstrapInProg                  (1),
        bootstrappedNoPeriodicVerif      (2),
        bootstrappedSendingPeriodicVerif (3)
    }
    MAX-ACCESS  read-only
    STATUS      current
    DESCRIPTION
        "The value of tmnxOamBfdOnLspOperState indicates the operational state
         (with respect to the RFC 5884 LSP Ping procedures) of the BFD-on-LSP
         session identified by tmnxOamBfdOnLspLocalBfdDiscrim.

         Code Points
         'bootstrapInProg(1)' - the session is being bootstrapped using LSP
             ping, as described in RFC 5884 Section 6.
         'bootstrappedNoPeriodicVerif(2)' - the bootstrap completed
             successfully.  This is the success state for a session which has
             periodic verification of the LSP (using LSP ping) disabled.
             Periodic verification is disabled by setting the session's LSP ping
             interval (e.g.
             TIMETRA-LDP-NG-MIB::vRtrLdpNgBfdOnLspPfxListPingIntv) to zero.
         'bootstrappedSendingPeriodicVerif(3)' - the bootstrap completed
             successfully, and the session is sending LSP pings to periodically
             verify the LSP (as described in RFC 5884 Section 3.2).  This is the
             success state for a session which has periodic verification of the
             session enabled.

         The BFD-level operational state of a BFD-on-LSP session is given by
         TIMETRA-BFD-MIB::tmnxBfdOnLspSessOperState."
    REFERENCE
        "RFC 5884, 'Bidirectional Forwarding Detection (BFD) for MPLS Label
         Switched Paths (LSPs)', Section 3.2, 'Using BFD in Conjunction with LSP
         Ping'.
         RFC 5884, 'Bidirectional Forwarding Detection (BFD) for MPLS Label
         Switched Paths (LSPs)', Section 6, 'Session Establishment'."
    ::= { tmnxOamBfdOnLspPingResultsEntry 19 }

tmnxOamVxlanPingResultsTable     OBJECT-TYPE
    SYNTAX      SEQUENCE OF TmnxOamVxlanPingResultsEntry
    MAX-ACCESS  not-accessible
    STATUS      current
    DESCRIPTION
        "tmnxOamVxlanPingResultsTable contains results of VXLAN (Virtual
         Extensible Local Area Network) ping tests."
    REFERENCE
        "IETF draft-jain-nvo3-overlay-oam-02, 'Generic Overlay OAM and Datapath
         Failure Detection', October 22, 2014.
         RFC 7348, 'VXLAN: A Framework for Overlaying Virtualized Layer 2
         Networks over Layer 3 Networks', August 2014."
    ::= { tmnxOamPingObjs 29 }

tmnxOamVxlanPingResultsEntry     OBJECT-TYPE
    SYNTAX      TmnxOamVxlanPingResultsEntry
    MAX-ACCESS  not-accessible
    STATUS      current
    DESCRIPTION
        "tmnxOamVxlanPingResultsEntry contains results of one 'vxlanPing'
         test run.  tmnxOamPingResultsEntry contains additional results for the
         test run.

         A tmnxOamVxlanPingResultsEntry is created/destroyed when a
         tmnxOamPingResultsEntry is created/destroyed for a 'vxlanPing' test.

         tmnxOamPingCtlEntry and tmnxOamVxlanPingCtlEntry are used to configure
         and start a 'vxlanPing' test.

         tmnxOamVxlanPingHistoryEntry contains per-probe results for a
         'vxlanPing' test run."
    INDEX       {
        tmnxOamPingCtlOwnerIndex,
        tmnxOamPingCtlTestIndex,
        tmnxOamPingResultsTestRunIndex
    }
    ::= { tmnxOamVxlanPingResultsTable 1 }

TmnxOamVxlanPingResultsEntry     ::= SEQUENCE
{
    tmnxOamVxlanPingResOutSrcAddrTyp InetAddressType,
    tmnxOamVxlanPingResOutSrcAddress InetAddress
}

tmnxOamVxlanPingResOutSrcAddrTyp OBJECT-TYPE
    SYNTAX      InetAddressType
    MAX-ACCESS  read-only
    STATUS      current
    DESCRIPTION
        "The value of tmnxOamVxlanPingResOutSrcAddrTyp indicates the address
         type of tmnxOamVxlanPingResOutSrcAddress."
    ::= { tmnxOamVxlanPingResultsEntry 1 }

tmnxOamVxlanPingResOutSrcAddress OBJECT-TYPE
    SYNTAX      InetAddress (SIZE (4|16))
    MAX-ACCESS  read-only
    STATUS      current
    DESCRIPTION
        "The value of tmnxOamVxlanPingResOutSrcAddress indicates the outer
         source IP address (as selected by SROS) used for the specified
         'vxlanPing' test run.  The value was copied into the Outer Source IPv4
         Address field of the VXLAN Header of each OAM echo request launched for
         the specified test run.

         IPv6 may be supported in a future release."
    REFERENCE
        "RFC 7348, 'VXLAN: A Framework for Overlaying Virtualized Layer 2
         Networks over Layer 3 Networks', August 2014, Section 5, 'VXLAN Frame
         Format'."
    ::= { tmnxOamVxlanPingResultsEntry 2 }

tmnxOamPingReadOnlyScalars       OBJECT IDENTIFIER ::= { tmnxOamPingObjs 30 }

tmnxOamBfdOnLspSessBootstrInProg OBJECT-TYPE
    SYNTAX      Gauge32
    UNITS       "sessions"
    MAX-ACCESS  read-only
    STATUS      current
    DESCRIPTION
        "The value of tmnxOamBfdOnLspSessBootstrInProg indicates the current
         number of BFD-on-LSP sessions with OAM operational state (i.e.
         tmnxOamBfdOnLspOperState) 'bootstrapInProg(1)'."
    ::= { tmnxOamPingReadOnlyScalars 1 }

tmnxOamBfdOnLspSessBootstrNoPV   OBJECT-TYPE
    SYNTAX      Gauge32
    UNITS       "sessions"
    MAX-ACCESS  read-only
    STATUS      current
    DESCRIPTION
        "The value of tmnxOamBfdOnLspSessBootstrNoPV indicates the current
         number of BFD-on-LSP sessions with OAM operational state (i.e.
         tmnxOamBfdOnLspOperState) 'bootstrappedNoPeriodicVerif(2)'."
    ::= { tmnxOamPingReadOnlyScalars 2 }

tmnxOamBfdOnLspSessBootstrSendPV OBJECT-TYPE
    SYNTAX      Gauge32
    UNITS       "sessions"
    MAX-ACCESS  read-only
    STATUS      current
    DESCRIPTION
        "The value of tmnxOamBfdOnLspSessBootstrSendPV indicates the current
         number of BFD-on-LSP sessions with OAM operational state (i.e.
         tmnxOamBfdOnLspOperState) 'bootstrappedSendingPeriodicVerif(3)'."
    ::= { tmnxOamPingReadOnlyScalars 3 }

tmnxOamTraceRouteObjs            OBJECT IDENTIFIER ::= { tmnxOamTestObjs 2 }

tmnxOamTraceRouteNotifyObjects   OBJECT IDENTIFIER ::= { tmnxOamTraceRouteObjs 1 }

tmnxOamTrMaxConcurrentRequests   OBJECT-TYPE
    SYNTAX      Unsigned32
    UNITS       "requests"
    MAX-ACCESS  read-write
    STATUS      current
    DESCRIPTION
        "The maximum number of concurrent active trace route requests
         that are allowed within an agent implementation.  A value
         of 0 for this object implies that there is no limit for
         the number of concurrent active requests in effect."
    DEFVAL      { 0 }
    ::= { tmnxOamTraceRouteObjs 2 }

tmnxOamTrCtlTable                OBJECT-TYPE
    SYNTAX      SEQUENCE OF TmnxOamTrCtlEntry
    MAX-ACCESS  not-accessible
    STATUS      current
    DESCRIPTION
        "Defines the Nokia SROS OAM Trace Route Control Table for
         providing the capability of invoking OAM trace route tests from
         SNMP.  The results of trace route operations can be stored in
         the tmnxOamTrResultsTable, tmnxOamTrProbeHistoryTable, and
         the tmnxOamTrHopsTable."
    ::= { tmnxOamTraceRouteObjs 3 }

tmnxOamTrCtlEntry                OBJECT-TYPE
    SYNTAX      TmnxOamTrCtlEntry
    MAX-ACCESS  not-accessible
    STATUS      current
    DESCRIPTION
        "Defines an entry in the tmnxOamTrCtlTable.  The first
         index element, tmnxOamTrCtlOwnerIndex, is of type
         SnmpAdminString, a textual convention that allows for
         use of the SNMPv3 View-Based Access Control Model
         (RFC 2575 [11], VACM) and allows an management
         application to identify its entries.  The second index,
         tmnxOamTrCtlTestIndex (also an SnmpAdminString),
         enables the same management application to have
         multiple requests outstanding."
    INDEX       {
        tmnxOamTrCtlOwnerIndex,
        tmnxOamTrCtlTestIndex
    }
    ::= { tmnxOamTrCtlTable 1 }

TmnxOamTrCtlEntry                ::= SEQUENCE
{
    tmnxOamTrCtlOwnerIndex           SnmpAdminString,
    tmnxOamTrCtlTestIndex            SnmpAdminString,
    tmnxOamTrCtlRowStatus            RowStatus,
    tmnxOamTrCtlStorageType          StorageType,
    tmnxOamTrCtlDescr                SnmpAdminString,
    tmnxOamTrCtlTestMode             INTEGER,
    tmnxOamTrCtlAdminStatus          INTEGER,
    tmnxOamTrCtlFcName               TFCName,
    tmnxOamTrCtlProfile              TProfile,
    tmnxOamTrCtlTargetIpAddress      IpAddress,
    tmnxOamTrCtlServiceId            TmnxServId,
    tmnxOamTrCtlDataSize             Unsigned32,
    tmnxOamTrCtlTimeOut              Unsigned32,
    tmnxOamTrCtlProbesPerHop         Unsigned32,
    tmnxOamTrCtlMaxTtl               Unsigned32,
    tmnxOamTrCtlInitialTtl           Unsigned32,
    tmnxOamTrCtlDSField              Unsigned32,
    tmnxOamTrCtlMaxFailures          Unsigned32,
    tmnxOamTrCtlInterval             Unsigned32,
    tmnxOamTrCtlMaxRows              Unsigned32,
    tmnxOamTrCtlTrapGeneration       BITS,
    tmnxOamTrCtlCreateHopsEntries    TruthValue,
    tmnxOamTrCtlSAA                  TruthValue,
    tmnxOamTrCtlRuns                 Counter32,
    tmnxOamTrCtlFailures             Counter32,
    tmnxOamTrCtlLastRunResult        TmnxOamTestResult,
    tmnxOamTrCtlLastChanged          TimeStamp,
    tmnxOamTrCtlVRtrID               TmnxVRtrID,
    tmnxOamTrCtlTgtAddrType          InetAddressType,
    tmnxOamTrCtlTgtAddress           InetAddress,
    tmnxOamTrCtlSrcAddrType          InetAddressType,
    tmnxOamTrCtlSrcAddress           InetAddress,
    tmnxOamTrCtlWaitMilliSec         Unsigned32
}

tmnxOamTrCtlOwnerIndex           OBJECT-TYPE
    SYNTAX      SnmpAdminString (SIZE (1..32))
    MAX-ACCESS  not-accessible
    STATUS      current
    DESCRIPTION
        "To facilitate the provisioning of access control by a
         security administrator using the View-Based Access
         Control Model (RFC 2575, VACM) for tables in which
         multiple users may need to independently create or
         modify entries, the initial index is used as an 'owner
         index'.  Such an initial index has a syntax of
         SnmpAdminString, and can thus be trivially mapped to a
         security name or group name as defined in VACM, in
         accordance with a security policy.

         When used in conjunction with such a security policy
         all entries in the table belonging to a particular user
         (or group) will have the same value for this initial
         index.  For a given user's entries in a particular
         table, the object identifiers for the information in
         these entries will have the same subidentifiers (except
         for the 'column' subidentifier) up to the end of the
         encoded owner index. To configure VACM to permit access
         to this portion of the table, one would create
         vacmViewTreeFamilyTable entries with the value of
         vacmViewTreeFamilySubtree including the owner index
         portion, and vacmViewTreeFamilyMask 'wildcarding' the
         column subidentifier.  More elaborate configurations
         are possible."
    ::= { tmnxOamTrCtlEntry 1 }

tmnxOamTrCtlTestIndex            OBJECT-TYPE
    SYNTAX      SnmpAdminString (SIZE (1..32))
    MAX-ACCESS  not-accessible
    STATUS      current
    DESCRIPTION
        "The test name index of a Nokia SROS OAM Trace Route test. This is
         locally unique, within the scope of a tmnxOamTrCtlOwnerIndex."
    ::= { tmnxOamTrCtlEntry 2 }

tmnxOamTrCtlRowStatus            OBJECT-TYPE
    SYNTAX      RowStatus
    MAX-ACCESS  read-create
    STATUS      current
    DESCRIPTION
        "This object allows entries to be created and deleted
         in the tmnxOamTrCtlTable.  Deletion of an entry in
         this table results in all corresponding (same
         tmnxOamTrCtlOwnerIndex and tmnxOamTrCtlTestIndex
         index values) tmnxOamTrResultsTable,
         tmnxOamTrProbeHistoryTable, and tmnxOamTrHopsTable
         entries being deleted.

         The values for configuration objects required for the type of test
         specified in tmnxOamTrCtlTestMode MUST be specified prior to a
         transition to active(1) state being accepted.

         Activation of an Nokia SROS OAM Trace Route operation is controlled
         via tmnxOamTrCtlAdminStatus and not by transitioning of this object's
         value to active(1).

         Transitions in and out of active(1) state are not allowed while an
         entry's tmnxOamTrResultsOperStatus is active(1) with the exception
         that deletion of an entry in this table by setting its RowStatus
         object to destroy(6) will stop an active Nokia SROS OAM Trace Route
         operation.

         The operational state of an Nokia SROS OAM Trace Route operation can
         be determined by examination of the corresponding
         tmnxOamTrResultsOperStatus object."
    REFERENCE
        "See definition of RowStatus in RFC 2579, 'Textual
         Conventions for SMIv2.'"
    ::= { tmnxOamTrCtlEntry 3 }

tmnxOamTrCtlStorageType          OBJECT-TYPE
    SYNTAX      StorageType
    MAX-ACCESS  read-create
    STATUS      obsolete
    DESCRIPTION
        "The storage type for this conceptual row. Conceptual rows having the
         value 'permanent' need not allow write-access to any columnar objects
         in the row.

         This object was marked obsolete in SROS Release 14.0 R1.  There is no
         replacement object."
    DEFVAL      { volatile }
    ::= { tmnxOamTrCtlEntry 4 }

tmnxOamTrCtlDescr                OBJECT-TYPE
    SYNTAX      SnmpAdminString
    MAX-ACCESS  read-create
    STATUS      obsolete
    DESCRIPTION
        "The purpose of this object is to provide a descriptive name of the
         Nokia SROS OAM Trace Route test.

         This object was marked obsolete in SROS Release 14.0 R1.  There is no
         replacement object."
    DEFVAL      { '00'H }
    ::= { tmnxOamTrCtlEntry 5 }

tmnxOamTrCtlTestMode             OBJECT-TYPE
    SYNTAX      INTEGER {
        none            (0),
        macTraceRoute   (1),
        lspTraceRoute   (2),
        vprnTraceRoute  (3),
        mcastTraceRoute (4),
        icmpTraceRoute  (5),
        ldpTreeTrace    (6),
        vccvTraceRoute  (7),
        p2mpLspTrace    (8),
        ethCfmLinkTrace (9)
    }
    MAX-ACCESS  read-create
    STATUS      current
    DESCRIPTION
        "The value of tmnxOamTrCtlTestMode specifies the type of trace route
         test defined by this row.  The configuration parameters unique to a
         specific test type are to be found in a sparsely dependent extension
         table for that test type.

         'ldpTreeTrace', 'mcastTraceRoute', and 'p2mpLspTrace' are supported
         for non-SAA tests only.

         'ethCfmLinkTrace' is supported for SAA tests only.

         This is a required parameter."
    DEFVAL      { none }
    ::= { tmnxOamTrCtlEntry 6 }

tmnxOamTrCtlAdminStatus          OBJECT-TYPE
    SYNTAX      INTEGER {
        enabled  (1),
        disabled (2)
    }
    MAX-ACCESS  read-create
    STATUS      current
    DESCRIPTION
        "Reflects the desired state that a tmnxOamTrCtlEntry
         should be in:
           enabled(1)  - Attempt to activate the test as defined by
                         this tmnxOamTrCtlEntry.
           disabled(2) - Deactivate the test as defined by this
                         tmnxOamTrCtlEntry.

         If tmnxOamTrCtlSAA has the value 'true' and tmnxOamSaaCtlAdminStatus
         has the value 'outOfService', an attempt to set this object to
         'enabled' will fail with an inconsistentValue error.

         Refer to the corresponding tmnxOamTrResultsOperStatus to determine the
         operational state of the test defined by this entry."
    DEFVAL      { disabled }
    ::= { tmnxOamTrCtlEntry 7 }

tmnxOamTrCtlFcName               OBJECT-TYPE
    SYNTAX      TFCName
    MAX-ACCESS  read-create
    STATUS      current
    DESCRIPTION
        "The value of tmnxOamTrCtlFcName specifies the forwarding class to be
         used when launching the probe(s).  The forwarding class name must be
         present in the index column of TIMETRA-QOS-MIB::tFCNameTable.  This
         object is optional.

         As shown in the following table a) this object is applicable to a
         subset of the test types, and b) the default forwarding class depends
         on the test type.

         tmnxOamTrCtlTestMode   Applicable?   Default
         --------------------   -----------   -------
         ethCfmLinkTrace        yes           'nc'
         ldpTreeTrace           yes           'be'
         lspTraceRoute          yes           'be'
         macTraceRoute          yes           'be'
         p2mpLspTrace           yes           'be'
         vccvTraceRoute         yes           'be'
         vprnTraceRoute         yes           'be'
         otherwise              no            N/A

         For 'ethCfmLinkTrace', the forwarding class depends on whether the
         request is configured to egress on a network port or an access port.
         In the network port case, the forwarding class is the forwarding class
         of the pseudowire.  In the access port case, the forwarding class is
         that of the SAP's egress encapsulation policy.

         For 'lspTraceRoute' this is the forwarding class of the LSP tunnel.

         For 'macTraceRoute' this is the forwarding class of the SDP
         encapsulation.

         For 'p2mpLspTrace' this is the forwarding class of the P2MP LSP tree.

         If forwarding classes are mapped by the applicable QoS policy, the
         probe(s) may be launched using a different forwarding class than the
         forwarding class specified by this object."
    DEFVAL      { "be" }
    ::= { tmnxOamTrCtlEntry 8 }

tmnxOamTrCtlProfile              OBJECT-TYPE
    SYNTAX      TProfile
    MAX-ACCESS  read-create
    STATUS      current
    DESCRIPTION
        "The value of tmnxOamTrCtlProfile specifies the profile to be used
         with the forwarding class specified in tmnxOamTrCtlFcName.  This
         object is optional.

         As shown in the following table a) this object is applicable to a
         subset of the test types, and b) the default profile value depends on
         the test type.

         tmnxOamTrCtlTestMode   Applicable?   Default
         --------------------   -----------   -------
         ethCfmLinkTrace        yes           'in(1)'
         ldpTreeTrace           yes           'out(2)'
         lspTraceRoute          yes           'out(2)'
         macTraceRoute          yes           'out(2)'
         p2mpLspTrace           yes           'out(2)'
         vccvTraceRoute         yes           'out(2)'
         vprnTraceRoute         yes           'out(2)'
         otherwise              no            N/A"
    DEFVAL      { out }
    ::= { tmnxOamTrCtlEntry 9 }

tmnxOamTrCtlTargetIpAddress      OBJECT-TYPE
    SYNTAX      IpAddress
    MAX-ACCESS  read-create
    STATUS      obsolete
    DESCRIPTION
        "Specifies the IPv4 address to be used as the destination for
         performing an OAM Trace Route operation.  This parameter is
         not used by 'macTraceRoute' or 'lspTraceRoute' or 'mcastTraceRoute'.
         This parameter is required by 'vprnTraceRoute'.

         This object was obsoleted in release 4.0 and replaced with InetAddress
         objects tmnxOamTrCtlTgtAddrType and tmnxOamTrCtlTgtAddress."
    DEFVAL      { '00000000'H }
    ::= { tmnxOamTrCtlEntry 10 }

tmnxOamTrCtlServiceId            OBJECT-TYPE
    SYNTAX      TmnxServId (0..2147483647)
    MAX-ACCESS  read-create
    STATUS      current
    DESCRIPTION
        "The value of tmnxOamTrCtlServiceId specifies the service ID of the
         service being tested.

         The applicability of tmnxOamTrCtlServiceId varies with the test type,
         as shown in the following table.

         tmnxOamTrCtlTestMode   Applicability    Related Virtual Router Object
         --------------------   -------------    -----------------------------
         'icmpTraceRoute'       optional         tmnxOamTrCtlVRtrID
         'macTraceRoute'        mandatory        none
         'mcastTraceRoute'      optional         tmnxOamMcastTrCtlVRtrID
         'vprnTraceRoute'       mandatory        none
         otherwise              not applicable   none

         When tmnxOamTrCtlServiceId is mandatory, a non-zero value must be
         provided.

         When tmnxOamTrCtlServiceId is optional, it is used to specify a VPRN
         service.  The test must use the VPRN service's virtual router.

         When a related virtual router object is shown, the interaction is
         described in the DESCRIPTION clause of the listed object.

         Service IDs larger than 2147483647 are internal, so they are excluded
         from the range.

         The default value is the null service ID."
    DEFVAL      { 0 }
    ::= { tmnxOamTrCtlEntry 11 }

tmnxOamTrCtlDataSize             OBJECT-TYPE
    SYNTAX      Unsigned32 (1..9198)
    UNITS       "octets"
    MAX-ACCESS  read-create
    STATUS      current
    DESCRIPTION
        "The value of tmnxOamTrCtlDataSize specifies the size of the data
         portion of the Trace Route request, in octets.  The size of the request
         does not include the SDP encapsulation, VC-Label (if applied) or any
         DLC headers or trailers.  This parameter is optional.

         The value of tmnxOamTrCtlDataSize is significant if the test type
         (i.e. tmnxOamTrCtlTestMode) is 'lspTraceRoute', 'macTraceRoute',
         'p2mpLspTrace', 'vccvTraceRoute', or 'vprnTraceRoute'.

         If the request PDU required for the specified test is larger than the
         PDU size indicated by tmnxOamTrCtlDataSize, SROS sends the smallest
         valid PDU larger than the size indicated.  For example, if
         tmnxOamTrCtlDataSize is 1 when a 'vccvTraceRoute' test is started on a
         FEC 128 pseudowire, an 88 octet request PDU is sent.

         When the OAM message is encapsulated in an IP/GRE SDP, the IP 'DF'
         (Don't Fragment) bit is set.  If any segment of the path between the
         sender and receiver cannot handle the message size, the message is
         discarded.  MPLS LSPs are not expected to fragment the message either,
         as the message contained in the LSP is not an IP packet."
    DEFVAL      { 1 }
    ::= { tmnxOamTrCtlEntry 12 }

tmnxOamTrCtlTimeOut              OBJECT-TYPE
    SYNTAX      Unsigned32 (1..60)
    UNITS       "seconds"
    MAX-ACCESS  read-create
    STATUS      current
    DESCRIPTION
        "Specifies the time-out value, in seconds, for an Nokia SROS
         OAM Trace Route request.  This parameter is optional.

         For 'ethCfmLinkTrace', this is the time out for the whole test.

         The minimum, maximum, and default values of this object vary with
         tmnxOamTrCtlTestMode, as follows:
           'icmpTraceRoute' :  N/A N/A N/A
           'ethCfmLinkTrace':    1  10   5
            otherwise       :    1  60   3

         If tmnxOamTrCtlTestMode is 'ethCfmLinkTrace', the value of
         tmnxOamTrCtlTimeOut must be less than or equal to the value of
         tmnxOamTrCtlInterval."
    DEFVAL      { 3 }
    ::= { tmnxOamTrCtlEntry 13 }

tmnxOamTrCtlProbesPerHop         OBJECT-TYPE
    SYNTAX      Unsigned32 (1..10)
    UNITS       "probes"
    MAX-ACCESS  read-create
    STATUS      current
    DESCRIPTION
        "Specifies the number of times to reissue an Nokia SROS OAM Trace Route
         request with the same time-to-live (TTL) value. This parameter is
         optional.

         This parameter is not configurable for 'icmpTraceRoute'; a default
         value of 3 is used."
    DEFVAL      { 1 }
    ::= { tmnxOamTrCtlEntry 14 }

tmnxOamTrCtlMaxTtl               OBJECT-TYPE
    SYNTAX      Unsigned32 (1..255)
    UNITS       "time-to-live value"
    MAX-ACCESS  read-create
    STATUS      current
    DESCRIPTION
        "The value of tmnxOamTrCtlMaxTtl specifies the maximum time-to-live
         value.  This parameter is optional.

         When tmnxOamTrCtlMaxTtl is not explicitly specified, the agent
         defaults the value based on the 'tmnxOamTrCtlTestMode'.

         In the case of 'lspTraceRoute' the default is set to 30. In the case
         of 'icmpTraceRoute' the default is set to 30. In the case of
         'ldpTreeTrace' the default is set to 30. In the case of
         'vccvTraceRoute' the default is set to 8. In the case of
         'p2mplspTrace' the default is set to 30. In the case of
         'ethCfmLinkTrace' the default is set to 64. Otherwise the default is
         set to 4."
    DEFVAL      { 4 }
    ::= { tmnxOamTrCtlEntry 15 }

tmnxOamTrCtlInitialTtl           OBJECT-TYPE
    SYNTAX      Unsigned32 (1..255)
    MAX-ACCESS  read-create
    STATUS      current
    DESCRIPTION
        "The value of tmnxOamTrCtlInitialTtl specifies the initial TTL
         value to use.  This enables bypassing the initial (often well known)
         portion of a path.  This parameter is optional.

         This parameter is not configurable for 'icmpTraceRoute'; the
         default value 1 is used.  This parameter is not used with
         'ethCfmLinkTrace'.  This parameter does not affect the test
         execution for 'vccvTraceRoute', but applications may use the
         value to filter results for that test type."
    DEFVAL      { 1 }
    ::= { tmnxOamTrCtlEntry 16 }

tmnxOamTrCtlDSField              OBJECT-TYPE
    SYNTAX      Unsigned32 (0..255)
    MAX-ACCESS  read-create
    STATUS      current
    DESCRIPTION
        "The value of tmnxOamTrCtlDSField specifies the value to load in the
         Type of Service (TOS) octet or the Traffic Class (TC) octet of the
         launched ICMP echo request(s).  The TOS octet is a field in the IPv4
         packet header.  The TC octet is a field in the IPv6 packet header.

         The value in the TOS or TC octet may influence the route, latency,
         and/or probability of loss for the echo request (and, by inference,
         for the associated data flow).

         This object is supported when tmnxOamTrCtlTestMode is
         'icmpTraceRoute'. Otherwise, it is ignored.

         This object is optional."
    REFERENCE
        "RFC  791, 'Internet Protocol', section 3.1.
         RFC 1812, 'Requirements for IP Version 4 Routers', section 5.3.2.
         RFC 2460, 'Internet Protocol, Version 6 (IPv6) Specification',
         section 7.
         RFC 2474, 'Definition of the Differentiated Services Field (DS Field)
         in the IPv4 and IPv6 Headers'."
    DEFVAL      { 0 }
    ::= { tmnxOamTrCtlEntry 17 }

tmnxOamTrCtlMaxFailures          OBJECT-TYPE
    SYNTAX      Unsigned32 (1..255)
    UNITS       "timeouts"
    MAX-ACCESS  read-create
    STATUS      current
    DESCRIPTION
        "The value of tmnxOamTrCtlMaxFailures specifies the maximum number of
         consecutive timeouts allowed before terminating a trace route test.
         This object is optional.

         As shown in the following table a) this object is applicable to a
         subset of the test types, and b) the default value and upper bound
         depend on the test type.

         tmnxOamTrCtlTestMode   Applicable?   Default   Upper Bound
         --------------------   -----------   -------   -----------
         'icmpTraceRoute'       yes            90        90
         'lspTraceRoute'        yes             5       255
         'p2mpLspTrace'         yes             5        10
         'vccvTraceRoute'       yes             5       255
         otherwise              no            N/A       N/A

         In the 'icmpTraceRoute' case, changing the tmnxOamTrCtlMaxFailures
         value away from the default is not supported."
    DEFVAL      { 5 }
    ::= { tmnxOamTrCtlEntry 18 }

tmnxOamTrCtlInterval             OBJECT-TYPE
    SYNTAX      Unsigned32
    UNITS       "seconds"
    MAX-ACCESS  read-create
    STATUS      current
    DESCRIPTION
        "The value of tmnxOamTrCtlInterval specifies the number of seconds to
         wait before repeating an Nokia SROS OAM Trace Route test as defined by
         the value of the various objects in the corresponding row. This
         parameter is optional.

         The number of hops in a single Nokia SROS OAM Trace Route test
         is determined by the value of the corresponding
         tmnxOamTrCtlProbesPerHop object.  After a single test completes,
         the number of seconds as defined by the value of tmnxOamTrCtlInterval
         MUST elapse before the next Nokia SROS OAM Trace Route test is
         started.

         The applicability, range, and default value of this object vary with
         tmnxOamTrCtlTestMode, as shown in the following table.

           tmnxOamTrCtlTestMode   Min Max Default
           'ethCfmLinkTrace'        1  10       5
           'icmpTraceRoute'        not applicable
           'vccvTraceRoute'         1 255       1
           otherwise                1  10       1"
    DEFVAL      { 1 }
    ::= { tmnxOamTrCtlEntry 19 }

tmnxOamTrCtlMaxRows              OBJECT-TYPE
    SYNTAX      Unsigned32
    UNITS       "rows"
    MAX-ACCESS  read-create
    STATUS      obsolete
    DESCRIPTION
        "The value of tmnxOamTrCtlMaxRows specifies the maximum number of
         entries allowed in the tmnxOamTrProbeHistoryTable.  The oldest entry
         in the tmnxOamTrProbeHistoryTable is removed to allow the addition
         of an new entry once the number of rows in the
         tmnxOamTrProbeHistoryTable reaches this value.

         Old entries are not removed when a new test is started.  Entries are
         added to the tmnxOamTrProbeHistoryTable until tmnxOamTrCtlMaxRows
         is reached before entries begin to be removed.

         A value of 0 for this object disables creation of
         tmnxOamTrProbeHistoryTable entries.

         This object was obsoleted in release 6.0R17."
    DEFVAL      { 300 }
    ::= { tmnxOamTrCtlEntry 20 }

tmnxOamTrCtlTrapGeneration       OBJECT-TYPE
    SYNTAX      BITS {
        pathChange     (0),
        testFailure    (1),
        testCompletion (2)
    }
    MAX-ACCESS  read-create
    STATUS      current
    DESCRIPTION
        "The value of tmnxOamTrCtlTrapGeneration specifies when and if to
         generate a notification for this entry:
         pathChange(0)     - Generate a tmnxOamTrPathChange
             notification when the current path varies from a previously
             determined path.
         testFailure(1)    - Generate a tmnxOamTrTestFailed notification when
             the full path to a target can't be determined.
         testCompletion(2) - Generate a tmnxOamTrTestCompleted notification
             when the test is completed."
    DEFVAL      { {} }
    ::= { tmnxOamTrCtlEntry 21 }

tmnxOamTrCtlCreateHopsEntries    OBJECT-TYPE
    SYNTAX      TruthValue
    MAX-ACCESS  read-create
    STATUS      obsolete
    DESCRIPTION
        "The value of tmnxOamTrCtlCreateHopsEntries specifies whether or not
         the current path for an Nokia SROS OAM Trace Route test is kept in the
         tmnxOamTrHopsTable on a per hop basis.

         tmnxOamTrHopsTable provides a current path topology based on the
         results of the OAM Trace Route tests.  If this feature is not
         supported tmnxOamTrCtlCreateHopsEntries will always be set to false(2)
         and any attempt to change its value to true(1) will be denied."
    DEFVAL      { false }
    ::= { tmnxOamTrCtlEntry 22 }

tmnxOamTrCtlSAA                  OBJECT-TYPE
    SYNTAX      TruthValue
    MAX-ACCESS  read-create
    STATUS      current
    DESCRIPTION
        "The value of tmnxOamTrCtlSAA specifies if this test is an SAA test
         (Service Assurance Agent; 'true'), or an OAM test ('false').  If
         there is a tmnxOamSaaCtlTable row with the specified index values,
         'true' is returned.  Otherwise, 'false' is returned."
    DEFVAL      { false }
    ::= { tmnxOamTrCtlEntry 23 }

tmnxOamTrCtlRuns                 OBJECT-TYPE
    SYNTAX      Counter32
    MAX-ACCESS  read-only
    STATUS      current
    DESCRIPTION
        "The value of tmnxOamTrCtlRuns indicates the number of times this OAM
         trace route test has been executed."
    ::= { tmnxOamTrCtlEntry 24 }

tmnxOamTrCtlFailures             OBJECT-TYPE
    SYNTAX      Counter32
    MAX-ACCESS  read-only
    STATUS      current
    DESCRIPTION
        "The value of tmnxOamTrCtlFailures indicates the number of times this
         OAM trace route test has failed."
    ::= { tmnxOamTrCtlEntry 25 }

tmnxOamTrCtlLastRunResult        OBJECT-TYPE
    SYNTAX      TmnxOamTestResult
    MAX-ACCESS  read-only
    STATUS      current
    DESCRIPTION
        "The value of tmnxOamTrCtlLastRunResult indicates the completion
         status the last time this test was executed.  If this OAM test is
         currently in progress, this object indicates the result of the
         previous test run, if any."
    ::= { tmnxOamTrCtlEntry 26 }

tmnxOamTrCtlLastChanged          OBJECT-TYPE
    SYNTAX      TimeStamp
    MAX-ACCESS  read-only
    STATUS      current
    DESCRIPTION
        "The value of tmnxOamTrCtlLastChanged indicates the time the value of a
         settable object in this row was last changed."
    ::= { tmnxOamTrCtlEntry 27 }

tmnxOamTrCtlVRtrID               OBJECT-TYPE
    SYNTAX      TmnxVRtrID
    MAX-ACCESS  read-create
    STATUS      current
    DESCRIPTION
        "The value of tmnxOamTrCtlVRtrID specifies the virtual router to be
         used for the test.  The value specified must be the index of an active
         row in TIMETRA-VRTR-MIB::vRtrConfTable.

         This object is applicable if tmnxOamTrCtlTestMode is 'icmpTraceRoute'.

         When directing an 'icmpTraceRoute' test to use a virtual router
         associated with a VPRN service, the virtual router can be specified
         using tmnxOamTrCtlVRtrID (with the VPRN's virtual router number) or
         tmnxOamTrCtlServiceId (with the VPRN's service number).
         tmnxOamTrCtlServiceId is preferred, because service numbers are
         constant across an SROS reboot (while virtual routers may be
         renumbered).  If non-default values are specified for both
         tmnxOamTrCtlVRtrID and tmnxOamTrCtlServiceId,
         tmnxOamTrCtlServiceId is used.

         Setting this object is optional."
    DEFVAL      { 1 }
    ::= { tmnxOamTrCtlEntry 28 }

tmnxOamTrCtlTgtAddrType          OBJECT-TYPE
    SYNTAX      InetAddressType
    MAX-ACCESS  read-create
    STATUS      current
    DESCRIPTION
        "The value of tmnxOamTrCtlTgtAddrType specifies the address type of
         tmnxOamTrCtlTgtAddress.

         The values which can be used as part of a successful test depend on
         tmnxOamTrCtlTestMode, as follows.

         Test Mode             tmnxOamTrCtlTgtAddrType Values Supported
         ----------------    ------------------------------------------
         'icmpTraceRoute'                 'ipv4(1)' 'ipv6(2)' 'dns(16)'
         'vprnTraceRoute'                 'ipv4(1)' 'ipv6(2)'
         otherwise           'unknown(0)' "
    DEFVAL      { unknown }
    ::= { tmnxOamTrCtlEntry 29 }

tmnxOamTrCtlTgtAddress           OBJECT-TYPE
    SYNTAX      InetAddress
    MAX-ACCESS  read-create
    STATUS      current
    DESCRIPTION
        "The value of tmnxOamTrCtlTgtAddress specifies the destination host
         address to be used when performing an OAM trace route operation.  The
         corresponding address type is configured using
         tmnxOamTrCtlTgtAddrType."
    DEFVAL      { ''H }
    ::= { tmnxOamTrCtlEntry 30 }

tmnxOamTrCtlSrcAddrType          OBJECT-TYPE
    SYNTAX      InetAddressType
    MAX-ACCESS  read-create
    STATUS      current
    DESCRIPTION
        "The value of tmnxOamTrCtlSrcAddrType specifies the type of Internet
         address stored in tmnxOamTrCtlSrcAddress."
    DEFVAL      { unknown }
    ::= { tmnxOamTrCtlEntry 31 }

tmnxOamTrCtlSrcAddress           OBJECT-TYPE
    SYNTAX      InetAddress (SIZE (0|4|16))
    MAX-ACCESS  read-create
    STATUS      current
    DESCRIPTION
        "The value of tmnxOamTrCtlSrcAddress specifies the IP host address to
         be used as the source when performing an OAM Trace Route operation.

         This object is valid only when the tmnxOamTrCtlTestMode has a value of
         'icmpTraceRoute', 'lspTraceRoute', or 'vccvTraceRoute'."
    DEFVAL      { ''H }
    ::= { tmnxOamTrCtlEntry 32 }

tmnxOamTrCtlWaitMilliSec         OBJECT-TYPE
    SYNTAX      Unsigned32 (10..60000)
    UNITS       "milliseconds"
    MAX-ACCESS  read-create
    STATUS      current
    DESCRIPTION
        "The value of tmnxOamTrCtlWaitMilliSec specifies the time in
         milliseconds to wait for a response before sending the next probe.

         This object is valid only for 'icmpTraceRoute' tests."
    DEFVAL      { 5000 }
    ::= { tmnxOamTrCtlEntry 33 }

tmnxOamTrResultsTable            OBJECT-TYPE
    SYNTAX      SEQUENCE OF TmnxOamTrResultsEntry
    MAX-ACCESS  not-accessible
    STATUS      current
    DESCRIPTION
        "Defines the Nokia SROS OAM Trace Route Test Results Table for keeping
         track of the status of a tmnxOamTrCtlEntry.

         An entry is added to the tmnxOamTrResultsTable when an
         tmnxOamTrCtlEntry is started by successful transition of its
         tmnxOamTrCtlAdminStatus object to enabled(1). An entry is removed from
         the tmnxOamTrResultsTable when its corresponding tmnxOamTrCtlEntry is
         deleted."
    ::= { tmnxOamTraceRouteObjs 4 }

tmnxOamTrResultsEntry            OBJECT-TYPE
    SYNTAX      TmnxOamTrResultsEntry
    MAX-ACCESS  not-accessible
    STATUS      current
    DESCRIPTION
        "Defines an entry in the tmnxOamTrResultsTable.  The
         first two indexes of the tmnxOamTrResultsTable are the
         same as the tmnxOamTrCtlTable in order for a tmnxOamTrResultsEntry
         to correspond to the tmnxOamTrCtlEntry that caused it to
         be created.  The third index allows a history of test runs
         to be stored."
    INDEX       {
        tmnxOamTrCtlOwnerIndex,
        tmnxOamTrCtlTestIndex,
        tmnxOamTrResultsTestRunIndex
    }
    ::= { tmnxOamTrResultsTable 1 }

TmnxOamTrResultsEntry            ::= SEQUENCE
{
    tmnxOamTrResultsOperStatus       INTEGER,
    tmnxOamTrResultsCurHopCount      Gauge32,
    tmnxOamTrResultsCurProbeCount    Gauge32,
    tmnxOamTrResultsIpTgtAddr        IpAddress,
    tmnxOamTrResultsTestAttempts     Unsigned32,
    tmnxOamTrResultsTestSuccesses    Unsigned32,
    tmnxOamTrResultsLastGoodPath     DateAndTime,
    tmnxOamTrResultsTestRunIndex     Unsigned32,
    tmnxOamTrResultsTgtAddrType      InetAddressType,
    tmnxOamTrResultsTgtAddress       InetAddress,
    tmnxOamTrResultsTestRunResult    TmnxOamTestResult
}

tmnxOamTrResultsOperStatus       OBJECT-TYPE
    SYNTAX      INTEGER {
        enabled  (1),
        disabled (2)
    }
    MAX-ACCESS  read-only
    STATUS      current
    DESCRIPTION
        "Reflects the operational state of a tmnxOamTrCtlEntry:

         enabled(1)  - Test is active.
         disabled(2) - Test has stopped."
    ::= { tmnxOamTrResultsEntry 1 }

tmnxOamTrResultsCurHopCount      OBJECT-TYPE
    SYNTAX      Gauge32
    UNITS       "hops"
    MAX-ACCESS  read-only
    STATUS      current
    DESCRIPTION
        "Reflects the current TTL value (range from 0 to 255) for an Nokia SROS
         OAM Trace Route operation. Maximum TTL value is determined by
         tmnxOamTrCtlMaxTtl.

         Zero is returned only in the case of an aborted 'ethCfmLinkTrace'
         test."
    ::= { tmnxOamTrResultsEntry 2 }

tmnxOamTrResultsCurProbeCount    OBJECT-TYPE
    SYNTAX      Gauge32
    UNITS       "probes"
    MAX-ACCESS  read-only
    STATUS      current
    DESCRIPTION
        "Reflects the current probe count (1..10) for an Nokia SROS OAM Trace
         Route operation. The maximum probe count is determined by
         tmnxOamTrCtlProbesPerHop."
    ::= { tmnxOamTrResultsEntry 3 }

tmnxOamTrResultsIpTgtAddr        OBJECT-TYPE
    SYNTAX      IpAddress
    MAX-ACCESS  read-only
    STATUS      obsolete
    DESCRIPTION
        "This objects reports the IP address associated with a
         tmnxOamTrCtlTargetIpAddress value when the destination address is
         specified as a DNS name. The value of this object should be a zero
         length octet string when a DNS name is not specified or when a
         specified DNS name fails to resolve.

         This object was obsoleted in release 4.0 and replaced with InetAddress
         objects tmnxOamTrResultsTgtAddrType and tmnxOamTrResultsTgtAddress."
    ::= { tmnxOamTrResultsEntry 4 }

tmnxOamTrResultsTestAttempts     OBJECT-TYPE
    SYNTAX      Unsigned32
    UNITS       "tests"
    MAX-ACCESS  read-only
    STATUS      obsolete
    DESCRIPTION
        "The current number of attempts to determine a path
         to a target.  The value of this object MUST be started
         at 0.

         This object was made obsolete in the 3.0 release.  Originally
         this table was used to report a summary of the results of all
         traceroute test for the configured test.  An additional index,
         tmnxOamTrResultsTestRunIndex, has been added to this table and
         a row in this table now represents the results of a single
         traceroute test run.  The new object tmnxOamTrCtlRuns in the
         tmnxOamTrCtlTable indicates the number of times this traceroute
         test has been run."
    ::= { tmnxOamTrResultsEntry 5 }

tmnxOamTrResultsTestSuccesses    OBJECT-TYPE
    SYNTAX      Unsigned32
    UNITS       "tests"
    MAX-ACCESS  read-only
    STATUS      obsolete
    DESCRIPTION
        "The current number of attempts to determine a path
         to a target that have succeeded.  The value of this
         object MUST be reported as 0 when no attempts have
         succeeded.

         This object was made obsolete in the 3.0 release.  Originally
         this table was used to report a summary of the results of all
         traceroute test for the configured test.  An additional index,
         tmnxOamTrResultsTestRunIndex, has been added to this table and
         a row in this table now represents the results of a single
         traceroute test run.  The new object tmnxOamTrCtlFailures in the
         tmnxOamTrCtlTable indicates the number of times an attempt to run
         this traceroute test has failed.  The number of successful runs
         can be calculated as (tmnxOamTrCtlRuns - tmnxOamTrCtlFailures)."
    ::= { tmnxOamTrResultsEntry 6 }

tmnxOamTrResultsLastGoodPath     OBJECT-TYPE
    SYNTAX      DateAndTime
    MAX-ACCESS  read-only
    STATUS      current
    DESCRIPTION
        "The date and time when the last complete path was determined."
    ::= { tmnxOamTrResultsEntry 7 }

tmnxOamTrResultsTestRunIndex     OBJECT-TYPE
    SYNTAX      Unsigned32 (1..4294967295)
    MAX-ACCESS  not-accessible
    STATUS      current
    DESCRIPTION
        "The value of tmnxOamTrResultsTestRunIndex identifies the row entry
         that reports results for a single OAM trace route test run.

         The agent starts assigning tmnxOamTrResultsTestRunIndex values at 1
         and wraps after exceeding the maximum possible value as defined by the
         limit of this object."
    ::= { tmnxOamTrResultsEntry 8 }

tmnxOamTrResultsTgtAddrType      OBJECT-TYPE
    SYNTAX      InetAddressType
    MAX-ACCESS  read-only
    STATUS      current
    DESCRIPTION
        "The value of tmnxOamTrResultsTgtAddrType indicates the Internet
         address type stored in tmnxOamTrResultsTgtAddress."
    ::= { tmnxOamTrResultsEntry 9 }

tmnxOamTrResultsTgtAddress       OBJECT-TYPE
    SYNTAX      InetAddress (SIZE (0|4|16))
    MAX-ACCESS  read-only
    STATUS      current
    DESCRIPTION
        "The value of tmnxOamTrResultsTgtAddress indicates the Internet
         address associated with a tmnxOamTrCtlTgtAddress value when the
         destination address is specified as a DNS name.  The value of this
         object should be a zero length octet string when a DNS name is not
         specified or when a specified DNS name fails to resolve."
    ::= { tmnxOamTrResultsEntry 10 }

tmnxOamTrResultsTestRunResult    OBJECT-TYPE
    SYNTAX      TmnxOamTestResult
    MAX-ACCESS  read-only
    STATUS      current
    DESCRIPTION
        "The object contains the overall state of the trace test."
    ::= { tmnxOamTrResultsEntry 11 }

tmnxOamTrProbeHistoryTable       OBJECT-TYPE
    SYNTAX      SEQUENCE OF TmnxOamTrProbeHistoryEntry
    MAX-ACCESS  not-accessible
    STATUS      current
    DESCRIPTION
        "tmnxOamTrProbeHistoryTable contains per-probe results for trace route
         tests.

         The number of rows in this table for a test is limited to the results
         of 3 runs.

         This table is not used for tests which have tmnxOamTrCtlTestMode set
         to 'ldpTreeTrace'."
    ::= { tmnxOamTraceRouteObjs 5 }

tmnxOamTrProbeHistoryEntry       OBJECT-TYPE
    SYNTAX      TmnxOamTrProbeHistoryEntry
    MAX-ACCESS  not-accessible
    STATUS      current
    DESCRIPTION
        "A tmnxOamTrProbeHistoryEntry is created by the system when the result
         of a trace route probe launch is determined.

         A tmnxOamTrProbeHistoryEntry is destroyed when the corresponding
         tmnxOamTrCtlEntry is destroyed.

         The first two indices identify the parent tmnxOamTrCtlEntry.  The third
         index identifies a trace route test run.  Each subsequent index is
         described in its DESCRIPTION clause, below."
    INDEX       {
        tmnxOamTrCtlOwnerIndex,
        tmnxOamTrCtlTestIndex,
        tmnxOamTrResultsTestRunIndex,
        tmnxOamTrProbeHistoryIndex,
        tmnxOamTrProbeHistoryHopIndex,
        tmnxOamTrProbeHistoryProbeIndex
    }
    ::= { tmnxOamTrProbeHistoryTable 1 }

TmnxOamTrProbeHistoryEntry       ::= SEQUENCE
{
    tmnxOamTrProbeHistoryIndex       Unsigned32,
    tmnxOamTrProbeHistoryHopIndex    Unsigned32,
    tmnxOamTrProbeHistoryProbeIndex  Unsigned32,
    tmnxOamTrProbeHistoryIpAddr      IpAddress,
    tmnxOamTrProbeHistoryResponse    Unsigned32,
    tmnxOamTrProbeHistoryOneWayTime  Integer32,
    tmnxOamTrProbeHistoryStatus      TmnxOamResponseStatus,
    tmnxOamTrProbeHistoryLastRC      Integer32,
    tmnxOamTrProbeHistoryTime        DateAndTime,
    tmnxOamTrProbeHistoryResponsePlane TmnxOamTestResponsePlane,
    tmnxOamTrProbeHistoryAddressType TmnxOamAddressType,
    tmnxOamTrProbeHistorySapId       TmnxStrSapId,
    tmnxOamTrProbeHistoryVersion     Unsigned32,
    tmnxOamTrProbeHistoryRouterID    RouterID,
    tmnxOamTrProbeHistoryIfIndex     InterfaceIndexOrZero,
    tmnxOamTrProbeHistoryDataLen     Unsigned32,
    tmnxOamTrProbeHistorySize        Unsigned32,
    tmnxOamTrProbeHistoryInOneWayTime Integer32,
    tmnxOamTrProbeHistoryAddrType    InetAddressType,
    tmnxOamTrProbeHistoryAddress     InetAddress,
    tmnxOamTrProbeHistorySrcGlobalId TmnxMplsTpGlobalID,
    tmnxOamTrProbeHistorySrcNodeId   TmnxMplsTpNodeID,
    tmnxOamTrProbeHistorySdpBindId   TNamedItemOrEmpty,
    tmnxOamTrProbeHistoryRtrnSubcode Unsigned32,
    tmnxOamTrProbeHistoryNtwrkIfName TNamedItemOrEmpty
}

tmnxOamTrProbeHistoryIndex       OBJECT-TYPE
    SYNTAX      Unsigned32 (1..4294967295)
    MAX-ACCESS  not-accessible
    STATUS      current
    DESCRIPTION
        "The value of tmnxOamTrProbeHistoryIndex specifies the entries
         belonging to a single OAM Trace Route test instance.

         The tmnxOamTrProbeHistoryIndex values are assigned starting at 1 and
         wrap on exceeding the upper bound."
    ::= { tmnxOamTrProbeHistoryEntry 1 }

tmnxOamTrProbeHistoryHopIndex    OBJECT-TYPE
    SYNTAX      Unsigned32 (1..255)
    MAX-ACCESS  not-accessible
    STATUS      current
    DESCRIPTION
        "The value of tmnxOamTrProbeHistoryHopIndex specifies the number of hops
         travelled by the outbound trace route request.  The initial value used
         for a particular test is configured using tmnxOamTrCtlInitialTtl."
    ::= { tmnxOamTrProbeHistoryEntry 2 }

tmnxOamTrProbeHistoryProbeIndex  OBJECT-TYPE
    SYNTAX      Unsigned32 (1..10)
    MAX-ACCESS  not-accessible
    STATUS      current
    DESCRIPTION
        "The value of tmnxOamTrProbeHistoryProbeIndex (combined with the
         preceding indices) specifies a trace route reply.  The number of probes
         per hop for a particular test is configured using
         tmnxOamTrCtlProbesPerHop."
    ::= { tmnxOamTrProbeHistoryEntry 3 }

tmnxOamTrProbeHistoryIpAddr      OBJECT-TYPE
    SYNTAX      IpAddress
    MAX-ACCESS  read-only
    STATUS      obsolete
    DESCRIPTION
        "The IP address of a hop in an Nokia SROS OAM Trace Route path. The
         value of tmnxOamTrProbeHistoryIpAddr specifies the IPv4 address of the
         remote node that generated this reply to a OAM Trace Route probe.

         This object was obsoleted in release 4.0 and replaced with InetAddress
         objects tmnxOamTrProbeHistoryAddrType and
         tmnxOamTrProbeHistoryAddress."
    ::= { tmnxOamTrProbeHistoryEntry 4 }

tmnxOamTrProbeHistoryResponse    OBJECT-TYPE
    SYNTAX      Unsigned32
    UNITS       "microseconds"
    MAX-ACCESS  read-only
    STATUS      current
    DESCRIPTION
        "The amount of time measured in microseconds from when a probe was sent
         to when its response was received, two-way time, or when it timed out.

         The value of this object is reported as 0 when it is not possible to
         transmit a probe."
    ::= { tmnxOamTrProbeHistoryEntry 5 }

tmnxOamTrProbeHistoryOneWayTime  OBJECT-TYPE
    SYNTAX      Integer32
    UNITS       "microseconds"
    MAX-ACCESS  read-only
    STATUS      current
    DESCRIPTION
        "The amount of time measured in microseconds from when a OAM probe was
         sent to when it was received by the replier, out-bound one-way time.

         The value of this object is reported as 0 when it is not possible to
         transmit an OAM probe or the information is not available."
    ::= { tmnxOamTrProbeHistoryEntry 6 }

tmnxOamTrProbeHistoryStatus      OBJECT-TYPE
    SYNTAX      TmnxOamResponseStatus
    MAX-ACCESS  read-only
    STATUS      current
    DESCRIPTION
        "The result of an Nokia SROS OAM Trace Route operation made by a remote
         node to a particular probe."
    ::= { tmnxOamTrProbeHistoryEntry 7 }

tmnxOamTrProbeHistoryLastRC      OBJECT-TYPE
    SYNTAX      Integer32
    MAX-ACCESS  read-only
    STATUS      current
    DESCRIPTION
        "The last implementation method specific reply code received.

         The Nokia SROS OAM Trace Route is usually implemented by
         transmitting a series of probe packets with increasing time-to-live
         values.  A probe packet is a UDP datagram encapsulated into an
         IP packet.  Each hop in a path to the target (destination) host
         rejects the probe packets (probe's TTL too small, ICMP reply) until
         either the maximum TTL is exceeded or the target host is
         received.

         For 'icmpTraceRoute', the ICMP code and ICMP type is contained in the
         least significant 16 bits of tmnxOamTrProbeHistoryLastRC. Bits 0 to 7
         contain the ICMP type and bits 8 to 15 contain the ICMP code."
    ::= { tmnxOamTrProbeHistoryEntry 8 }

tmnxOamTrProbeHistoryTime        OBJECT-TYPE
    SYNTAX      DateAndTime
    MAX-ACCESS  read-only
    STATUS      current
    DESCRIPTION
        "Timestamp for when this probe results were determined."
    ::= { tmnxOamTrProbeHistoryEntry 9 }

tmnxOamTrProbeHistoryResponsePlane OBJECT-TYPE
    SYNTAX      TmnxOamTestResponsePlane
    MAX-ACCESS  read-only
    STATUS      current
    DESCRIPTION
        "The value of tmnxOamTrProbeHistoryResponsePlane indicates the type of
         response plane this trace route response was received on."
    ::= { tmnxOamTrProbeHistoryEntry 10 }

tmnxOamTrProbeHistoryAddressType OBJECT-TYPE
    SYNTAX      TmnxOamAddressType
    MAX-ACCESS  read-only
    STATUS      current
    DESCRIPTION
        "The value of tmnxOamTrProbeHistoryAddressType indicates the type of
         binding address information returned in response to a test.

         When the test has the tmnxOamTrCtlTestMode value 'ethCfmLinkTrace',
         'unknown' is returned.

         For 'macTraceRoute', three types of address are applicable - 'sapId',
         'localCpu', and 'sdpId'.  Address type of 'sdpId' is a special case
         used specifically to indicate that the probe was traversing a b-vpls
         node in a PBB network (but where destination MAC is not necessarily
         known to the b-vpls node)."
    ::= { tmnxOamTrProbeHistoryEntry 11 }

tmnxOamTrProbeHistorySapId       OBJECT-TYPE
    SYNTAX      TmnxStrSapId
    MAX-ACCESS  read-only
    STATUS      current
    DESCRIPTION
        "The value of tmnxOamTrProbeHistorySapId is the name of the access port
         of the SAP supporting the requested IP address returned in response to
         a 'vprnTraceRoute' probe.

         If the value of tmnxOamTrProbeHistoryAddressType is not 'sapId', this
         object is not relevant and MUST have a null string ''."
    ::= { tmnxOamTrProbeHistoryEntry 12 }

tmnxOamTrProbeHistoryVersion     OBJECT-TYPE
    SYNTAX      Unsigned32
    MAX-ACCESS  read-only
    STATUS      current
    DESCRIPTION
        "The value of tmnxOamTrProbeHistoryVersion indicates the protocol
         version for this OAM ping reply."
    ::= { tmnxOamTrProbeHistoryEntry 14 }

tmnxOamTrProbeHistoryRouterID    OBJECT-TYPE
    SYNTAX      RouterID
    MAX-ACCESS  read-only
    STATUS      obsolete
    DESCRIPTION
        "The value tmnxOamTrProbeHistoryRouterID indicates the downstream
         router ID of the node that provided this ping reply.  This object
         is valid only when tmnxOamTrCtlTestMode has a value of
         'lspTraceRoute'.

         This object was made obsolete in SROS release 13.0 R1."
    ::= { tmnxOamTrProbeHistoryEntry 15 }

tmnxOamTrProbeHistoryIfIndex     OBJECT-TYPE
    SYNTAX      InterfaceIndexOrZero
    MAX-ACCESS  read-only
    STATUS      current
    DESCRIPTION
        "The value of tmnxOamTrProbeHistoryIfIndex indicates for a
         'lspTraceRoute' or 'vccvTraceRoute' probe the ifIndex value of the
         interface that this probe was transmitted from.

         For other types of probes, this value is not significant and zero is
         returned."
    ::= { tmnxOamTrProbeHistoryEntry 16 }

tmnxOamTrProbeHistoryDataLen     OBJECT-TYPE
    SYNTAX      Unsigned32
    UNITS       "octets"
    MAX-ACCESS  read-only
    STATUS      current
    DESCRIPTION
        "The value of tmnxOamTrProbeHistoryDataLen indicates the UDP data
         length of the echo reply.

         A valid value is returned when the test has a tmnxOamTrCtlTestMode
         value of 'icmpTraceRoute', 'lspTraceRoute', 'p2mpLspTrace', or
         'vccvTraceRoute'.  Otherwise, this value is not significant and zero is
         returned."
    ::= { tmnxOamTrProbeHistoryEntry 17 }

tmnxOamTrProbeHistorySize        OBJECT-TYPE
    SYNTAX      Unsigned32
    UNITS       "octets"
    MAX-ACCESS  read-only
    STATUS      current
    DESCRIPTION
        "The value of tmnxOamTrProbeHistorySize indicates the size in octets
         of the user payload in the probe request packet.  It does not
         include the service encapsulation."
    ::= { tmnxOamTrProbeHistoryEntry 18 }

tmnxOamTrProbeHistoryInOneWayTime OBJECT-TYPE
    SYNTAX      Integer32
    UNITS       "microseconds"
    MAX-ACCESS  read-only
    STATUS      current
    DESCRIPTION
        "The amount of time measured in microseconds from when a OAM probe
         reply was sent to when it was received, in-bound one-way time.

         The value of this object is reported as 0 when the information is not
         available."
    ::= { tmnxOamTrProbeHistoryEntry 19 }

tmnxOamTrProbeHistoryAddrType    OBJECT-TYPE
    SYNTAX      InetAddressType
    MAX-ACCESS  read-only
    STATUS      current
    DESCRIPTION
        "The value of tmnxOamTrProbeHistoryAddrType indicates the address type
         of tmnxOamTrProbeHistoryAddress."
    ::= { tmnxOamTrProbeHistoryEntry 20 }

tmnxOamTrProbeHistoryAddress     OBJECT-TYPE
    SYNTAX      InetAddress (SIZE (0|4|16))
    MAX-ACCESS  read-only
    STATUS      current
    DESCRIPTION
        "The value of tmnxOamTrProbeHistoryAddress indicates the IP address of
         the node which sent the specified trace route reply."
    ::= { tmnxOamTrProbeHistoryEntry 21 }

tmnxOamTrProbeHistorySrcGlobalId OBJECT-TYPE
    SYNTAX      TmnxMplsTpGlobalID
    MAX-ACCESS  read-only
    STATUS      current
    DESCRIPTION
        "The value of tmnxOamTrProbeHistorySrcGlobalId indicates the source
         MPLS-TP global identifier of the replying node.  The value is copied
         from the reply's RFC 6426 Source Identifier TLV.  If the TLV is absent,
         zero is returned.

         This value is relevant when tmnxOamTrCtlTestMode is 'lspTraceRoute' or
         'vccvTraceRoute'.  Otherwise, zero is returned."
    REFERENCE
        "RFC 6426, 'MPLS On-Demand Connectivity Verification and Route Tracing',
         Section 2.2.2, 'Source Identifier TLV'."
    ::= { tmnxOamTrProbeHistoryEntry 22 }

tmnxOamTrProbeHistorySrcNodeId   OBJECT-TYPE
    SYNTAX      TmnxMplsTpNodeID
    MAX-ACCESS  read-only
    STATUS      current
    DESCRIPTION
        "The value of tmnxOamTrProbeHistorySrcNodeId indicates the source
         MPLS-TP node identifier of the replying node.  The value is copied from
         the reply's RFC 6426 Source Identifier TLV.  If the TLV is absent, zero
         is returned.

         This value is relevant when tmnxOamTrCtlTestMode is 'lspTraceRoute' or
         'vccvTraceRoute'.  Otherwise, zero is returned."
    REFERENCE
        "RFC 6426, 'MPLS On-Demand Connectivity Verification and Route Tracing',
         Section 2.2.2, 'Source Identifier TLV'."
    ::= { tmnxOamTrProbeHistoryEntry 23 }

tmnxOamTrProbeHistorySdpBindId   OBJECT-TYPE
    SYNTAX      TNamedItemOrEmpty
    MAX-ACCESS  read-only
    STATUS      current
    DESCRIPTION
        "The value of tmnxOamTrProbeHistorySdpBindId indicates the SDP binding
         provided by the remote system.

         The value of tmnxOamTrProbeHistorySdpBindId is relevant when
         tmnxOamTrProbeHistoryAddressType is 'sdpBindId(9)'."
    ::= { tmnxOamTrProbeHistoryEntry 24 }

tmnxOamTrProbeHistoryRtrnSubcode OBJECT-TYPE
    SYNTAX      Unsigned32
    MAX-ACCESS  read-only
    STATUS      current
    DESCRIPTION
        "The value of tmnxOamTrProbeHistoryRtrnSubcode indicates the value
         present in an MPLS echo reply's RFC 4379 Return Subcode (RSC) field.

         A valid value is returned when the test has a tmnxOamTrCtlTestMode
         value of 'lspTraceRoute' or 'ldpTreeTrace'.  Otherwise, zero is
         returned."
    REFERENCE
        "RFC 4379, 'Detecting Multi-Protocol Label Switched (MPLS) Data Plane
         Failures', Section 3.1, 'Return Codes'."
    ::= { tmnxOamTrProbeHistoryEntry 25 }

tmnxOamTrProbeHistoryNtwrkIfName OBJECT-TYPE
    SYNTAX      TNamedItemOrEmpty
    MAX-ACCESS  read-only
    STATUS      current
    DESCRIPTION
        "The value of tmnxOamTrProbeHistoryNtwrkIfName indicates the network
         interface name provided by the replying node.

         Network interface names are configured using
         TIMETRA-VRTR-MIB::vRtrIfName.

         The value of this object is the empty string when the value of
         tmnxOamTrProbeHistoryAddressType is not 'networkInterface(11)'."
    ::= { tmnxOamTrProbeHistoryEntry 26 }

tmnxOamTrHopsTable               OBJECT-TYPE
    SYNTAX      SEQUENCE OF TmnxOamTrHopsEntry
    MAX-ACCESS  not-accessible
    STATUS      current
    DESCRIPTION
        "Defines the Nokia SROS OAM Trace Route Hop Table for keeping track of
         the results of an Nokia SROS OAM Trace Route test on a per hop basis."
    ::= { tmnxOamTraceRouteObjs 6 }

tmnxOamTrHopsEntry               OBJECT-TYPE
    SYNTAX      TmnxOamTrHopsEntry
    MAX-ACCESS  not-accessible
    STATUS      current
    DESCRIPTION
        "Defines an entry in the tmnxOamTrHopsTable.
         The first two index elements identify the tmnxOamTrCtlEntry
         that a tmnxOamTrHopsEntry belongs to.  The third index element
         identifies a OAM trace route test run.  The fourth index element,
         tmnxOamTrHopsHopIndex, selects a hop in an Nokia SROS OAM
         Trace Route path."
    INDEX       {
        tmnxOamTrCtlOwnerIndex,
        tmnxOamTrCtlTestIndex,
        tmnxOamTrResultsTestRunIndex,
        tmnxOamTrHopsHopIndex
    }
    ::= { tmnxOamTrHopsTable 1 }

TmnxOamTrHopsEntry               ::= SEQUENCE
{
    tmnxOamTrHopsHopIndex            Unsigned32,
    tmnxOamTrHopsIpTgtAddress        IpAddress,
    tmnxOamTrHopsMinRtt              Unsigned32,
    tmnxOamTrHopsMaxRtt              Unsigned32,
    tmnxOamTrHopsAverageRtt          Unsigned32,
    tmnxOamTrHopsRttSumOfSquares     Unsigned32,
    tmnxOamTrHopsMinTt               Integer32,
    tmnxOamTrHopsMaxTt               Integer32,
    tmnxOamTrHopsAverageTt           Integer32,
    tmnxOamTrHopsTtSumOfSquares      Unsigned32,
    tmnxOamTrHopsSentProbes          Unsigned32,
    tmnxOamTrHopsProbeResponses      Unsigned32,
    tmnxOamTrHopsLastGoodProbe       DateAndTime,
    tmnxOamTrHopsMinInTt             Integer32,
    tmnxOamTrHopsMaxInTt             Integer32,
    tmnxOamTrHopsAverageInTt         Integer32,
    tmnxOamTrHopsInTtSumOfSqrs       Unsigned32,
    tmnxOamTrHopsOutJitter           Integer32,
    tmnxOamTrHopsInJitter            Integer32,
    tmnxOamTrHopsRtJitter            Integer32,
    tmnxOamTrHopsProbeTimeouts       Unsigned32,
    tmnxOamTrHopsProbeFailures       Unsigned32,
    tmnxOamTrHopsTgtAddrType         InetAddressType,
    tmnxOamTrHopsTgtAddress          InetAddress,
    tmnxOamTrHopsRttOFSumSquares     Counter32,
    tmnxOamTrHopsRttHCSumSquares     Counter64,
    tmnxOamTrHopsTtOFSumSquares      Counter32,
    tmnxOamTrHopsTtHCSumSquares      Counter64,
    tmnxOamTrHopsInTtOFSumSqrs       Counter32,
    tmnxOamTrHopsInTtHCSumSqrs       Counter64
}

tmnxOamTrHopsHopIndex            OBJECT-TYPE
    SYNTAX      Unsigned32
    MAX-ACCESS  not-accessible
    STATUS      current
    DESCRIPTION
        "Specifies the hop index for an Nokia SROS OAM Trace Route
         hop.  Values for this object with respect to the same
         tmnxOamTrCtlOwnerIndex and tmnxOamTrCtlTestIndex MUST start at 1
         and increase monotonically.

         The tmnxOamTrHopsTable keeps the current Nokia SROS OAM Trace Route
         path per tmnxOamTrCtlEntry.

         All hops (tmnxOamTrHopsTable entries) in an Nokia SROS OAM
         Trace Route path MUST be updated at the same time when an
         Nokia SROS OAM Trace Route operation completes.  Care needs
         to be applied when either a path changes or can't be determined.
         The initial portion of the path, up to the first hop change, MUST
         retain the same tmnxOamTrHopsHopIndex values.  The remaining portion
         of the path SHOULD be assigned new tmnxOamTrHopsHopIndex values."
    ::= { tmnxOamTrHopsEntry 1 }

tmnxOamTrHopsIpTgtAddress        OBJECT-TYPE
    SYNTAX      IpAddress
    MAX-ACCESS  read-only
    STATUS      obsolete
    DESCRIPTION
        "This object reports the IP address associated with
         the hop.  A value for this object should be reported
         as a numeric IP address and not as a DNS name.

         This value of this object is not significant when tmnxOamTrCtlTestMode
         has a value of 'macTraceRoute'.

         This object was obsoleted in release 4.0 and replaced with InetAddress
         objects tmnxOamTrHopsTgtAddrType and tmnxOamTrHopsTgtAddrType."
    ::= { tmnxOamTrHopsEntry 2 }

tmnxOamTrHopsMinRtt              OBJECT-TYPE
    SYNTAX      Unsigned32
    UNITS       "microseconds"
    MAX-ACCESS  read-only
    STATUS      current
    DESCRIPTION
        "The minimum Nokia SROS OAM Trace Route round-trip-time (RTT)
         received for this hop.  A value of 0 for this object implies that no
         RTT has been received."
    ::= { tmnxOamTrHopsEntry 3 }

tmnxOamTrHopsMaxRtt              OBJECT-TYPE
    SYNTAX      Unsigned32
    UNITS       "microseconds"
    MAX-ACCESS  read-only
    STATUS      current
    DESCRIPTION
        "The maximum Nokia SROS OAM Trace Route round-trip-time (RTT)
         received for this hop.  A value of 0 for this object implies that no
         RTT has been received."
    ::= { tmnxOamTrHopsEntry 4 }

tmnxOamTrHopsAverageRtt          OBJECT-TYPE
    SYNTAX      Unsigned32
    UNITS       "microseconds"
    MAX-ACCESS  read-only
    STATUS      current
    DESCRIPTION
        "The current average Nokia SROS OAM Trace Route round-trip-time (RTT)
         for this hop."
    ::= { tmnxOamTrHopsEntry 5 }

tmnxOamTrHopsRttSumOfSquares     OBJECT-TYPE
    SYNTAX      Unsigned32
    UNITS       "microseconds squared"
    MAX-ACCESS  read-only
    STATUS      current
    DESCRIPTION
        "The value of tmnxOamTrHopsRttSumOfSquares indicates the least
         significant 32 bits of tmnxOamTrHopsRttHCSumSquares."
    ::= { tmnxOamTrHopsEntry 6 }

tmnxOamTrHopsMinTt               OBJECT-TYPE
    SYNTAX      Integer32
    UNITS       "microseconds"
    MAX-ACCESS  read-only
    STATUS      current
    DESCRIPTION
        "The minimum Nokia SROS OAM Trace Route outbound one-way trip
         time received for this hop.  A value of 0 for this object implies
         that no one-way trip time has been received."
    ::= { tmnxOamTrHopsEntry 7 }

tmnxOamTrHopsMaxTt               OBJECT-TYPE
    SYNTAX      Integer32
    UNITS       "microseconds"
    MAX-ACCESS  read-only
    STATUS      current
    DESCRIPTION
        "The maximum Nokia SROS OAM Trace Route outbound one-way trip
         time received for this hop.  A value of 0 for this object implies
         that no one-way trip time has been received."
    ::= { tmnxOamTrHopsEntry 8 }

tmnxOamTrHopsAverageTt           OBJECT-TYPE
    SYNTAX      Integer32
    UNITS       "microseconds"
    MAX-ACCESS  read-only
    STATUS      current
    DESCRIPTION
        "The current average Nokia SROS OAM Trace Route outbound one-way trip
         time for this hop."
    ::= { tmnxOamTrHopsEntry 9 }

tmnxOamTrHopsTtSumOfSquares      OBJECT-TYPE
    SYNTAX      Unsigned32
    UNITS       "microseconds squared"
    MAX-ACCESS  read-only
    STATUS      current
    DESCRIPTION
        "The value of tmnxOamTrHopsTtSumOfSquares indicates the least
         significant 32 bits of tmnxOamTrHopsTtHCSumSquares."
    ::= { tmnxOamTrHopsEntry 10 }

tmnxOamTrHopsSentProbes          OBJECT-TYPE
    SYNTAX      Unsigned32
    MAX-ACCESS  read-only
    STATUS      current
    DESCRIPTION
        "The value of this object reflects the number of probes sent for this
         hop during this Nokia SROS OAM Trace Route test. The value of this
         object should start at 0."
    ::= { tmnxOamTrHopsEntry 11 }

tmnxOamTrHopsProbeResponses      OBJECT-TYPE
    SYNTAX      Unsigned32
    MAX-ACCESS  read-only
    STATUS      current
    DESCRIPTION
        "Number of responses received for this hop during this Nokia
         SROS OAM Trace Route test.  This value of this object should
         start at 0."
    ::= { tmnxOamTrHopsEntry 12 }

tmnxOamTrHopsLastGoodProbe       OBJECT-TYPE
    SYNTAX      DateAndTime
    MAX-ACCESS  read-only
    STATUS      current
    DESCRIPTION
        "Date and time when the last response was received for a probe for this
         hop during this Nokia SROS OAM Trace Route test."
    ::= { tmnxOamTrHopsEntry 13 }

tmnxOamTrHopsMinInTt             OBJECT-TYPE
    SYNTAX      Integer32
    UNITS       "microseconds"
    MAX-ACCESS  read-only
    STATUS      current
    DESCRIPTION
        "The minimum OAM trace route inbound one-way trip time received. A
         value of 0 for this object implies that no one-way trip time
         measurement is available."
    ::= { tmnxOamTrHopsEntry 18 }

tmnxOamTrHopsMaxInTt             OBJECT-TYPE
    SYNTAX      Integer32
    UNITS       "microseconds"
    MAX-ACCESS  read-only
    STATUS      current
    DESCRIPTION
        "The maximum OAM trace route inbound one-way trip time received. A
         value of 0 for this object implies that no one-way trip time
         measurement is available."
    ::= { tmnxOamTrHopsEntry 19 }

tmnxOamTrHopsAverageInTt         OBJECT-TYPE
    SYNTAX      Integer32
    UNITS       "microseconds"
    MAX-ACCESS  read-only
    STATUS      current
    DESCRIPTION
        "The current average OAM inbound inbound one-way trip time. A value of
         0 for this object implies that no one-way trip time measurement is
         available."
    ::= { tmnxOamTrHopsEntry 20 }

tmnxOamTrHopsInTtSumOfSqrs       OBJECT-TYPE
    SYNTAX      Unsigned32
    UNITS       "microseconds squared"
    MAX-ACCESS  read-only
    STATUS      current
    DESCRIPTION
        "The value of tmnxOamTrHopsInTtSumOfSqrs indicates the least
         significant 32 bits of tmnxOamTrHopsInTtHCSumSqrs."
    ::= { tmnxOamTrHopsEntry 21 }

tmnxOamTrHopsOutJitter           OBJECT-TYPE
    SYNTAX      Integer32
    UNITS       "microseconds"
    MAX-ACCESS  read-only
    STATUS      current
    DESCRIPTION
        "The value of tmnxOamTrHopsOutJitter indicates the amount of outbound
         one-way trip jitter, expressed in microseconds, for a trace route
         probe request packet sent for this OAM test.

         A value of 0 for this object implies that no one-way trip jitter
         measurement is available."
    ::= { tmnxOamTrHopsEntry 22 }

tmnxOamTrHopsInJitter            OBJECT-TYPE
    SYNTAX      Integer32
    UNITS       "microseconds"
    MAX-ACCESS  read-only
    STATUS      current
    DESCRIPTION
        "The value of tmnxOamTrHopsInJitter indicates the amount of inbound
         one-way trip jitter, expressed in microseconds, for a trace route
         probe response packet received for this OAM test.

         A value of 0 for this object implies that no one-way trip jitter
         measurement is available."
    ::= { tmnxOamTrHopsEntry 23 }

tmnxOamTrHopsRtJitter            OBJECT-TYPE
    SYNTAX      Integer32
    UNITS       "microseconds"
    MAX-ACCESS  read-only
    STATUS      current
    DESCRIPTION
        "The value of tmnxOamTrHopsRtJitter indicates the amount of two-way
         trip jitter, expressed in microseconds, for a trace route probe sent
         for this OAM test.

         A value of 0 for this object implies that no two-way-trip jitter
         measurement is available."
    ::= { tmnxOamTrHopsEntry 24 }

tmnxOamTrHopsProbeTimeouts       OBJECT-TYPE
    SYNTAX      Unsigned32
    MAX-ACCESS  read-only
    STATUS      current
    DESCRIPTION
        "The value of tmnxOamTrHopsProbeTimeouts indicates the number of probes
         that timed out without receiving a response."
    ::= { tmnxOamTrHopsEntry 25 }

tmnxOamTrHopsProbeFailures       OBJECT-TYPE
    SYNTAX      Unsigned32
    MAX-ACCESS  read-only
    STATUS      current
    DESCRIPTION
        "The value of tmnxOamTrHopsProbeFailures indicates the total number of
         probes that failed to be transmitted plus the number of probes that
         timed out without receiving a response."
    ::= { tmnxOamTrHopsEntry 26 }

tmnxOamTrHopsTgtAddrType         OBJECT-TYPE
    SYNTAX      InetAddressType
    MAX-ACCESS  read-only
    STATUS      current
    DESCRIPTION
        "The value of tmnxOamTrHopsTgtAddrType indicates the Internet address
         type stored in tmnxOamTrHopsTgtAddress."
    ::= { tmnxOamTrHopsEntry 27 }

tmnxOamTrHopsTgtAddress          OBJECT-TYPE
    SYNTAX      InetAddress (SIZE (0|4|16))
    MAX-ACCESS  read-only
    STATUS      current
    DESCRIPTION
        "The value of tmnxOamTrHopsTgtAddress indicates the Internet
         address associated with the hop.  A value for this object should
         be reported as a numeric IP address and not as a DNS name.

         This value of this object is not significant when tmnxOamTrCtlTestMode
         has a value of 'macTraceRoute' or 'ethCfmLinkTrace'."
    ::= { tmnxOamTrHopsEntry 28 }

tmnxOamTrHopsRttOFSumSquares     OBJECT-TYPE
    SYNTAX      Counter32
    MAX-ACCESS  read-only
    STATUS      current
    DESCRIPTION
        "The value of tmnxOamTrHopsRttOFSumSquares indicates the number of
         times tmnxOamTrHopsRttSumOfSquares overflowed."
    ::= { tmnxOamTrHopsEntry 29 }

tmnxOamTrHopsRttHCSumSquares     OBJECT-TYPE
    SYNTAX      Counter64
    UNITS       "microseconds squared"
    MAX-ACCESS  read-only
    STATUS      current
    DESCRIPTION
        "The value of tmnxOamTrHopsRttHCSumSquares indicates the sum of squares
         of the round trip times of the trace route test for this hop.  Its
         purpose is to enable the standard deviation calculation.

         The value of this object will be reported as 0 when one or more of the
         following conditions apply:
         1.  No round trip time measurement is available.
         2.  The test stopped before completion.
         3.  The test type (i.e. tmnxOamTrCtlTestMode) is one of the following:
             'ldpTreeTrace',
             'mcastTraceRoute',
             'p2mpLspTrace'."
    ::= { tmnxOamTrHopsEntry 30 }

tmnxOamTrHopsTtOFSumSquares      OBJECT-TYPE
    SYNTAX      Counter32
    MAX-ACCESS  read-only
    STATUS      current
    DESCRIPTION
        "The value of tmnxOamTrHopsTtOFSumSquares indicates the number of times
         tmnxOamTrHopsTtSumOfSquares overflowed."
    ::= { tmnxOamTrHopsEntry 31 }

tmnxOamTrHopsTtHCSumSquares      OBJECT-TYPE
    SYNTAX      Counter64
    UNITS       "microseconds squared"
    MAX-ACCESS  read-only
    STATUS      current
    DESCRIPTION
        "The value of tmnxOamTrHopsTtHCSumSquares indicates the sum of squares
         of the outbound one-way trip times of the trace route test for this
         hop.  Its purpose is to enable the standard deviation calculation.

         The value of this object will be reported as 0 when one or more of the
         following conditions apply:
         1.  No outbound one-way trip time measurement is available.
         2.  The test stopped before completion.
         3.  The test type (i.e. tmnxOamTrCtlTestMode) is one of the following:
             'ldpTreeTrace',
             'mcastTraceRoute',
             'p2mpLspTrace'."
    ::= { tmnxOamTrHopsEntry 32 }

tmnxOamTrHopsInTtOFSumSqrs       OBJECT-TYPE
    SYNTAX      Counter32
    MAX-ACCESS  read-only
    STATUS      current
    DESCRIPTION
        "The value of tmnxOamTrHopsInTtOFSumSqrs indicates the number of times
         tmnxOamTrHopsInTtSumOfSqrs overflowed."
    ::= { tmnxOamTrHopsEntry 33 }

tmnxOamTrHopsInTtHCSumSqrs       OBJECT-TYPE
    SYNTAX      Counter64
    UNITS       "microseconds squared"
    MAX-ACCESS  read-only
    STATUS      current
    DESCRIPTION
        "The value of tmnxOamTrHopsInTtHCSumSqrs indicates the sum of squares
         of the inbound one-way trip times of the trace route test for this
         hop. Its purpose is to enable the standard deviation calculation.

         The value of this object will be reported as 0 when one or more of the
         following conditions apply:
         1.  No inbound one-way trip time measurement is available.
         2.  The test stopped before completion.
         3.  The test type (i.e. tmnxOamTrCtlTestMode) is one of the following:
             'ldpTreeTrace',
             'mcastTraceRoute',
             'p2mpLspTrace'."
    ::= { tmnxOamTrHopsEntry 34 }

tmnxOamMacTrCtlTable             OBJECT-TYPE
    SYNTAX      SEQUENCE OF TmnxOamMacTrCtlEntry
    MAX-ACCESS  not-accessible
    STATUS      current
    DESCRIPTION
        "Defines the Nokia SROS OAM MAC Trace Route Control Table for
         providing, via SNMP, the capability of performing Nokia SROS
         OAM 'macTraceRoute' test operations.  The results of these tests
         are stored in the tmnxOamTrResultsTable, tmnxOamTrProbeHistoryTable
         and the tmnxOamMacTrL2MapTable."
    ::= { tmnxOamTraceRouteObjs 7 }

tmnxOamMacTrCtlEntry             OBJECT-TYPE
    SYNTAX      TmnxOamMacTrCtlEntry
    MAX-ACCESS  not-accessible
    STATUS      current
    DESCRIPTION
        "Defines an entry in the tmnxOamMacTrCtlTable.  The first index
         element, tmnxOamTrCtlOwnerIndex, is of type SnmpAdminString,
         a textual convention that allows for use of the SNMPv3
         View-Based Access Control Model (RFC 2575 [11], VACM)
         and allows a management application to identify its entries.
         The second index, tmnxOamTrCtlTestIndex, enables the same
         management application to have multiple outstanding requests."
    INDEX       {
        tmnxOamTrCtlOwnerIndex,
        tmnxOamTrCtlTestIndex
    }
    ::= { tmnxOamMacTrCtlTable 1 }

TmnxOamMacTrCtlEntry             ::= SEQUENCE
{
    tmnxOamMacTrCtlTargetMacAddr     MacAddress,
    tmnxOamMacTrCtlSourceMacAddr     MacAddress,
    tmnxOamMacTrCtlSendControl       TruthValue,
    tmnxOamMacTrCtlReplyControl      TruthValue
}

tmnxOamMacTrCtlTargetMacAddr     OBJECT-TYPE
    SYNTAX      MacAddress
    MAX-ACCESS  read-create
    STATUS      current
    DESCRIPTION
        "The value of tmnxOamMacTrCtlTargetMacAddr is a 6-octet value that
         specifies the target MAC address to be used in the query request for
         performing an OAM Mac Trace Route operation when tmnxOamTrCtlTestMode
         has a value of 'macTraceRoute'. "
    REFERENCE
        "IEEE 802.3 Subclause 30.7.1.1.9"
    DEFVAL      { '000000000000'H }
    ::= { tmnxOamMacTrCtlEntry 1 }

tmnxOamMacTrCtlSourceMacAddr     OBJECT-TYPE
    SYNTAX      MacAddress
    MAX-ACCESS  read-create
    STATUS      current
    DESCRIPTION
        "The value of tmnxOamMacTrCtlSourceMacAddr is a 6-octet value that
         specifies the MAC address to be used as the source in the query
         request for performing an OAM MAC Trace Route operation when
         tmnxOamTrCtlTestMode has a value of 'macTraceRoute'. "
    REFERENCE
        "IEEE 802.3 Subclause 30.7.1.1.9"
    DEFVAL      { '000000000000'H }
    ::= { tmnxOamMacTrCtlEntry 2 }

tmnxOamMacTrCtlSendControl       OBJECT-TYPE
    SYNTAX      TruthValue
    MAX-ACCESS  read-create
    STATUS      current
    DESCRIPTION
        "The value of tmnxOamMacTrCtlSendControl specifies whether the outbound
         MAC trace route packet will use the data plane or the control plane.

         When the value is 'false', the packet is sent using the data plane.

         As of SROS release 13.0 R1, a test cannot be started if
         tmnxOamMacTrCtlSendControl is 'true'.  A test is started using
         tmnxOamTrCtlAdminStatus.

         This object will be marked obsolete in a future release."
    DEFVAL      { false }
    ::= { tmnxOamMacTrCtlEntry 3 }

tmnxOamMacTrCtlReplyControl      OBJECT-TYPE
    SYNTAX      TruthValue
    MAX-ACCESS  read-create
    STATUS      current
    DESCRIPTION
        "When the value of tmnxOamMacTrCtlReplyControl is 'true', the OAM Mac
         Trace Route response is returned using the control plane. If its value
         is 'false', the packet is sent via the data plane."
    DEFVAL      { false }
    ::= { tmnxOamMacTrCtlEntry 4 }

tmnxOamMacTrL2MapTable           OBJECT-TYPE
    SYNTAX      SEQUENCE OF TmnxOamMacTrL2MapEntry
    MAX-ACCESS  not-accessible
    STATUS      current
    DESCRIPTION
        "Defines a table for storing the results of an OAM 'macTraceRoute'
         probe operation when a L2 Mapping TLV was returned.  Each row
         represents a single L2FEC TLV within the L2 Mapping TLV. A single
         L2 mapping entry is returned if the 'macTraceRoute' replier knows
         the requested VPN ID and has a binding for the requested MAC
         address.  Multiple downstream L2 mappings that specify
         the replier's flooding domain may be returned if the replier has
         no bindings for the MAC address.

         An entry in this table is created when the result of an OAM
         'macTraceRoute' probe is determined.  An entry is removed from
         this table when its corresponding tmnxOamTrCtlEntry is deleted."
    ::= { tmnxOamTraceRouteObjs 8 }

tmnxOamMacTrL2MapEntry           OBJECT-TYPE
    SYNTAX      TmnxOamMacTrL2MapEntry
    MAX-ACCESS  not-accessible
    STATUS      current
    DESCRIPTION
        "Defines an entry in the tmnxOamMacTrL2MapTable.  The first two
         index elements identify the tmnxOamTrCtlEntry that a
         tmnxOamMacTrL2MapEntry belongs to.  The third index element
         identifies a particular OAM trace route test run.  The fourth
         index element selects the group of responses associated with a
         specific probe attempt.  The fifth and sixth indexes select the
         hop and the probe at that hop for a particular Nokia SROS
         OAM Trace Route operation.  Note that in the case of a successful
         'macTraceRoute' reply there will be only one row entry created.
         However there may also be one or more error replies.  The seventh
         index selects a single L2 mapping entry within a specific
         probe reply."
    INDEX       {
        tmnxOamTrCtlOwnerIndex,
        tmnxOamTrCtlTestIndex,
        tmnxOamTrResultsTestRunIndex,
        tmnxOamTrProbeHistoryIndex,
        tmnxOamTrProbeHistoryHopIndex,
        tmnxOamTrProbeHistoryProbeIndex,
        tmnxOamMacTrL2MapIndex
    }
    ::= { tmnxOamMacTrL2MapTable 1 }

TmnxOamMacTrL2MapEntry           ::= SEQUENCE
{
    tmnxOamMacTrL2MapIndex           Unsigned32,
    tmnxOamMacTrL2MapRouterID        IpAddress,
    tmnxOamMacTrL2MapLabel           MplsLabel,
    tmnxOamMacTrL2MapProtocol        TmnxOamSignalProtocol,
    tmnxOamMacTrL2MapVCType          TmnxOamVcType,
    tmnxOamMacTrL2MapVCID            TmnxVcId,
    tmnxOamMacTrL2MapDirection       INTEGER,
    tmnxOamMacTrL2MapSdpId           SdpId,
    tmnxOamMacTrL2MapSapName         TNamedItemOrEmpty
}

tmnxOamMacTrL2MapIndex           OBJECT-TYPE
    SYNTAX      Unsigned32 (1..4294967295)
    MAX-ACCESS  not-accessible
    STATUS      current
    DESCRIPTION
        "The tmnxOamMacTrL2MapIndex selects a single L2 mapping entry within a
         specific 'macTraceRoute' probe reply.

         The agent starts assigning tmnxOamMacTrL2MapIndex values at 1."
    ::= { tmnxOamMacTrL2MapEntry 1 }

tmnxOamMacTrL2MapRouterID        OBJECT-TYPE
    SYNTAX      IpAddress
    MAX-ACCESS  read-only
    STATUS      current
    DESCRIPTION
        "The value of tmnxOamMacTrL2MapRouterID is the router ID for this L2
         mapping entry."
    ::= { tmnxOamMacTrL2MapEntry 2 }

tmnxOamMacTrL2MapLabel           OBJECT-TYPE
    SYNTAX      MplsLabel
    MAX-ACCESS  read-only
    STATUS      current
    DESCRIPTION
        "The value of tmnxOamMacTrL2MapLabel is the label used by the router
         for the L2FEC or VC ID specified by this L2 mapping entry."
    ::= { tmnxOamMacTrL2MapEntry 3 }

tmnxOamMacTrL2MapProtocol        OBJECT-TYPE
    SYNTAX      TmnxOamSignalProtocol
    MAX-ACCESS  read-only
    STATUS      current
    DESCRIPTION
        "The value of tmnxOamMacTrL2MapProtocol is the signaling protocol used
         by the router for the L2FEC or VC ID specified by this L2 mapping
         entry."
    ::= { tmnxOamMacTrL2MapEntry 4 }

tmnxOamMacTrL2MapVCType          OBJECT-TYPE
    SYNTAX      TmnxOamVcType
    MAX-ACCESS  read-only
    STATUS      current
    DESCRIPTION
        "The value of tmnxOamMacTrL2MapVCType indicates the class of VC ID
         given in tmnxOamMacTrL2MapVCID."
    ::= { tmnxOamMacTrL2MapEntry 5 }

tmnxOamMacTrL2MapVCID            OBJECT-TYPE
    SYNTAX      TmnxVcId
    MAX-ACCESS  read-only
    STATUS      current
    DESCRIPTION
        "The value of tmnxOamMacTrL2MapVCID is the VC ID associated with the
         label used by the L2FEC specified by this L2 mapping entry."
    ::= { tmnxOamMacTrL2MapEntry 6 }

tmnxOamMacTrL2MapDirection       OBJECT-TYPE
    SYNTAX      INTEGER {
        upstream   (1),
        downstream (2)
    }
    MAX-ACCESS  read-only
    STATUS      current
    DESCRIPTION
        "The value of tmnxOamMacTrL2MapDirection indicates the direction that
         this L2 mapping entry is in relation to the node that returned the
         'macTraceRoute' reply."
    ::= { tmnxOamMacTrL2MapEntry 7 }

tmnxOamMacTrL2MapSdpId           OBJECT-TYPE
    SYNTAX      SdpId
    MAX-ACCESS  read-only
    STATUS      current
    DESCRIPTION
        "The value of tmnxOamMacTrL2MapSdpId indicates the ID of the SDP
         supporting the L2 mapping entry that returned the reply.

         If this mapping is not a SDP, this object is not relevant and MUST
         return a value of '0'."
    ::= { tmnxOamMacTrL2MapEntry 8 }

tmnxOamMacTrL2MapSapName         OBJECT-TYPE
    SYNTAX      TNamedItemOrEmpty
    MAX-ACCESS  read-only
    STATUS      current
    DESCRIPTION
        "The value of tmnxOamMacTrL2MapSapName indicates the SAP name when the
         downstream of the responder is a SAP.

         If the downstream responder is not a SAP, this object is not relevant
         and MUST return a zero length empty string."
    ::= { tmnxOamMacTrL2MapEntry 9 }

tmnxOamLspTrCtlTable             OBJECT-TYPE
    SYNTAX      SEQUENCE OF TmnxOamLspTrCtlEntry
    MAX-ACCESS  not-accessible
    STATUS      current
    DESCRIPTION
        "Each row in tmnxOamLspTrCtlTable contains the LSP-specific
         configuration information needed to launch an LSP (Label Switched Path)
         trace route test.  The rest of the configuration information needed to
         launch the test resides in the corresponding row of tmnxOamTrCtlTable.

         Results of LSP trace route tests are stored in tmnxOamTrResultsTable,
         tmnxOamTrProbeHistoryTable, tmnxOamTrHopsTable, tmnxOamLspTrMapTable,
         and tmnxOamLspTrDSLabelTable.

         Seven types of LSP trace route tests are supported.  An abbreviated
         name for each test type is defined in the following table (for use in a
         subsequent table).  The test type's tmnxOamLspTrCtlTestSubMode code
         point is shown as well.

         Test Sub Mode           Abbreviated Test Type Name(s)
         ---------------------   -------------------------------
         'unspecified     (1)'   LDP, RSVP
         'static          (2)'   TPST (Transport Profile Static)
         'bgpLabeledPrefix(3)'   BGP
         'srIsis          (4)'   ISIS
         'srOspf          (5)'   OSPF
         'srTe            (6)'   SRTE

         The following table has a row for each LSP trace route test type,
         showing the mandatory and optional objects applicable to the test
         type.

         Test
         Type   Mandatory Objects               Optional Objects
         ---- -------------------------------- ---------------------------------
         BGP  tmnxOamLspTrCtlLdpPrefixType     *tmnxOamLspTrCtlNhAddressType
              tmnxOamLspTrCtlLdpPrefix         *tmnxOamLspTrCtlNhAddress
              tmnxOamLspTrCtlLdpPrefixLen       tmnxOamLspTrCtlNhIntfName
              tmnxOamLspTrCtlTestSubMode       #tmnxOamLspTrCtlPathDestType
                                               #tmnxOamLspTrCtlPathDest

         ISIS tmnxOamLspTrCtlLdpPrefixType      tmnxOamLspTrCtlIgpInstance
              tmnxOamLspTrCtlLdpPrefix         *tmnxOamLspTrCtlNhAddressType
              tmnxOamLspTrCtlLdpPrefixLen      *tmnxOamLspTrCtlNhAddress
              tmnxOamLspTrCtlTestSubMode        tmnxOamLspTrCtlNhIntfName
                                               #tmnxOamLspTrCtlPathDestType
                                               #tmnxOamLspTrCtlPathDest

         LDP  tmnxOamLspTrCtlLdpPrefixType     *tmnxOamLspTrCtlNhAddressType
              tmnxOamLspTrCtlLdpPrefix         *tmnxOamLspTrCtlNhAddress
              tmnxOamLspTrCtlLdpPrefixLen       tmnxOamLspTrCtlNhIntfName
                                               #tmnxOamLspTrCtlPathDestType
                                               #tmnxOamLspTrCtlPathDest

         OSPF tmnxOamLspTrCtlLdpPrefixType      tmnxOamLspTrCtlIgpInstance
              tmnxOamLspTrCtlLdpPrefix         *tmnxOamLspTrCtlNhAddressType
              tmnxOamLspTrCtlLdpPrefixLen      *tmnxOamLspTrCtlNhAddress
              tmnxOamLspTrCtlTestSubMode        tmnxOamLspTrCtlNhIntfName
                                               #tmnxOamLspTrCtlPathDestType
                                               #tmnxOamLspTrCtlPathDest

         RSVP tmnxOamLspTrCtlLspName            tmnxOamLspTrCtlPathName

         SRTE tmnxOamLspTrCtlLspName           *tmnxOamLspTrCtlNhAddressType
              tmnxOamLspTrCtlTestSubMode       *tmnxOamLspTrCtlNhAddress
                                                tmnxOamLspTrCtlNhIntfName
                                               #tmnxOamLspTrCtlPathDestType
                                               #tmnxOamLspTrCtlPathDest
                                                tmnxOamLspTrCtlPathName

         TPST tmnxOamLspTrCtlLspName            tmnxOamLspTrCtlAssocChannel
              tmnxOamLspTrCtlTestSubMode        tmnxOamLspTrCtlForce
                                                tmnxOamLspTrCtlMplsTpPathType

         ALL  none                              tmnxOamLspTrCtlDownstreamMapTlv
                                                tmnxOamTrCtlDataSize
                                                tmnxOamTrCtlFcName
                                                tmnxOamTrCtlInitialTtl
                                                tmnxOamTrCtlInterval
                                                tmnxOamTrCtlMaxFailures
                                                tmnxOamTrCtlMaxTtl
                                                tmnxOamTrCtlProbesPerHop
                                                tmnxOamTrCtlProfile
                                               *tmnxOamTrCtlSrcAddrType
                                               *tmnxOamTrCtlSrcAddress
                                                tmnxOamTrCtlTimeOut
         ---- -------------------------------- ---------------------------------

         In the table above,
         1.  The optional objects in the ALL row apply to all LSP trace route
             test types.
         2.  Asterisks (*) mark a set of optional objects which must all be
             specified, or must all be unspecified.
         3.  Octothorpes (#) mark a separate set of optional objects which must
             all be specified, or must all be unspecified.
         4.  There are four supported combinations of
             tmnxOamLspTrCtlNhAddressType, tmnxOamLspTrCtlNhAddress,
             tmnxOamLspTrCtlNhIntfName, tmnxOamLspTrCtlPathDestType, and
             tmnxOamLspTrCtlPathDest, as follows:
             a) all unspecified
             b) tmnxOamLspTrCtlPathDestType and tmnxOamLspTrCtlPathDest
             c) tmnxOamLspTrCtlPathDestType, tmnxOamLspTrCtlPathDest, and
                tmnxOamLspTrCtlNhIntfName
             d) tmnxOamLspTrCtlPathDestType, tmnxOamLspTrCtlPathDest,
                tmnxOamLspTrCtlNhAddressType, and tmnxOamLspTrCtlNhAddress

         When an object combination other than a combination listed above is
         specified, values will be rejected or ignored, or the test will fail."
    REFERENCE
        "IETF draft-ietf-mpls-spring-lsp-ping-00, 'Label Switched Path (LSP)
         Ping/Trace for Segment Routing Networks Using MPLS Dataplane'.
         RFC 4379, 'Detecting Multi-Protocol Label Switched (MPLS) Data Plane
         Failures'.
         RFC 6426, 'MPLS On-Demand Connectivity Verification and Route Tracing'"
    ::= { tmnxOamTraceRouteObjs 9 }

tmnxOamLspTrCtlEntry             OBJECT-TYPE
    SYNTAX      TmnxOamLspTrCtlEntry
    MAX-ACCESS  not-accessible
    STATUS      current
    DESCRIPTION
        "The system creates a row in tmnxOamLspTrCtlTable when a row is created
         in tmnxOamTrCtlTable with tmnxOamTrCtlTestMode set to 'lspTraceRoute'.

         The system deletes a row in tmnxOamLspTrCtlTable when the
         corresponding row in tmnxOamTrCtlTable is deleted."
    INDEX       {
        tmnxOamTrCtlOwnerIndex,
        tmnxOamTrCtlTestIndex
    }
    ::= { tmnxOamLspTrCtlTable 1 }

TmnxOamLspTrCtlEntry             ::= SEQUENCE
{
    tmnxOamLspTrCtlVRtrID            TmnxVRtrID,
    tmnxOamLspTrCtlLspName           TLNamedItemOrEmpty,
    tmnxOamLspTrCtlPathName          TNamedItemOrEmpty,
    tmnxOamLspTrCtlLdpIpPrefix       IpAddress,
    tmnxOamLspTrCtlLdpIpPrefixLen    IpAddressPrefixLength,
    tmnxOamLspTrCtlLdpPrefixType     InetAddressType,
    tmnxOamLspTrCtlLdpPrefix         InetAddress,
    tmnxOamLspTrCtlLdpPrefixLen      InetAddressPrefixLength,
    tmnxOamLspTrCtlPathDestType      InetAddressType,
    tmnxOamLspTrCtlPathDest          InetAddress,
    tmnxOamLspTrCtlNhIntfName        TNamedItemOrEmpty,
    tmnxOamLspTrCtlNhAddressType     InetAddressType,
    tmnxOamLspTrCtlNhAddress         InetAddress,
    tmnxOamLspTrCtlDownstreamMapTlv  TmnxOamMplsEchoDownMapTlvOrNone,
    tmnxOamLspTrCtlTestSubMode       TmnxOamLspTestSubMode,
    tmnxOamLspTrCtlMplsTpPathType    TmnxOamMplsTpPathType,
    tmnxOamLspTrCtlAssocChannel      TmnxOamLspAssocChannel,
    tmnxOamLspTrCtlForce             TruthValue,
    tmnxOamLspTrCtlIgpInstance       TmnxIgpInstance
}

tmnxOamLspTrCtlVRtrID            OBJECT-TYPE
    SYNTAX      TmnxVRtrID
    MAX-ACCESS  read-create
    STATUS      obsolete
    DESCRIPTION
        "tmnxOamLspTrCtlVRtrID was obsoleted in release 6.0R15 and replaced
         with tmnxOamTrCtlVRtrID in tmnxOamTrCtlTable."
    DEFVAL      { 1 }
    ::= { tmnxOamLspTrCtlEntry 1 }

tmnxOamLspTrCtlLspName           OBJECT-TYPE
    SYNTAX      TLNamedItemOrEmpty
    MAX-ACCESS  read-create
    STATUS      current
    DESCRIPTION
        "The value of tmnxOamLspTrCtlLspName specifies the name of the LSP for
         this LSP trace route test.

         When the test is started, if this name is not empty, there must be a
         TIMETRA-MPLS-MIB::vRtrMplsLspTable row with:
         1.  tmnxOamLspTrCtlLspName equal to
             TIMETRA-MPLS-MIB::vRtrMplsLspName, AND
         2.  TIMETRA-VRTR-MIB::vRtrID equal to 1, AND
         3.  TIMETRA-MPLS-MIB::vRtrMplsLspType equal to 'dynamic(2)',
             'bypassOnly(4)', or 'mplsTp(7)'.
         Otherwise, the test will fail.

         The supported object combinations for LSP trace route tests are listed
         in the tmnxOamLspTrCtlTable DESCRIPTION clause."
    DEFVAL      { ''H }
    ::= { tmnxOamLspTrCtlEntry 2 }

tmnxOamLspTrCtlPathName          OBJECT-TYPE
    SYNTAX      TNamedItemOrEmpty
    MAX-ACCESS  read-create
    STATUS      current
    DESCRIPTION
        "The value of tmnxOamLspTrCtlPathName specifies the name of the Path
         (LSP) for this LSP trace route test.

         When the test is started, if this name is not empty, there must be a
         matching name in the column MPLS-TE-MIB::mplsTunnelName.  Otherwise,
         the test will fail.

         The supported object combinations for LSP trace route tests are listed
         in the tmnxOamLspTrCtlTable DESCRIPTION clause."
    DEFVAL      { ''H }
    ::= { tmnxOamLspTrCtlEntry 3 }

tmnxOamLspTrCtlLdpIpPrefix       OBJECT-TYPE
    SYNTAX      IpAddress
    MAX-ACCESS  read-create
    STATUS      obsolete
    DESCRIPTION
        "tmnxOamLspTrCtlLdpIpPrefix was obsoleted in release 4.0 and replaced
         with InetAddress objects tmnxOamLspTrCtlLdpPrefixType and
         tmnxOamLspTrCtlLdpPrefix."
    DEFVAL      { '00000000'H }
    ::= { tmnxOamLspTrCtlEntry 4 }

tmnxOamLspTrCtlLdpIpPrefixLen    OBJECT-TYPE
    SYNTAX      IpAddressPrefixLength
    MAX-ACCESS  read-create
    STATUS      obsolete
    DESCRIPTION
        "tmnxOamLspTrCtlLdpIpPrefixLen was obsoleted in release 4.0 and
         replaced with InetAddress object tmnxOamLspTrCtlLdpPrefixLen."
    DEFVAL      { 32 }
    ::= { tmnxOamLspTrCtlEntry 5 }

tmnxOamLspTrCtlLdpPrefixType     OBJECT-TYPE
    SYNTAX      InetAddressType
    MAX-ACCESS  read-create
    STATUS      current
    DESCRIPTION
        "The value of tmnxOamLspTrCtlLdpPrefixType specifies the type of
         Internet address stored in tmnxOamLspTrCtlLdpPrefix.

         The supported object combinations for LSP trace route tests are listed
         in the tmnxOamLspTrCtlTable DESCRIPTION clause."
    DEFVAL      { unknown }
    ::= { tmnxOamLspTrCtlEntry 6 }

tmnxOamLspTrCtlLdpPrefix         OBJECT-TYPE
    SYNTAX      InetAddress (SIZE (0|4|16))
    MAX-ACCESS  read-create
    STATUS      current
    DESCRIPTION
        "The value of tmnxOamLspTrCtlLdpPrefix, along with
         tmnxOamLspTrCtlLdpPrefixType and tmnxOamLspTrCtlLdpPrefixLen,
         specifies the destination prefix for this LSP trace route test.

         The supported object combinations for LSP trace route tests are listed
         in the tmnxOamLspTrCtlTable DESCRIPTION clause."
    DEFVAL      { ''H }
    ::= { tmnxOamLspTrCtlEntry 7 }

tmnxOamLspTrCtlLdpPrefixLen      OBJECT-TYPE
    SYNTAX      InetAddressPrefixLength
    UNITS       "bits"
    MAX-ACCESS  read-create
    STATUS      current
    DESCRIPTION
        "The value of tmnxOamLspTrCtlLdpPrefixLen specifies the Internet
         address prefix length of tmnxOamLspTrCtlLdpPrefix.

         The supported object combinations for LSP trace route tests are listed
         in the tmnxOamLspTrCtlTable DESCRIPTION clause."
    DEFVAL      { 32 }
    ::= { tmnxOamLspTrCtlEntry 8 }

tmnxOamLspTrCtlPathDestType      OBJECT-TYPE
    SYNTAX      InetAddressType
    MAX-ACCESS  read-create
    STATUS      current
    DESCRIPTION
        "The value of tmnxOamLspTrCtlPathDestType specifies the type of
         Internet address stored in tmnxOamLspTrCtlPathDest.

         The supported object combinations for LSP trace route tests are listed
         in the tmnxOamLspTrCtlTable DESCRIPTION clause."
    DEFVAL      { unknown }
    ::= { tmnxOamLspTrCtlEntry 9 }

tmnxOamLspTrCtlPathDest          OBJECT-TYPE
    SYNTAX      InetAddress (SIZE (0|4|16))
    MAX-ACCESS  read-create
    STATUS      current
    DESCRIPTION
        "The value of tmnxOamLspTrCtlPathDest specifies a unique path in a
         multipath setup for this OAM LSP trace route to traverse.  This
         address is used as part of a hash key to select the appropriate ECMP to
         the destination.

         The supported object combinations for LSP trace route tests are listed
         in the tmnxOamLspTrCtlTable DESCRIPTION clause."
    DEFVAL      { ''H }
    ::= { tmnxOamLspTrCtlEntry 10 }

tmnxOamLspTrCtlNhIntfName        OBJECT-TYPE
    SYNTAX      TNamedItemOrEmpty
    MAX-ACCESS  read-create
    STATUS      current
    DESCRIPTION
        "The value of tmnxOamLspTrCtlNhIntfName specifies the name of the next
         hop interface to be used when launching the LSP trace route test.

         When the test is started, if this name is not empty, there must be a
         TIMETRA-VRTR-MIB::vRtrIfTable row with:
         1.  tmnxOamLspTrCtlNhIntfName equal to TIMETRA-VRTR-MIB::vRtrIfName,
             AND
         2.  TIMETRA-VRTR-MIB::vRtrID equal to 1.
         Otherwise, the test will fail.

         The supported object combinations for LSP trace route tests are listed
         in the tmnxOamLspTrCtlTable DESCRIPTION clause."
    DEFVAL      { ''H }
    ::= { tmnxOamLspTrCtlEntry 11 }

tmnxOamLspTrCtlNhAddressType     OBJECT-TYPE
    SYNTAX      InetAddressType
    MAX-ACCESS  read-create
    STATUS      current
    DESCRIPTION
        "The value of tmnxOamLspTrCtlNhAddressType specifies the type of
         Internet address stored in tmnxOamLspTrCtlNhAddress.

         The supported object combinations for LSP trace route tests are listed
         in the tmnxOamLspTrCtlTable DESCRIPTION clause."
    DEFVAL      { unknown }
    ::= { tmnxOamLspTrCtlEntry 12 }

tmnxOamLspTrCtlNhAddress         OBJECT-TYPE
    SYNTAX      InetAddress (SIZE (0|4|16))
    MAX-ACCESS  read-create
    STATUS      current
    DESCRIPTION
        "The value of tmnxOamLspTrCtlNhAddress specifies the interface address
         to the next hop which will be used to launch the LSP trace route test.

         The supported object combinations for LSP trace route tests are listed
         in the tmnxOamLspTrCtlTable DESCRIPTION clause."
    DEFVAL      { ''H }
    ::= { tmnxOamLspTrCtlEntry 13 }

tmnxOamLspTrCtlDownstreamMapTlv  OBJECT-TYPE
    SYNTAX      TmnxOamMplsEchoDownMapTlvOrNone
    MAX-ACCESS  read-create
    STATUS      current
    DESCRIPTION
        "The value of tmnxOamLspTrCtlDownstreamMapTlv specifies the type of
         downstream mapping TLV to insert in the MPLS echo request PDU when
         launching the test.

         When an LSP trace route test is created, the value of this object
         defaults to the value of the global configuration object
         tmnxOamMplsEchoDownstreamMapTlv.

         The supported object combinations for LSP trace route tests are listed
         in the tmnxOamLspTrCtlTable DESCRIPTION clause."
    ::= { tmnxOamLspTrCtlEntry 14 }

tmnxOamLspTrCtlTestSubMode       OBJECT-TYPE
    SYNTAX      TmnxOamLspTestSubMode
    MAX-ACCESS  read-create
    STATUS      current
    DESCRIPTION
        "The value of tmnxOamLspTrCtlTestSubMode specifies the type of LSP
         trace route test to perform.

         When this object is 'unspecified(1)', the type of LSP trace route test
         to be performed is determined when the test is started, from the set
         of tmnxOamLspTrCtlTable objects configured with non-default values.

         If there is a mismatch between tmnxOamLspTrCtlTestSubMode and the
         type of the LSP to be tested, the test will fail.  For example, if
         tmnxOamLspTrCtlTestSubMode is 'static(2)', and
         tmnxOamLspTrCtlLspName refers to an LSP with
         TIMETRA-MPLS-MIB::vRtrMplsLspType not equal to 'mplsTp(7)', the test
         will fail.

         The supported object combinations for LSP trace route tests are listed
         in the tmnxOamLspTrCtlTable DESCRIPTION clause."
    DEFVAL      { unspecified }
    ::= { tmnxOamLspTrCtlEntry 15 }

tmnxOamLspTrCtlMplsTpPathType    OBJECT-TYPE
    SYNTAX      TmnxOamMplsTpPathType
    MAX-ACCESS  read-create
    STATUS      current
    DESCRIPTION
        "The value of tmnxOamLspTrCtlMplsTpPathType specifies the type of the
         MPLS-TP path to be tested.

         The supported object combinations for LSP trace route tests are listed
         in the tmnxOamLspTrCtlTable DESCRIPTION clause."
    DEFVAL      { active }
    ::= { tmnxOamLspTrCtlEntry 16 }

tmnxOamLspTrCtlAssocChannel      OBJECT-TYPE
    SYNTAX      TmnxOamLspAssocChannel
    MAX-ACCESS  read-create
    STATUS      current
    DESCRIPTION
        "The value of tmnxOamLspTrCtlAssocChannel specifies the launched echo
         request's usage of the Associated Channel (ACH) mechanism, when
         testing an MPLS-TP LSP.

         When tmnxOamLspTrCtlTestSubMode is 'static(2)', the default value for
         tmnxOamLspTrCtlAssocChannel is 'nonIp(2)'.

         The supported object combinations for LSP trace route tests are listed
         in the tmnxOamLspTrCtlTable DESCRIPTION clause."
    DEFVAL      { notApplicable }
    ::= { tmnxOamLspTrCtlEntry 17 }

tmnxOamLspTrCtlForce             OBJECT-TYPE
    SYNTAX      TruthValue
    MAX-ACCESS  read-create
    STATUS      current
    DESCRIPTION
        "The value of tmnxOamLspTrCtlForce specifies whether or not to force
         the transmission of the 'lspTraceRoute' request PDU(s).

         If tmnxOamLspTrCtlForce is 'true(1)', the test will proceed and
         request PDU(s) will be sent regardless of the local operational status
         of the tested LSP path.

         If tmnxOamLspTrCtlForce is 'false(2)',  the test will fail
         immediately when the local operational status of the tested LSP path is
         down.

         The supported object combinations for LSP trace route tests are listed
         in the tmnxOamLspTrCtlTable DESCRIPTION clause."
    DEFVAL      { false }
    ::= { tmnxOamLspTrCtlEntry 18 }

tmnxOamLspTrCtlIgpInstance       OBJECT-TYPE
    SYNTAX      TmnxIgpInstance
    MAX-ACCESS  read-create
    STATUS      current
    DESCRIPTION
        "The value of tmnxOamLspTrCtlIgpInstance specifies the Interior Gateway
         Protocol (IGP) instance to be used for the test.

         The supported object combinations for LSP trace route tests are listed
         in the tmnxOamLspTrCtlTable DESCRIPTION clause."
    DEFVAL      { 0 }
    ::= { tmnxOamLspTrCtlEntry 19 }

tmnxOamLspTrMapTable             OBJECT-TYPE
    SYNTAX      SEQUENCE OF TmnxOamLspTrMapEntry
    MAX-ACCESS  not-accessible
    STATUS      current
    DESCRIPTION
        "tmnxOamLspTrMapTable contains the information obtained from RFC 4379
         Downstream Mapping TLVs and/or RFC 6424 Downstream Detailed Mapping
         TLVs within reply PDUs for active 'lspTraceRoute' tests."
    REFERENCE
        "RFC 4379, 'Detecting Multi-Protocol Label Switched (MPLS) Data Plane
         Failures', Section 3.3, 'Downstream Mapping'.
         RFC 6426, 'MPLS On-Demand Connectivity Verification and Route Tracing',
         Section 3.3, 'Downstream Detailed Mapping TLV'."
    ::= { tmnxOamTraceRouteObjs 10 }

tmnxOamLspTrMapEntry             OBJECT-TYPE
    SYNTAX      TmnxOamLspTrMapEntry
    MAX-ACCESS  not-accessible
    STATUS      current
    DESCRIPTION
        "tmnxOamLspTrMapEntry contains the information obtained from one RFC
         4379 Downstream Mapping TLV (or one RFC 6424 Downstream Detailed
         Mapping TLV) within one 'lspTraceRoute' reply PDU.

         The first six indices specify an 'lspTraceRoute' reply PDU.  The
         seventh index specifies one Downstream [Detailed] Mapping TLV within
         the PDU.

         Rows are created when a managed 'lspTraceRoute' reply PDU arrives
         containing one or more Downstream [Detailed] Mapping TLVs.

         Rows are deleted when the parent tmnxOamTrProbeHistoryTable row is
         deleted."
    REFERENCE
        "RFC 4379, 'Detecting Multi-Protocol Label Switched (MPLS) Data Plane
         Failures', Section 3.3, 'Downstream Mapping'.
         RFC 6426, 'MPLS On-Demand Connectivity Verification and Route Tracing',
         Section 3.3, 'Downstream Detailed Mapping TLV'."
    INDEX       {
        tmnxOamTrCtlOwnerIndex,
        tmnxOamTrCtlTestIndex,
        tmnxOamTrResultsTestRunIndex,
        tmnxOamTrProbeHistoryIndex,
        tmnxOamTrProbeHistoryHopIndex,
        tmnxOamTrProbeHistoryProbeIndex,
        tmnxOamLspTrMapIndex
    }
    ::= { tmnxOamLspTrMapTable 1 }

TmnxOamLspTrMapEntry             ::= SEQUENCE
{
    tmnxOamLspTrMapIndex             Unsigned32,
    tmnxOamLspTrMapDSIPv4Addr        IpAddress,
    tmnxOamLspTrMapAddrType          TmnxOamAddressType,
    tmnxOamLspTrMapDSIfAddr          Unsigned32,
    tmnxOamLspTrMapMTU               Unsigned32,
    tmnxOamLspTrMapDSIndex           Unsigned32,
    tmnxOamLspTrMapDsEgrIfNum        Unsigned32,
    tmnxOamLspTrMapDsIngIfNum        Unsigned32,
    tmnxOamLspTrMapDsIpAddressType   InetAddressType,
    tmnxOamLspTrMapDsIpAddress       InetAddress,
    tmnxOamLspTrMapDsIfAddressType   InetAddressType,
    tmnxOamLspTrMapDsIfAddress       InetAddress
}

tmnxOamLspTrMapIndex             OBJECT-TYPE
    SYNTAX      Unsigned32 (1..4294967295)
    MAX-ACCESS  not-accessible
    STATUS      current
    DESCRIPTION
        "The value of tmnxOamLspTrMapIndex specifies one RFC 4379 Downstream
         Mapping TLV (or one RFC 6424 Downstream Detailed Mapping TLV) within
         the reply PDU specified by the other indices.

         The agent starts assigning tmnxOamLspTrMapIndex values at 1."
    REFERENCE
        "RFC 4379, 'Detecting Multi-Protocol Label Switched (MPLS) Data Plane
         Failures', Section 3.3, 'Downstream Mapping'.
         RFC 6426, 'MPLS On-Demand Connectivity Verification and Route Tracing',
         Section 3.3, 'Downstream Detailed Mapping TLV'."
    ::= { tmnxOamLspTrMapEntry 1 }

tmnxOamLspTrMapDSIPv4Addr        OBJECT-TYPE
    SYNTAX      IpAddress
    MAX-ACCESS  read-only
    STATUS      obsolete
    DESCRIPTION
        "The value of tmnxOamLspTrMapDSIPv4Addr indicates the IPv4 address
         of the downstream LSR that this entry in the tmnxOamLspTrMapTable
         describes.  If the interface to the downstream LSR is numbered,
         then the tmnxOamLspTrMapDSIPv4Addr can either be the downstream
         LSR's Router ID or the interface address of the downstream LSR.

         If the interface to the downstream LSR is unnumbered, the value of
         tmnxOamLspTrMapDSIPv4Addr indicates the downstream LSR's Router ID.

         This object was marked obsolete in release 13.0 R1."
    ::= { tmnxOamLspTrMapEntry 2 }

tmnxOamLspTrMapAddrType          OBJECT-TYPE
    SYNTAX      TmnxOamAddressType
    MAX-ACCESS  read-only
    STATUS      current
    DESCRIPTION
        "The value of tmnxOamLspTrMapAddrType indicates the type of addressing
         used on the replying interface.  The value is copied from the Address
         Type field of the specified RFC 4379 Downstream Mapping TLV (or RFC
         6424 Downstream Detailed Mapping TLV), and then mapped from the RFC
         code point number to the SROS code point number.

         The supported SROS code points are listed in the following table.

         Code Point            Definition
         -------------------   ----------
         'ipv4Address   (1)'     RFC 4379
         'ipv4Unnumbered(7)'     RFC 4379
         'ipv6Address   (2)'     RFC 4379
         'ipv6Unnumbered(8)'     RFC 4379
         'nonIp        (10)'     RFC 6426

         The supported combinations of tmnxOamLspTrMapAddrType,
         tmnxOamLspTrMapDsEgrIfNum, tmnxOamLspTrMapDsIngIfNum,
         tmnxOamLspTrMapDsIpAddressType, and tmnxOamLspTrMapDsIfAddressType are
         listed in the following table.

         _AddrType          _EgrIfNum  _IngIfNum  _IpAddressType  _IfAddressType
         ----------------   ---------  ---------  --------------  --------------
         'ipv4Address'           zero       zero          'ipv4'          'ipv4'
         'ipv4Unnumbered'        zero   positive          'ipv4'       'unknown'
         'ipv6Address'           zero       zero          'ipv6'          'ipv6'
         'ipv6Unnumbered'        zero   positive          'ipv6'       'unknown'
         'nonIp'             positive   positive       'unknown'       'unknown'

         In the table above, zero is the null interface number."
    REFERENCE
        "RFC 4379, 'Detecting Multi-Protocol Label Switched (MPLS) Data Plane
         Failures', Section 3.3, 'Downstream Mapping'.
         RFC 6426, 'MPLS On-Demand Connectivity Verification and Route Tracing',
         Section 2.1, 'New Address Type for Downstream Mapping TLV'.
         RFC 6426, 'MPLS On-Demand Connectivity Verification and Route Tracing',
         Section 3.3, 'Downstream Detailed Mapping TLV'."
    ::= { tmnxOamLspTrMapEntry 3 }

tmnxOamLspTrMapDSIfAddr          OBJECT-TYPE
    SYNTAX      Unsigned32
    MAX-ACCESS  read-only
    STATUS      obsolete
    DESCRIPTION
        "When tmnxOamLspTrMapAddrType has a value of 'ipv4Address'
         tmnxOamLspTrMapDSIfAddr indicates the downstream LSR's
         interface address.  When tmnxOamLspTrMapAddrType has a value
         of 'unnumbered', tmnxOamLspTrMapDSIfAddr indicates the index
         assigned by the upstream LSR to the interface.

         This object was marked obsolete in release 13.0 R1."
    ::= { tmnxOamLspTrMapEntry 4 }

tmnxOamLspTrMapMTU               OBJECT-TYPE
    SYNTAX      Unsigned32 (0..65535)
    UNITS       "octets"
    MAX-ACCESS  read-only
    STATUS      current
    DESCRIPTION
        "The value of tmnxOamLspTrMapMTU indicates the largest MPLS frame
         (including the label stack) that fits on the interface to the
         downstream LSR (Label Switching Router).

         The value is copied from the MTU (Maximum Transmission Unit) field of
         the specified RFC 4379 Downstream Mapping TLV (or RFC 6424 Downstream
         Detailed Mapping TLV)."
    REFERENCE
        "RFC 4379, 'Detecting Multi-Protocol Label Switched (MPLS) Data Plane
         Failures', Section 3.3, 'Downstream Mapping'.
         RFC 6426, 'MPLS On-Demand Connectivity Verification and Route Tracing',
         Section 3.3, 'Downstream Detailed Mapping TLV'."
    ::= { tmnxOamLspTrMapEntry 5 }

tmnxOamLspTrMapDSIndex           OBJECT-TYPE
    SYNTAX      Unsigned32 (0..255)
    MAX-ACCESS  read-only
    STATUS      obsolete
    DESCRIPTION
        "The value of tmnxOamLspTrMapDSIndex indicates the unique index
         assigned to the pair of downstream router and interface addresses
         represented by this row in the tmnxOamLspTrMapTable.

         tmnxOamLspTrMapDSIndex was made obsolete in release 5.0."
    ::= { tmnxOamLspTrMapEntry 6 }

tmnxOamLspTrMapDsEgrIfNum        OBJECT-TYPE
    SYNTAX      Unsigned32
    MAX-ACCESS  read-only
    STATUS      current
    DESCRIPTION
        "The value of tmnxOamLspTrMapDsEgrIfNum indicates the egress interface
         number reported by the replying node.  This value is copied from the
         Downstream IP Address field of the specified RFC 4379 Downstream
         Mapping TLV (or the Downstream Address field of the specified RFC 6424
         Downstream Detailed Mapping TLV).  See the DESCRIPTION clause of
         tmnxOamLspTrMapAddrType for more information."
    REFERENCE
        "RFC 4379, 'Detecting Multi-Protocol Label Switched (MPLS) Data Plane
         Failures', Section 3.3, 'Downstream Mapping'.
         RFC 6426, 'MPLS On-Demand Connectivity Verification and Route Tracing',
         Section 3.3, 'Downstream Detailed Mapping TLV'."
    ::= { tmnxOamLspTrMapEntry 7 }

tmnxOamLspTrMapDsIngIfNum        OBJECT-TYPE
    SYNTAX      Unsigned32
    MAX-ACCESS  read-only
    STATUS      current
    DESCRIPTION
        "The value of tmnxOamLspTrMapDsIngIfNum indicates the ingress interface
         number reported by the replying node.  This value is copied from the
         Downstream Interface Address field of the specified RFC 4379 Downstream
         Mapping TLV (or RFC 6424 Downstream Detailed Mapping TLV).  See the
         DESCRIPTION clause of tmnxOamLspTrMapAddrType for more information."
    REFERENCE
        "RFC 4379, 'Detecting Multi-Protocol Label Switched (MPLS) Data Plane
         Failures', Section 3.3, 'Downstream Mapping'.
         RFC 6426, 'MPLS On-Demand Connectivity Verification and Route Tracing',
         Section 3.3, 'Downstream Detailed Mapping TLV'."
    ::= { tmnxOamLspTrMapEntry 8 }

tmnxOamLspTrMapDsIpAddressType   OBJECT-TYPE
    SYNTAX      InetAddressType
    MAX-ACCESS  read-only
    STATUS      current
    DESCRIPTION
        "The value of tmnxOamLspTrMapDsIpAddressType indicates the type of
         address in tmnxOamLspTrMapDsIpAddress.  See the DESCRIPTION clause of
         tmnxOamLspTrMapAddrType for more information."
    ::= { tmnxOamLspTrMapEntry 9 }

tmnxOamLspTrMapDsIpAddress       OBJECT-TYPE
    SYNTAX      InetAddress (SIZE (0|4|16))
    MAX-ACCESS  read-only
    STATUS      current
    DESCRIPTION
        "The value of tmnxOamLspTrMapDsIpAddress indicates the Downstream IP
         Address field in the specified RFC 4379 Downstream Mapping TLV (or the
         Downstream Address field in the specified RFC 6424 Downstream Detailed
         Mapping TLV)."
    REFERENCE
        "RFC 4379, 'Detecting Multi-Protocol Label Switched (MPLS) Data Plane
         Failures', Section 3.3, 'Downstream Mapping'.
         RFC 6426, 'MPLS On-Demand Connectivity Verification and Route Tracing',
         Section 3.3, 'Downstream Detailed Mapping TLV'."
    ::= { tmnxOamLspTrMapEntry 10 }

tmnxOamLspTrMapDsIfAddressType   OBJECT-TYPE
    SYNTAX      InetAddressType
    MAX-ACCESS  read-only
    STATUS      current
    DESCRIPTION
        "The value of tmnxOamLspTrMapDsIfAddressType indicates the type of
         address in tmnxOamLspTrMapDsIfAddress.  See the DESCRIPTION clause of
         tmnxOamLspTrMapAddrType for more information."
    ::= { tmnxOamLspTrMapEntry 11 }

tmnxOamLspTrMapDsIfAddress       OBJECT-TYPE
    SYNTAX      InetAddress (SIZE (0|4|16))
    MAX-ACCESS  read-only
    STATUS      current
    DESCRIPTION
        "The value of tmnxOamLspTrMapDsIfAddress indicates the Downstream
         Interface Address field in the specified RFC 4379 Downstream Mapping
         TLV (or RFC 6424 Downstream Detailed Mapping TLV)."
    REFERENCE
        "RFC 4379, 'Detecting Multi-Protocol Label Switched (MPLS) Data Plane
         Failures', Section 3.3, 'Downstream Mapping'.
         RFC 6426, 'MPLS On-Demand Connectivity Verification and Route Tracing',
         Section 3.3, 'Downstream Detailed Mapping TLV'."
    ::= { tmnxOamLspTrMapEntry 12 }

tmnxOamVprnTrCtlTable            OBJECT-TYPE
    SYNTAX      SEQUENCE OF TmnxOamVprnTrCtlEntry
    MAX-ACCESS  not-accessible
    STATUS      current
    DESCRIPTION
        "Defines the Nokia SROS OAM VPRN Trace Route Control Table for
         providing, via SNMP, the capability of performing Nokia SROS
         OAM 'vprnTraceRoute' test operations.  The results of these tests
         are stored in the tmnxOamTrResultsTable, the
         tmnxOamTrProbeHistoryTable, the tmnxOamVprnTrRTTable and the
         tmnxOamVprnTrNextHopTable."
    ::= { tmnxOamTraceRouteObjs 11 }

tmnxOamVprnTrCtlEntry            OBJECT-TYPE
    SYNTAX      TmnxOamVprnTrCtlEntry
    MAX-ACCESS  not-accessible
    STATUS      current
    DESCRIPTION
        "Defines an entry in the tmnxOamVprnTrCtlTable.  The first index
         element, tmnxOamTrCtlOwnerIndex, is of type SnmpAdminString,
         a textual convention that allows for use of the SNMPv3
         View-Based Access Control Model (RFC 2575 [11], VACM)
         and allows a management application to identify its entries.
         The second index, tmnxOamTrCtlTestIndex, enables the same
         management application to have multiple outstanding requests."
    INDEX       {
        tmnxOamTrCtlOwnerIndex,
        tmnxOamTrCtlTestIndex
    }
    ::= { tmnxOamVprnTrCtlTable 1 }

TmnxOamVprnTrCtlEntry            ::= SEQUENCE
{
    tmnxOamVprnTrCtlSourceIpAddr     IpAddress,
    tmnxOamVprnTrCtlReplyControl     TruthValue,
    tmnxOamVprnTrCtlSrcAddrType      InetAddressType,
    tmnxOamVprnTrCtlSrcAddress       InetAddress
}

tmnxOamVprnTrCtlSourceIpAddr     OBJECT-TYPE
    SYNTAX      IpAddress
    MAX-ACCESS  read-create
    STATUS      obsolete
    DESCRIPTION
        "Specifies the IPv4 address to be used as the source for
         performing an OAM 'vprnTraceRoute' operation when tmnxOamTrCtlTestMode
         has a value of 'vprnTraceRoute'.   This parameter is required.

         This object was obsoleted in release 4.0 and replaced with InetAddress
         objects tmnxOamVprnTrCtlSrcAddrType and tmnxOamVprnTrCtlSrcAddress."
    DEFVAL      { '00000000'h }
    ::= { tmnxOamVprnTrCtlEntry 1 }

tmnxOamVprnTrCtlReplyControl     OBJECT-TYPE
    SYNTAX      TruthValue
    MAX-ACCESS  read-create
    STATUS      current
    DESCRIPTION
        "When the value of tmnxOamVprnTrCtlReplyControl is 'true', the OAM
         'vprnTraceRoute' response is returned using the control plane. If its
         value is 'false', the packet is sent via the data plane.

         This object is optional and is not relevant when tmnxOamTrCtlTestMode
         has a value other than 'vprnTraceRoute'."
    DEFVAL      { false }
    ::= { tmnxOamVprnTrCtlEntry 2 }

tmnxOamVprnTrCtlSrcAddrType      OBJECT-TYPE
    SYNTAX      InetAddressType
    MAX-ACCESS  read-create
    STATUS      current
    DESCRIPTION
        "The value of tmnxOamVprnTrCtlSrcAddrType specifies the type of
         Internet address stored in tmnxOamVprnTrCtlSrcAddress."
    DEFVAL      { unknown }
    ::= { tmnxOamVprnTrCtlEntry 3 }

tmnxOamVprnTrCtlSrcAddress       OBJECT-TYPE
    SYNTAX      InetAddress (SIZE (0|4|16))
    MAX-ACCESS  read-create
    STATUS      current
    DESCRIPTION
        "The value of tmnxOamVprnTrCtlSrcAddress specifies the Internet
         address to be used as the source for performing an OAM
         'vprnTraceRoute' operation when tmnxOamTrCtlTestMode has a value of
         'vprnTraceRoute'.  This parameter is required."
    DEFVAL      { ''H }
    ::= { tmnxOamVprnTrCtlEntry 4 }

tmnxOamVprnTrL3MapTable          OBJECT-TYPE
    SYNTAX      SEQUENCE OF TmnxOamVprnTrL3MapEntry
    MAX-ACCESS  not-accessible
    STATUS      current
    DESCRIPTION
        "Defines a table for storing the results of an OAM 'vprnTraceRoute'
         probe operation.  The number of entries for a test in this table
         is limited to the results of 3 runs.

         An entry in this table is created when the result of an OAM
         'vprnTraceRoute' probe is determined.  An entry is removed from
         this table when its corresponding tmnxOamTrCtlEntry is deleted."
    ::= { tmnxOamTraceRouteObjs 12 }

tmnxOamVprnTrL3MapEntry          OBJECT-TYPE
    SYNTAX      TmnxOamVprnTrL3MapEntry
    MAX-ACCESS  not-accessible
    STATUS      current
    DESCRIPTION
        "Defines an entry in the tmnxOamVprnTrL3MapTable.  The first
         two index elements identify the tmnxOamTrCtlEntry that a
         tmnxOamVprnTrL3MapEntry belongs to.  The third index element
         identifies an OAM trace route test run.  The fourth index element
         selects a single Nokia SROS OAM 'vprnTraceRoute' operation
         result.  The fifth and sixth indexes select the hop and the
         probe at that hop for a particular Nokia SROS OAM
         'vprnTraceRoute' operation.  The seventh index selects either the
         requestor's or responder's L3 route information."
    INDEX       {
        tmnxOamTrCtlOwnerIndex,
        tmnxOamTrCtlTestIndex,
        tmnxOamTrResultsTestRunIndex,
        tmnxOamTrProbeHistoryIndex,
        tmnxOamTrProbeHistoryHopIndex,
        tmnxOamTrProbeHistoryProbeIndex,
        tmnxOamVprnTrL3MapReporter
    }
    ::= { tmnxOamVprnTrL3MapTable 1 }

TmnxOamVprnTrL3MapEntry          ::= SEQUENCE
{
    tmnxOamVprnTrL3MapReporter       INTEGER,
    tmnxOamVprnTrL3MapRouterID       RouterID,
    tmnxOamVprnTrL3MapRteDestAddr    IpAddress,
    tmnxOamVprnTrL3MapRteDestMask    Unsigned32,
    tmnxOamVprnTrL3MapRteVprnLabel   MplsLabel,
    tmnxOamVprnTrL3MapRteMetrics     Unsigned32,
    tmnxOamVprnTrL3MapRteLastUp      DateAndTime,
    tmnxOamVprnTrL3MapRteOwner       INTEGER,
    tmnxOamVprnTrL3MapRtePref        Unsigned32,
    tmnxOamVprnTrL3MapRteDist        TmnxVPNRouteDistinguisher,
    tmnxOamVprnTrL3MapNumNextHops    Unsigned32,
    tmnxOamVprnTrL3MapNumRteTargets  Unsigned32,
    tmnxOamVprnTrL3MapDestAddrType   InetAddressType,
    tmnxOamVprnTrL3MapDestAddress    InetAddress,
    tmnxOamVprnTrL3MapDestMaskLen    InetAddressPrefixLength
}

tmnxOamVprnTrL3MapReporter       OBJECT-TYPE
    SYNTAX      INTEGER {
        requestor (1),
        responder (2)
    }
    MAX-ACCESS  not-accessible
    STATUS      current
    DESCRIPTION
        "The value of tmnxOamVprnTrL3MapReporter specifies who reported
         the route information in this row entry.  It may have come from
         the 'vprnTraceRoute' requestor's local information or it may be
         from the remote 'vprnTraceRoute' responder."
    ::= { tmnxOamVprnTrL3MapEntry 1 }

tmnxOamVprnTrL3MapRouterID       OBJECT-TYPE
    SYNTAX      RouterID
    MAX-ACCESS  read-only
    STATUS      current
    DESCRIPTION
        "The value of tmnxOamVprnTrL3MapRouterID indicates the router ID of the
         node, requestor or responder, that provided this route information."
    ::= { tmnxOamVprnTrL3MapEntry 2 }

tmnxOamVprnTrL3MapRteDestAddr    OBJECT-TYPE
    SYNTAX      IpAddress
    MAX-ACCESS  read-only
    STATUS      obsolete
    DESCRIPTION
        "The value of tmnxOamVprnTrL3MapRteDestAddr indicates the IP
         address to be advertised for the route information returned by
         this 'vprnTraceRoute' reply.  When used together with the values
         in tmnxOamVprnTrL3MapRteDestMask and tmnxOamVprnTrL3MapRteVprnLabel
         a customer route can be identified.

         This object was obsoleted in release 4.0 and replaced with InetAddress
         objects tmnxOamVprnTrL3MapDestAddrType and
         tmnxOamVprnTrL3MapDestAddrType."
    ::= { tmnxOamVprnTrL3MapEntry 3 }

tmnxOamVprnTrL3MapRteDestMask    OBJECT-TYPE
    SYNTAX      Unsigned32
    MAX-ACCESS  read-only
    STATUS      obsolete
    DESCRIPTION
        "The value of tmnxOamVprnTrL3MapRteDestMask indicates the number of
         prefix bits (prefix width) to be &-ed with IP address in
         tmnxOamVprnTrL3MapRteDestAddr.

         This object was obsoleted in release 4.0 and replaced with InetAddress
         object tmnxOamVprnTrL3MapDestMaskLen."
    ::= { tmnxOamVprnTrL3MapEntry 4 }

tmnxOamVprnTrL3MapRteVprnLabel   OBJECT-TYPE
    SYNTAX      MplsLabel
    MAX-ACCESS  read-only
    STATUS      current
    DESCRIPTION
        "The value of tmnxOamVprnTrL3MapRteVprnLabel indicates the VPRN label
         associated with the route information returned in this
         'vprnTraceRoute' reply."
    ::= { tmnxOamVprnTrL3MapEntry 5 }

tmnxOamVprnTrL3MapRteMetrics     OBJECT-TYPE
    SYNTAX      Unsigned32
    MAX-ACCESS  read-only
    STATUS      current
    DESCRIPTION
        "The value of tmnxOamVprnTrL3MapRteMetrics indicates the metrics to be
         used with this vprnTraceRoute route."
    ::= { tmnxOamVprnTrL3MapEntry 6 }

tmnxOamVprnTrL3MapRteLastUp      OBJECT-TYPE
    SYNTAX      DateAndTime
    MAX-ACCESS  read-only
    STATUS      current
    DESCRIPTION
        "The value of tmnxOamVprnTrL3MapRteLastUp indicates the time this route
         was last added or modified by the protocol."
    ::= { tmnxOamVprnTrL3MapEntry 7 }

tmnxOamVprnTrL3MapRteOwner       OBJECT-TYPE
    SYNTAX      INTEGER {
        invalid   (0),
        local     (1),
        static    (2),
        rip       (3),
        ospf      (4),
        isis      (5),
        bgp       (6),
        bgpVpn    (7),
        ldp       (8),
        aggregate (9),
        any       (10)
    }
    MAX-ACCESS  read-only
    STATUS      current
    DESCRIPTION
        "The value of tmnxOamVprnTrL3MapRteOwner indicates the protocol
         that owns this route.  It may be a local or remote route."
    ::= { tmnxOamVprnTrL3MapEntry 8 }

tmnxOamVprnTrL3MapRtePref        OBJECT-TYPE
    SYNTAX      Unsigned32
    MAX-ACCESS  read-only
    STATUS      current
    DESCRIPTION
        "The value of tmnxOamVprnTrL3MapRtePref indicates the route preference
         value for this route."
    ::= { tmnxOamVprnTrL3MapEntry 9 }

tmnxOamVprnTrL3MapRteDist        OBJECT-TYPE
    SYNTAX      TmnxVPNRouteDistinguisher
    MAX-ACCESS  read-only
    STATUS      current
    DESCRIPTION
        "The value of tmnxOamVprnTrL3MapRteDist is the route distinguisher
         associated with the route information returned in this
         'vprnTraceRoute' reply."
    ::= { tmnxOamVprnTrL3MapEntry 10 }

tmnxOamVprnTrL3MapNumNextHops    OBJECT-TYPE
    SYNTAX      Unsigned32
    MAX-ACCESS  read-only
    STATUS      current
    DESCRIPTION
        "The value of tmnxOamVprnTrL3MapNumNextHops indicates the number of
         entries in the tmnxOamVprnTrNextHopTable for this route."
    ::= { tmnxOamVprnTrL3MapEntry 11 }

tmnxOamVprnTrL3MapNumRteTargets  OBJECT-TYPE
    SYNTAX      Unsigned32
    MAX-ACCESS  read-only
    STATUS      current
    DESCRIPTION
        "The value of tmnxOamVprnTrL3MapNumRteTargets indicates the number of
         entries in the tmnxOamVprnTrRTTable for this route."
    ::= { tmnxOamVprnTrL3MapEntry 12 }

tmnxOamVprnTrL3MapDestAddrType   OBJECT-TYPE
    SYNTAX      InetAddressType
    MAX-ACCESS  read-only
    STATUS      current
    DESCRIPTION
        "The value of tmnxOamVprnTrL3MapDestAddrType indicates the type of
         internet address stored in tmnxOamVprnTrL3MapDestAddress."
    ::= { tmnxOamVprnTrL3MapEntry 13 }

tmnxOamVprnTrL3MapDestAddress    OBJECT-TYPE
    SYNTAX      InetAddress (SIZE (0|4|16))
    MAX-ACCESS  read-only
    STATUS      current
    DESCRIPTION
        "The value of tmnxOamVprnTrL3MapDestAddress indicates the Internet
         address to be advertised for the route information returned by this
         'vprnTraceRoute' reply.  When used together with
         tmnxOamVprnTrL3MapDestMaskLen and tmnxOamVprnTrL3MapRteVprnLabel,
         a customer route can be identified."
    ::= { tmnxOamVprnTrL3MapEntry 14 }

tmnxOamVprnTrL3MapDestMaskLen    OBJECT-TYPE
    SYNTAX      InetAddressPrefixLength
    MAX-ACCESS  read-only
    STATUS      current
    DESCRIPTION
        "The value of tmnxOamVprnTrL3MapDestMaskLen indicates the number of
         prefix bits (prefix width) to be &-ed with the IP address in
         tmnxOamVprnTrL3MapDestAddress."
    ::= { tmnxOamVprnTrL3MapEntry 15 }

tmnxOamVprnTrNextHopTable        OBJECT-TYPE
    SYNTAX      SEQUENCE OF TmnxOamVprnTrNextHopEntry
    MAX-ACCESS  not-accessible
    STATUS      current
    DESCRIPTION
        "Defines a table for storing the results of an OAM 'vprnTraceRoute'
         probe operation where a L3 route next hop list is returned.

         An entry in this table is created when the result of an OAM
         'vprnTraceRoute' probe is determined. An entry is removed from this
         table when its corresponding tmnxOamTrCtlEntry is deleted."
    ::= { tmnxOamTraceRouteObjs 13 }

tmnxOamVprnTrNextHopEntry        OBJECT-TYPE
    SYNTAX      TmnxOamVprnTrNextHopEntry
    MAX-ACCESS  not-accessible
    STATUS      current
    DESCRIPTION
        "Defines an entry in the tmnxOamVprnTrNextHopTable.  The first two
         index elements identify the tmnxOamTrCtlEntry that a
         tmnxOamVprnTrNextHopEntry belongs to.  The third index element
         identifies an OAM trace route test run.  The fourth, fifth and sixth
         index elements select a single OAM 'vprnTraceRoute' reply.  The
         seventh index selects either the requestor's or responder's route
         information. The eighth index selects a single L3 next hop entry
         within a specific 'vprnTraceRoute' probe reply route information."
    INDEX       {
        tmnxOamTrCtlOwnerIndex,
        tmnxOamTrCtlTestIndex,
        tmnxOamTrResultsTestRunIndex,
        tmnxOamTrProbeHistoryIndex,
        tmnxOamTrProbeHistoryHopIndex,
        tmnxOamTrProbeHistoryProbeIndex,
        tmnxOamVprnTrL3MapReporter,
        tmnxOamVprnTrNextHopIndex
    }
    ::= { tmnxOamVprnTrNextHopTable 1 }

TmnxOamVprnTrNextHopEntry        ::= SEQUENCE
{
    tmnxOamVprnTrNextHopIndex        Unsigned32,
    tmnxOamVprnTrNextHopRtrID        RouterID,
    tmnxOamVprnTrNextHopType         INTEGER,
    tmnxOamVprnTrNextHopTunnelID     TmnxTunnelID,
    tmnxOamVprnTrNextHopTunnelType   TmnxTunnelType,
    tmnxOamVprnTrNextHopIfIndex      InterfaceIndex,
    tmnxOamVprnTrNextHopAddrType     InetAddressType,
    tmnxOamVprnTrNextHopAddress      InetAddress
}

tmnxOamVprnTrNextHopIndex        OBJECT-TYPE
    SYNTAX      Unsigned32 (1..4294967295)
    MAX-ACCESS  not-accessible
    STATUS      current
    DESCRIPTION
        "The tmnxOamVprnTrNextHopIndex selects a single L3 next hop entry
         associated with the router information returned within a specific
         'vprnTraceRoute' probe reply.

         The agent starts assigning tmnxOamVprnTrNextHopIndex values at 1."
    ::= { tmnxOamVprnTrNextHopEntry 1 }

tmnxOamVprnTrNextHopRtrID        OBJECT-TYPE
    SYNTAX      RouterID
    MAX-ACCESS  read-only
    STATUS      obsolete
    DESCRIPTION
        "The value of tmnxOamVprnTrNextHopRtrID is the router ID for this L3
         next hop entry.

         This object was obsoleted in release 6.0 and replaced with InetAddress
         objects tmnxOamVprnTrNextHopAddrType and tmnxOamVprnTrNextHopAddress."
    ::= { tmnxOamVprnTrNextHopEntry 2 }

tmnxOamVprnTrNextHopType         OBJECT-TYPE
    SYNTAX      INTEGER {
        local  (1),
        remote (2)
    }
    MAX-ACCESS  read-only
    STATUS      current
    DESCRIPTION
        "The value of tmnxOamVprnTrNextHopType indicates whether the route
         owner is a local route or a remote, BGP-VPRN, route."
    ::= { tmnxOamVprnTrNextHopEntry 3 }

tmnxOamVprnTrNextHopTunnelID     OBJECT-TYPE
    SYNTAX      TmnxTunnelID
    MAX-ACCESS  read-only
    STATUS      current
    DESCRIPTION
        "When the value of tmnxOamVprnTrNextHopType is 'remote' the value of
         tmnxOamVprnTrNextHopTunnelID indicates the tunnel ID used to reach
         this BGP next hop."
    ::= { tmnxOamVprnTrNextHopEntry 4 }

tmnxOamVprnTrNextHopTunnelType   OBJECT-TYPE
    SYNTAX      TmnxTunnelType
    MAX-ACCESS  read-only
    STATUS      current
    DESCRIPTION
        "When the value of tmnxOamVprnTrNextHopType is 'remote' the value of
         tmnxOamVprnTrNextHopTunnelType indicates the type of tunnel used to
         reach this BGP next hop."
    ::= { tmnxOamVprnTrNextHopEntry 5 }

tmnxOamVprnTrNextHopIfIndex      OBJECT-TYPE
    SYNTAX      InterfaceIndex
    MAX-ACCESS  read-only
    STATUS      current
    DESCRIPTION
        "When the value of tmnxOamVprnTrNextHopType is 'local' the value of
         tmnxOamVprnTrNextHopIfIndex indicates the interface used to reach this
         ECMP next hop."
    ::= { tmnxOamVprnTrNextHopEntry 6 }

tmnxOamVprnTrNextHopAddrType     OBJECT-TYPE
    SYNTAX      InetAddressType
    MAX-ACCESS  read-only
    STATUS      current
    DESCRIPTION
        "tmnxOamVprnTrNextHopAddrType indicates the type of Internet address
         stored in tmnxOamVprnTrNextHopAddress.  Address types 'unknown(0)',
         'ipv4(1)', 'ipv6(2)', and 'ipv6z(4)' are supported."
    ::= { tmnxOamVprnTrNextHopEntry 7 }

tmnxOamVprnTrNextHopAddress      OBJECT-TYPE
    SYNTAX      InetAddress (SIZE (0|4|16|20))
    MAX-ACCESS  read-only
    STATUS      current
    DESCRIPTION
        "The value of tmnxOamVprnTrNextHopAddress is the Internet address for
         this L3 next hop entry."
    ::= { tmnxOamVprnTrNextHopEntry 8 }

tmnxOamVprnTrRTTable             OBJECT-TYPE
    SYNTAX      SEQUENCE OF TmnxOamVprnTrRTEntry
    MAX-ACCESS  not-accessible
    STATUS      current
    DESCRIPTION
        "Defines a table for storing the results of an OAM 'vprnTraceRoute'
         probe operation where a L3 route target list is returned.

         An entry in this table is created when the result of an OAM
         'vprnTraceRoute' probe is determined. An entry is removed from this
         table when its corresponding tmnxOamTrCtlEntry is deleted."
    ::= { tmnxOamTraceRouteObjs 14 }

tmnxOamVprnTrRTEntry             OBJECT-TYPE
    SYNTAX      TmnxOamVprnTrRTEntry
    MAX-ACCESS  not-accessible
    STATUS      current
    DESCRIPTION
        "Defines an entry in the tmnxOamVprnTrRTTable.  The first two
         index elements identify the tmnxOamTrCtlEntry that a
         tmnxOamVprnTrRTEntry belongs to.  The third index element
         identifies an OAM trace route test run.  The fourth, fifth and sixth
         index elements select a single OAM 'vprnTraceRoute' reply.
         The seventh index selects either the probe requestor's or
         probe replier's route information.  The eighth index selects
         successive L3 route target entries contained in a specific
         'vprnTraceRoute' requestor or probe reply route information."
    INDEX       {
        tmnxOamTrCtlOwnerIndex,
        tmnxOamTrCtlTestIndex,
        tmnxOamTrResultsTestRunIndex,
        tmnxOamTrProbeHistoryIndex,
        tmnxOamTrProbeHistoryHopIndex,
        tmnxOamTrProbeHistoryProbeIndex,
        tmnxOamVprnTrL3MapReporter,
        tmnxOamVprnTrRTIndex
    }
    ::= { tmnxOamVprnTrRTTable 1 }

TmnxOamVprnTrRTEntry             ::= SEQUENCE
{
    tmnxOamVprnTrRTIndex             Unsigned32,
    tmnxOamVprnTrRouteTarget         TmnxBgpRouteTarget
}

tmnxOamVprnTrRTIndex             OBJECT-TYPE
    SYNTAX      Unsigned32 (1..4294967295)
    MAX-ACCESS  not-accessible
    STATUS      current
    DESCRIPTION
        "The tmnxOamVprnTrRTIndex selects a single L3 route target entry
         associated with the router information returned within a specific
         'vprnTraceRoute' probe reply.

         The agent starts assigning tmnxOamVprnTrRTIndex values at 1."
    ::= { tmnxOamVprnTrRTEntry 1 }

tmnxOamVprnTrRouteTarget         OBJECT-TYPE
    SYNTAX      TmnxBgpRouteTarget
    MAX-ACCESS  read-only
    STATUS      current
    DESCRIPTION
        "The value of tmnxOamVprnTrRouteTarget is the route target ID for this
         L3 route target entry."
    ::= { tmnxOamVprnTrRTEntry 2 }

tmnxOamLspTrDSLabelTable         OBJECT-TYPE
    SYNTAX      SEQUENCE OF TmnxOamLspTrDSLabelEntry
    MAX-ACCESS  not-accessible
    STATUS      current
    DESCRIPTION
        "Defines a table for storing the results of an OAM 'lspTraceRoute' probe
         operation when a Downstream Mapping TLV was returned.  Each row
         represents a single downstream label within a returned downstream L2
         mapping TLV.

         An entry in this table is created when the result of an OAM
         'lspTraceRoute' probe is determined.

         An entry is removed from this table when its corresponding
         tmnxOamTrCtlEntry is deleted."
    ::= { tmnxOamTraceRouteObjs 15 }

tmnxOamLspTrDSLabelEntry         OBJECT-TYPE
    SYNTAX      TmnxOamLspTrDSLabelEntry
    MAX-ACCESS  not-accessible
    STATUS      current
    DESCRIPTION
        "Defines an entry in the tmnxOamLspTrDSLabelTable.  The first
         two index elements identify the tmnxOamTrCtlEntry that a
         tmnxOamLspTrMapEntry belongs to.  The third index element
         identifies a OAM trace route test run. The fourth index element
         selects the group of responses associated with a specific
         probe attempt. The fifth and sixth indexes select the hop and
         the probe at that hop for a particular Nokia SROS OAM
         Trace Route operation. The seventh index selects a single downstream
         L2 map entry within the specific probe reply.  The eighth index
         selects successive downstream L2 label entries contained in a
         specific probe reply."
    INDEX       {
        tmnxOamTrCtlOwnerIndex,
        tmnxOamTrCtlTestIndex,
        tmnxOamTrResultsTestRunIndex,
        tmnxOamTrProbeHistoryIndex,
        tmnxOamTrProbeHistoryHopIndex,
        tmnxOamTrProbeHistoryProbeIndex,
        tmnxOamLspTrMapIndex,
        tmnxOamLspTrDSLabelIndex
    }
    ::= { tmnxOamLspTrDSLabelTable 1 }

TmnxOamLspTrDSLabelEntry         ::= SEQUENCE
{
    tmnxOamLspTrDSLabelIndex         Unsigned32,
    tmnxOamLspTrDSLabelLabel         MplsLabel,
    tmnxOamLspTrDSLabelProtocol      TmnxOamSignalProtocol
}

tmnxOamLspTrDSLabelIndex         OBJECT-TYPE
    SYNTAX      Unsigned32 (1..4294967295)
    MAX-ACCESS  not-accessible
    STATUS      current
    DESCRIPTION
        "The tmnxOamLspTrDSLabelIndex selects a single downstream L2 label
         entry within a specific L2 mapping entry reply.

         The agent starts assigning tmnxOamLspTrDSLabelIndex values at 1."
    ::= { tmnxOamLspTrDSLabelEntry 1 }

tmnxOamLspTrDSLabelLabel         OBJECT-TYPE
    SYNTAX      MplsLabel
    MAX-ACCESS  read-only
    STATUS      current
    DESCRIPTION
        "The value of tmnxOamLspTrDSLabelLabel is the label used by the
         downstream router specified by this downstream L2 label entry."
    ::= { tmnxOamLspTrDSLabelEntry 2 }

tmnxOamLspTrDSLabelProtocol      OBJECT-TYPE
    SYNTAX      TmnxOamSignalProtocol
    MAX-ACCESS  read-only
    STATUS      current
    DESCRIPTION
        "The value of tmnxOamLspTrDSLabelProtocol is the signaling protocol
         used by the router for the label specified by this downstream L2 label
         entry."
    ::= { tmnxOamLspTrDSLabelEntry 3 }

tmnxOamMcastTrCtlTable           OBJECT-TYPE
    SYNTAX      SEQUENCE OF TmnxOamMcastTrCtlEntry
    MAX-ACCESS  not-accessible
    STATUS      current
    DESCRIPTION
        "Each row in tmnxOamMcastTrCtlTable contains the multicast-trace-route-
         specific configuration information needed to launch a multicast trace
         route test.  The rest of the configuration information needed to
         launch the test resides in the corresponding row of tmnxOamTrCtlTable.

         Results of multicast trace route tests are stored in
         tmnxOamTrResultsTable, tmnxOamTrProbeHistoryTable, and
         tmnxOamMcastTrRespTable."
    ::= { tmnxOamTraceRouteObjs 16 }

tmnxOamMcastTrCtlEntry           OBJECT-TYPE
    SYNTAX      TmnxOamMcastTrCtlEntry
    MAX-ACCESS  not-accessible
    STATUS      current
    DESCRIPTION
        "The system creates a row in tmnxOamMcastTrCtlTable when a row is
         created in tmnxOamTrCtlTable with tmnxOamTrCtlTestMode set to
         'mcastTraceRoute'.

         The system deletes a row in tmnxOamMcastTrCtlTable when the
         corresponding row in tmnxOamTrCtlTable is deleted."
    INDEX       {
        tmnxOamTrCtlOwnerIndex,
        tmnxOamTrCtlTestIndex
    }
    ::= { tmnxOamMcastTrCtlTable 1 }

TmnxOamMcastTrCtlEntry           ::= SEQUENCE
{
    tmnxOamMcastTrCtlVRtrID          TmnxVRtrID,
    tmnxOamMcastTrCtlSrcIpAddr       IpAddress,
    tmnxOamMcastTrCtlDestIpAddr      IpAddress,
    tmnxOamMcastTrCtlRespIpAddr      IpAddress,
    tmnxOamMcastTrCtlGrpIpAddr       IpAddress,
    tmnxOamMcastTrCtlHops            Unsigned32,
    tmnxOamMcastTrQueryId            Unsigned32,
    tmnxOamMcastTrCtlSrcAddrType     InetAddressType,
    tmnxOamMcastTrCtlSrcAddress      InetAddress,
    tmnxOamMcastTrCtlDestAddrType    InetAddressType,
    tmnxOamMcastTrCtlDestAddress     InetAddress,
    tmnxOamMcastTrCtlRespAddrType    InetAddressType,
    tmnxOamMcastTrCtlRespAddress     InetAddress,
    tmnxOamMcastTrCtlGrpAddrType     InetAddressType,
    tmnxOamMcastTrCtlGrpAddress      InetAddress
}

tmnxOamMcastTrCtlVRtrID          OBJECT-TYPE
    SYNTAX      TmnxVRtrID
    MAX-ACCESS  read-create
    STATUS      current
    DESCRIPTION
        "The value of tmnxOamMcastTrCtlVRtrID specifies the virtual router to be
         used for the test.  The value specified must be the index of an active
         row in TIMETRA-VRTR-MIB::vRtrConfTable (i.e. tmnxOamMcastTrCtlVRtrID
         must match a valid TIMETRA-VRTR-MIB::vRtrID value).  The only
         system-generated TIMETRA-VRTR-MIB::vRtrID value supported by
         tmnxOamMcastTrCtlVRtrID is 1 (i.e. the Base virtual router).

         tmnxOamTrCtlVRtrID (i.e. the equivalent object in the parent table) is
         irrelevant when the test type is 'mcastTraceRoute'.

         When directing an 'mcastTraceRoute' test to use a virtual router
         associated with a VPRN service, the virtual router can be specified
         using tmnxOamMcastTrCtlVRtrID (with the VPRN's virtual router number)
         or tmnxOamTrCtlServiceId (with the VPRN's service number).
         tmnxOamTrCtlServiceId is preferred, because service numbers are
         constant across an SROS reboot (while virtual routers may be
         renumbered).  If non-default values are specified for both
         tmnxOamMcastTrCtlVRtrID and tmnxOamTrCtlServiceId,
         tmnxOamTrCtlServiceId is used."
    DEFVAL      { 1 }
    ::= { tmnxOamMcastTrCtlEntry 1 }

tmnxOamMcastTrCtlSrcIpAddr       OBJECT-TYPE
    SYNTAX      IpAddress
    MAX-ACCESS  read-create
    STATUS      obsolete
    DESCRIPTION
        "tmnxOamMcastTrCtlSrcIpAddr was obsoleted in release 4.0 and replaced
         with InetAddress objects tmnxOamMcastTrCtlSrcAddrType and
         tmnxOamMcastTrCtlSrcAddress."
    ::= { tmnxOamMcastTrCtlEntry 2 }

tmnxOamMcastTrCtlDestIpAddr      OBJECT-TYPE
    SYNTAX      IpAddress
    MAX-ACCESS  read-create
    STATUS      obsolete
    DESCRIPTION
        "tmnxOamMcastTrCtlDestIpAddr was obsoleted in release 4.0 and replaced
         with InetAddress objects tmnxOamMcastTrCtlDestAddrType and
         tmnxOamMcastTrCtlDestAddress."
    DEFVAL      { '00000000'h }
    ::= { tmnxOamMcastTrCtlEntry 3 }

tmnxOamMcastTrCtlRespIpAddr      OBJECT-TYPE
    SYNTAX      IpAddress
    MAX-ACCESS  read-create
    STATUS      obsolete
    DESCRIPTION
        "tmnxOamMcastTrCtlRespIpAddr was obsoleted in release 4.0 and replaced
         with InetAddress objects tmnxOamMcastTrCtlRespAddrType and
         tmnxOamMcastTrCtlRespAddress."
    ::= { tmnxOamMcastTrCtlEntry 4 }

tmnxOamMcastTrCtlGrpIpAddr       OBJECT-TYPE
    SYNTAX      IpAddress
    MAX-ACCESS  read-create
    STATUS      obsolete
    DESCRIPTION
        "tmnxOamMcastTrCtlGrpIpAddr was obsoleted in release 4.0 and replaced
         with InetAddress objects tmnxOamMcastTrCtlGrpAddrType and
         tmnxOamMcastTrCtlGrpAddress."
    ::= { tmnxOamMcastTrCtlEntry 5 }

tmnxOamMcastTrCtlHops            OBJECT-TYPE
    SYNTAX      Unsigned32 (1..255)
    MAX-ACCESS  read-create
    STATUS      current
    DESCRIPTION
        "The value of tmnxOamMcastTrCtlHops specifies the maximum number of
         hops that will be traced along the path to the source. This object is
         optional."
    DEFVAL      { 32 }
    ::= { tmnxOamMcastTrCtlEntry 6 }

tmnxOamMcastTrQueryId            OBJECT-TYPE
    SYNTAX      Unsigned32
    MAX-ACCESS  read-only
    STATUS      current
    DESCRIPTION
        "The value of tmnxOamMcastTrQueryId indicates the 24 bit random number
         that uniquely identifies the multicast trace query. When the router
         receives the response back from the first hop router, it maps the
         response to the query by looking at the query id in the packet."
    ::= { tmnxOamMcastTrCtlEntry 7 }

tmnxOamMcastTrCtlSrcAddrType     OBJECT-TYPE
    SYNTAX      InetAddressType
    MAX-ACCESS  read-create
    STATUS      current
    DESCRIPTION
        "The value of tmnxOamMcastTrCtlSrcAddrType specifies the type of
         Internet address stored in tmnxOamMcastTrCtlSrcAddress."
    DEFVAL      { unknown }
    ::= { tmnxOamMcastTrCtlEntry 8 }

tmnxOamMcastTrCtlSrcAddress      OBJECT-TYPE
    SYNTAX      InetAddress (SIZE (0|4|16))
    MAX-ACCESS  read-create
    STATUS      current
    DESCRIPTION
        "The value of tmnxOamMcastTrCtlSrcAddress specifies the Internet
         address to be used as the source address for the 'mcastTraceRoute'
         test.

         A non-empty address must be specified before the test is enabled."
    DEFVAL      { ''H }
    ::= { tmnxOamMcastTrCtlEntry 9 }

tmnxOamMcastTrCtlDestAddrType    OBJECT-TYPE
    SYNTAX      InetAddressType
    MAX-ACCESS  read-create
    STATUS      current
    DESCRIPTION
        "The value of tmnxOamMcastTrCtlDestAddrType specifies the type of
         Internet address stored in tmnxOamMcastTrCtlDestAddress."
    DEFVAL      { unknown }
    ::= { tmnxOamMcastTrCtlEntry 10 }

tmnxOamMcastTrCtlDestAddress     OBJECT-TYPE
    SYNTAX      InetAddress (SIZE (0|4|16))
    MAX-ACCESS  read-create
    STATUS      current
    DESCRIPTION
        "The value of tmnxOamMcastTrCtlDestAddress specifies the Internet
         address to be used as the destination address for the 'mcastTraceRoute'
         test.  The multicast trace query is sent to this destination address.
         If this object is not set, the multicast trace starts from this
         router."
    DEFVAL      { ''H }
    ::= { tmnxOamMcastTrCtlEntry 11 }

tmnxOamMcastTrCtlRespAddrType    OBJECT-TYPE
    SYNTAX      InetAddressType
    MAX-ACCESS  read-only
    STATUS      current
    DESCRIPTION
        "The value of tmnxOamMcastTrCtlRespAddrType indicates the type of
         Internet address stored in tmnxOamMcastTrCtlRespAddress."
    DEFVAL      { unknown }
    ::= { tmnxOamMcastTrCtlEntry 12 }

tmnxOamMcastTrCtlRespAddress     OBJECT-TYPE
    SYNTAX      InetAddress (SIZE (0|4|16))
    MAX-ACCESS  read-only
    STATUS      current
    DESCRIPTION
        "The value of tmnxOamMcastTrCtlRespAddress indicates the Internet
         address to be used as the response address for the 'mcastTraceRoute'
         test."
    DEFVAL      { ''H }
    ::= { tmnxOamMcastTrCtlEntry 13 }

tmnxOamMcastTrCtlGrpAddrType     OBJECT-TYPE
    SYNTAX      InetAddressType
    MAX-ACCESS  read-create
    STATUS      current
    DESCRIPTION
        "The value of tmnxOamMcastTrCtlGrpAddrType specifies the type of
         Internet address stored in tmnxOamMcastTrCtlGrpAddress."
    DEFVAL      { unknown }
    ::= { tmnxOamMcastTrCtlEntry 14 }

tmnxOamMcastTrCtlGrpAddress      OBJECT-TYPE
    SYNTAX      InetAddress (SIZE (0|4|16))
    MAX-ACCESS  read-create
    STATUS      current
    DESCRIPTION
        "The value of tmnxOamMcastTrCtlGrpAddress specifies the Internet
         multicast group address for the 'mcastTraceRoute' test.

         A non-empty address must be specified before the test is enabled."
    DEFVAL      { ''H }
    ::= { tmnxOamMcastTrCtlEntry 15 }

tmnxOamMcastTrRespTable          OBJECT-TYPE
    SYNTAX      SEQUENCE OF TmnxOamMcastTrRespEntry
    MAX-ACCESS  not-accessible
    STATUS      current
    DESCRIPTION
        "Defines the Nokia SROS OAM Multicast Trace Route Response
         Table for providing, via SNMP, the result of OAM 'mcastTraceRoute' test
         operation.  The results of these tests are stored in the
         tmnxOamTrResultsTable, the tmnxOamTrProbeHistoryTable and
         the tmnxOamMcastTrRespTable."
    ::= { tmnxOamTraceRouteObjs 17 }

tmnxOamMcastTrRespEntry          OBJECT-TYPE
    SYNTAX      TmnxOamMcastTrRespEntry
    MAX-ACCESS  not-accessible
    STATUS      current
    DESCRIPTION
        "Defines an entry in the tmnxOamMcastTrRespTable.
         The first two index elements identify the tmnxOamTrCtlEntry that
         a tmnxOamMcastTrRespEntry belongs to.  The third index element
         selects an OAM trace route test run.  The fourth index element
         selects a single Nokia SROS OAM Trace Route operation result.
         The fifth and sixth indexes select the hop and the probe at that
         hop for a particular Nokia SROS OAM Trace Route operation."
    INDEX       {
        tmnxOamTrCtlOwnerIndex,
        tmnxOamTrCtlTestIndex,
        tmnxOamTrResultsTestRunIndex,
        tmnxOamTrProbeHistoryIndex,
        tmnxOamTrProbeHistoryHopIndex,
        tmnxOamTrProbeHistoryProbeIndex
    }
    ::= { tmnxOamMcastTrRespTable 1 }

TmnxOamMcastTrRespEntry          ::= SEQUENCE
{
    tmnxOamMcastTrRespQueryArrivalTime Unsigned32,
    tmnxOamMcastTrRespInIfAddr       IpAddress,
    tmnxOamMcastTrRespOutIfAddr      IpAddress,
    tmnxOamMcastTrRespPrevHopRtrAddr IpAddress,
    tmnxOamMcastTrRespInPktCount     Counter32,
    tmnxOamMcastTrRespOutPktCount    Counter32,
    tmnxOamMcastTrRespSGPktCount     Counter32,
    tmnxOamMcastTrRespRtgProtocol    INTEGER,
    tmnxOamMcastTrRespFwdTtl         Unsigned32,
    tmnxOamMcastTrRespMBZBit         Unsigned32,
    tmnxOamMcastTrRespSrcBit         Unsigned32,
    tmnxOamMcastTrRespSrcMask        Unsigned32,
    tmnxOamMcastTrRespFwdCode        INTEGER,
    tmnxOamMcastTrRespInIfAddrType   InetAddressType,
    tmnxOamMcastTrRespInIfAddress    InetAddress,
    tmnxOamMcastTrRespOutIfAddrType  InetAddressType,
    tmnxOamMcastTrRespOutIfAddress   InetAddress,
    tmnxOamMcastTrRespPhRtrAddrType  InetAddressType,
    tmnxOamMcastTrRespPhRtrAddress   InetAddress
}

tmnxOamMcastTrRespQueryArrivalTime OBJECT-TYPE
    SYNTAX      Unsigned32
    MAX-ACCESS  read-only
    STATUS      current
    DESCRIPTION
        "tmnxOamMcastTrRespQueryArrivalTime indicates the 32 bit NTP timestamp.
         It is the time at which a particular hop received the Multicast Trace
         query/request."
    ::= { tmnxOamMcastTrRespEntry 1 }

tmnxOamMcastTrRespInIfAddr       OBJECT-TYPE
    SYNTAX      IpAddress
    MAX-ACCESS  read-only
    STATUS      obsolete
    DESCRIPTION
        "tmnxOamMcastTrRespInIfAddr indicates the address of the interface on
         which packets from this source and group are expected to arrive.

         This object was obsoleted in release 4.0 and replaced with InetAddress
         objects tmnxOamMcastTrRespInIfAddrType and
         tmnxOamMcastTrRespInIfAddress."
    ::= { tmnxOamMcastTrRespEntry 2 }

tmnxOamMcastTrRespOutIfAddr      OBJECT-TYPE
    SYNTAX      IpAddress
    MAX-ACCESS  read-only
    STATUS      obsolete
    DESCRIPTION
        "tmnxOamMcastTrRespOutIfAddr indicates the address of the interface on
         which packets from this source and group flow to the specified
         destination.

         This object was obsoleted in release 4.0 and replaced with InetAddress
         objects tmnxOamMcastTrRespOutIfAddrType and
         tmnxOamMcastTrRespOutIfAddress."
    ::= { tmnxOamMcastTrRespEntry 3 }

tmnxOamMcastTrRespPrevHopRtrAddr OBJECT-TYPE
    SYNTAX      IpAddress
    MAX-ACCESS  read-only
    STATUS      obsolete
    DESCRIPTION
        "tmnxOamMcastTrRespPrevHopRtrAddr indicates the router from which this
         router expects packets from this source.  This may be a multicast
         group (e.g. ALL-[protocol]-ROUTERS.MCAST.NET) if the previous hop is
         not known because of the workings of the multicast routing protocol.

         This object was obsoleted in release 4.0 and replaced with InetAddress
         objects tmnxOamMcastTrRespPhRtrAddrType and
         tmnxOamMcastTrRespPhRtrAddress."
    ::= { tmnxOamMcastTrRespEntry 4 }

tmnxOamMcastTrRespInPktCount     OBJECT-TYPE
    SYNTAX      Counter32
    MAX-ACCESS  read-only
    STATUS      current
    DESCRIPTION
        "tmnxOamMcastTrRespInPktCount contains the number of multicast packets
         received for all groups and sources on the incoming interface, or
         0xffffffff if no count can be reported.  This counter should have the
         same value as ifInMulticastPkts from the IF-MIB for this interface."
    ::= { tmnxOamMcastTrRespEntry 5 }

tmnxOamMcastTrRespOutPktCount    OBJECT-TYPE
    SYNTAX      Counter32
    MAX-ACCESS  read-only
    STATUS      current
    DESCRIPTION
        "tmnxOamMcastTrRespOutPktCount contains the number of multicast packets
         that have been transmitted or queued for transmission for all groups
         and sources on the outgoing interface, or 0xffffffff if no count can
         be reported.  This counter should have the same value as
         ifOutMulticastPkts from the IF-MIB for this interface."
    ::= { tmnxOamMcastTrRespEntry 6 }

tmnxOamMcastTrRespSGPktCount     OBJECT-TYPE
    SYNTAX      Counter32
    MAX-ACCESS  read-only
    STATUS      current
    DESCRIPTION
        "tmnxOamMcastTrRespSGPktCount counts the number of packets from the
         specified source forwarded by this router to the specified group, or
         0xffffffff if no count can be reported. If the value of
         tmnxOamMcastTrRespSrcBit is set to one, the count is for the source
         network, as specified by tmnxOamMcastTrRespSrcMask. If the S bit is
         set and the Src Mask field is 63, indicating no source-specific state,
         the count is for all sources sending to this group."
    ::= { tmnxOamMcastTrRespEntry 7 }

tmnxOamMcastTrRespRtgProtocol    OBJECT-TYPE
    SYNTAX      INTEGER {
        unknown     (0),
        dvmrp       (1),
        mospf       (2),
        pim         (3),
        cbt         (4),
        pimSpecial  (5),
        pimStatic   (6),
        dvmrpStatic (7),
        bgp4Plus    (8),
        cbtSpecial  (9),
        cbtStatic   (10),
        pimAssert   (11)
    }
    MAX-ACCESS  read-only
    STATUS      current
    DESCRIPTION
        "tmnxOamMcastTrRespRtgProtocol describes the routing protocol in use
         between this router and the previous-hop router."
    ::= { tmnxOamMcastTrRespEntry 8 }

tmnxOamMcastTrRespFwdTtl         OBJECT-TYPE
    SYNTAX      Unsigned32
    MAX-ACCESS  read-only
    STATUS      current
    DESCRIPTION
        "tmnxOamMcastTrRespFwdTtl contains the TTL that a packet is required to
         have before it will be forwarded over the outgoing interface."
    ::= { tmnxOamMcastTrRespEntry 9 }

tmnxOamMcastTrRespMBZBit         OBJECT-TYPE
    SYNTAX      Unsigned32
    MAX-ACCESS  read-only
    STATUS      current
    DESCRIPTION
        "tmnxOamMcastTrRespMBZBit is zeroed on transmission and ignored on
         reception."
    ::= { tmnxOamMcastTrRespEntry 10 }

tmnxOamMcastTrRespSrcBit         OBJECT-TYPE
    SYNTAX      Unsigned32
    MAX-ACCESS  read-only
    STATUS      current
    DESCRIPTION
        "If the value of tmnxOamMcastTrRespSrcBit is 1, it indicates that the
         packet count for the source-group pair is for the source network, as
         determined by masking the source address with the
         tmnxOamMcastTrRespSrcMask field."
    ::= { tmnxOamMcastTrRespEntry 11 }

tmnxOamMcastTrRespSrcMask        OBJECT-TYPE
    SYNTAX      Unsigned32
    MAX-ACCESS  read-only
    STATUS      current
    DESCRIPTION
        "tmnxOamMcastTrRespSrcMask contains the number of 1's in the netmask
         this router has for the source (i.e. a value of 24 means the netmask is
         0xffffff00).  If the router is forwarding solely on group state,
         this field is set to 63 (0x3f)."
    ::= { tmnxOamMcastTrRespEntry 12 }

tmnxOamMcastTrRespFwdCode        OBJECT-TYPE
    SYNTAX      INTEGER {
        noError       (0),
        wrongIf       (1),
        pruneSent     (2),
        pruneRecvd    (3),
        scoped        (4),
        noRoute       (5),
        wrongLastHop  (6),
        notForwarding (7),
        reachedRP     (8),
        rpfIf         (9),
        noMulticast   (10),
        infoHidden    (11),
        fatalError    (128),
        noSpace       (129),
        oldRouter     (130),
        adminProhib   (131),
        unknown       (132)
    }
    MAX-ACCESS  read-only
    STATUS      current
    DESCRIPTION
        "tmnxOamMcastTrRespFwdCode contains a forwarding information/error
         code:
         noError(0)       - No error
         wrongIf(1)       - Traceroute request arrived on an interface to
                            which this router would not forward for this
                            source,group,destination.
         pruneSent(2)     - This router has sent a prune upstream which
                            applies to the source and group in the traceroute
                            request.
         pruneRecvd(3)    - This router has stopped forwarding for this
                            source and group in response to a request from
                            the next hop router.
         scoped(4)        - The group is subject to administrative scoping
                            at this hop.
         noRoute(5)       - This router has no route for the source or
                            group and no way to determine a potential route.
         wrongLastHop(6)  - This router is not the proper last-hop router.
         notForwarding(7) - This router is not forwarding this
                            source,group out the outgoing interface for an
                            unspecified reason.
         reachedRP(8)     - Reached Rendezvous Point or Core
         rpfIf(9)         - Traceroute request arrived on the expected RPF
                            interface for this source,group.
         noMulticast(10)  - Traceroute request arrived on an interface
                            which is not enabled for multicast.
         infoHidden(11)   - One or more hops have been hidden from this trace.
         fatalError(128)  - Router may know the previous hop but cannot forward
                            the message to it.
         noSpace(129)     - There was not enough room to insert another
                            response data block in the packet.
         oldRouter(130)   - The previous hop router does not understand
                            traceroute requests
         adminProhib(131) - Traceroute is administratively prohibited.
         unknown(132)     - Unknown forwarding code received."
    ::= { tmnxOamMcastTrRespEntry 13 }

tmnxOamMcastTrRespInIfAddrType   OBJECT-TYPE
    SYNTAX      InetAddressType
    MAX-ACCESS  read-only
    STATUS      current
    DESCRIPTION
        "tmnxOamMcastTrRespInIfAddrType indicates the type of Internet address
         stored at tmnxOamMcastTrRespInIfAddress."
    ::= { tmnxOamMcastTrRespEntry 14 }

tmnxOamMcastTrRespInIfAddress    OBJECT-TYPE
    SYNTAX      InetAddress (SIZE (0|4|16))
    MAX-ACCESS  read-only
    STATUS      current
    DESCRIPTION
        "tmnxOamMcastTrRespInIfAddress indicates the Internet address of the
         interface on which packets from this source and group are expected to
         arrive."
    ::= { tmnxOamMcastTrRespEntry 15 }

tmnxOamMcastTrRespOutIfAddrType  OBJECT-TYPE
    SYNTAX      InetAddressType
    MAX-ACCESS  read-only
    STATUS      current
    DESCRIPTION
        "tmnxOamMcastTrRespOutIfAddrType indicates the type of Internet address
         stored in tmnxOamMcastTrRespOutIfAddress."
    ::= { tmnxOamMcastTrRespEntry 16 }

tmnxOamMcastTrRespOutIfAddress   OBJECT-TYPE
    SYNTAX      InetAddress (SIZE (0|4|16))
    MAX-ACCESS  read-only
    STATUS      current
    DESCRIPTION
        "tmnxOamMcastTrRespOutIfAddress indicates the Internet address of the
         interface on which packets from this source and group flow to the
         specified destination."
    ::= { tmnxOamMcastTrRespEntry 17 }

tmnxOamMcastTrRespPhRtrAddrType  OBJECT-TYPE
    SYNTAX      InetAddressType
    MAX-ACCESS  read-only
    STATUS      current
    DESCRIPTION
        "tmnxOamMcastTrRespPhRtrAddrType indicates the type of internet address
         stored in tmnxOamMcastTrRespPhRtrAddress."
    ::= { tmnxOamMcastTrRespEntry 18 }

tmnxOamMcastTrRespPhRtrAddress   OBJECT-TYPE
    SYNTAX      InetAddress (SIZE (0|4|16))
    MAX-ACCESS  read-only
    STATUS      current
    DESCRIPTION
        "tmnxOamMcastTrRespPhRtrAddress indicates the Internet address of the
         router from which this router expects packets for this source. This
         may be a multicast group (e.g. ALL-[protocol]-ROUTERS.MCAST.NET) if
         the previous hop is not known because of the workings of the multicast
         routing protocol."
    ::= { tmnxOamMcastTrRespEntry 19 }

tmnxOamLTtraceCtlTable           OBJECT-TYPE
    SYNTAX      SEQUENCE OF TmnxOamLTtraceCtlEntry
    MAX-ACCESS  not-accessible
    STATUS      current
    DESCRIPTION
        "Each row in tmnxOamLTtraceCtlTable contains the LDP-tree-trace-specific
         configuration information needed to launch a foreground LDP (Label
         Distribution Protocol) tree trace test.  The rest of the configuration
         information needed to launch the test resides in the corresponding row
         of tmnxOamTrCtlTable.

         Results of LDP tree trace tests are stored in
         tmnxOamLTtraceResultsTable and tmnxOamLTtraceHopInfoTable."
    ::= { tmnxOamTraceRouteObjs 18 }

tmnxOamLTtraceCtlEntry           OBJECT-TYPE
    SYNTAX      TmnxOamLTtraceCtlEntry
    MAX-ACCESS  not-accessible
    STATUS      current
    DESCRIPTION
        "The system creates a row in tmnxOamLTtraceCtlTable when a row is
         created in tmnxOamTrCtlTable with tmnxOamTrCtlTestMode set to
         'ldpTreeTrace'.

         The system deletes a row in tmnxOamLTtraceCtlTable when the
         corresponding row in tmnxOamTrCtlTable is deleted."
    INDEX       {
        tmnxOamTrCtlOwnerIndex,
        tmnxOamTrCtlTestIndex
    }
    ::= { tmnxOamLTtraceCtlTable 1 }

TmnxOamLTtraceCtlEntry           ::= SEQUENCE
{
    tmnxOamLTtraceCtlLdpPrefixType   InetAddressType,
    tmnxOamLTtraceCtlLdpPrefix       InetAddress,
    tmnxOamLTtraceCtlLdpPrefixLen    InetAddressPrefixLength,
    tmnxOamLTtraceCtlMaxPath         Unsigned32,
    tmnxOamLTtraceCtlDownstreamMpTlv TmnxOamMplsEchoDownMapTlv
}

tmnxOamLTtraceCtlLdpPrefixType   OBJECT-TYPE
    SYNTAX      InetAddressType
    MAX-ACCESS  read-create
    STATUS      current
    DESCRIPTION
        "The value of tmnxOamLTtraceCtlLdpPrefixType specifies the type of
         Internet address stored in tmnxOamLTtraceCtlLdpPrefix."
    DEFVAL      { unknown }
    ::= { tmnxOamLTtraceCtlEntry 2 }

tmnxOamLTtraceCtlLdpPrefix       OBJECT-TYPE
    SYNTAX      InetAddress (SIZE (0|4|16))
    MAX-ACCESS  read-create
    STATUS      current
    DESCRIPTION
        "The value of tmnxOamLTtraceCtlLdpPrefix specifies the Internet address
         prefix for the LDP based LSP for this LDP tree trace test."
    DEFVAL      { ''H }
    ::= { tmnxOamLTtraceCtlEntry 3 }

tmnxOamLTtraceCtlLdpPrefixLen    OBJECT-TYPE
    SYNTAX      InetAddressPrefixLength
    UNITS       "bits"
    MAX-ACCESS  read-create
    STATUS      current
    DESCRIPTION
        "The value of tmnxOamLTtraceCtlLdpPrefixLen specifies the Internet
         address prefix length for the LDP based LSP for this LDP tree trace
         test.

         The value of this parameter is valid only when the LDP prefix
         (tmnxOamLTtraceCtlLdpPrefix) has been specified."
    DEFVAL      { 32 }
    ::= { tmnxOamLTtraceCtlEntry 4 }

tmnxOamLTtraceCtlMaxPath         OBJECT-TYPE
    SYNTAX      Unsigned32 (1..255)
    MAX-ACCESS  read-create
    STATUS      current
    DESCRIPTION
        "The value of tmnxOamLTtraceCtlMaxPath specifies the maximum number of
         paths that can be discovered for the given LDP Prefix
         (tmnxOamLTtraceCtlLdpPrefix)."
    DEFVAL      { 128 }
    ::= { tmnxOamLTtraceCtlEntry 5 }

tmnxOamLTtraceCtlDownstreamMpTlv OBJECT-TYPE
    SYNTAX      TmnxOamMplsEchoDownMapTlv
    MAX-ACCESS  read-create
    STATUS      current
    DESCRIPTION
        "The value of tmnxOamLTtraceCtlDownstreamMpTlv specifies the type of
         downstream mapping TLV to insert in the MPLS echo request PDUs when
         launching the test.

         When an LDP tree trace test is created, the value of this object
         defaults to the value of the global configuration object
         tmnxOamMplsEchoDownstreamMapTlv."
    ::= { tmnxOamLTtraceCtlEntry 6 }

tmnxOamLTtraceMaxConRequests     OBJECT-TYPE
    SYNTAX      Unsigned32
    UNITS       "requests"
    MAX-ACCESS  read-only
    STATUS      current
    DESCRIPTION
        "The value of tmnxOamLTtraceMaxConRequests indicates the maximum number
         of concurrent LDP Tree Trace manual discovery sessions that are
         allowed within an agent implementation."
    ::= { tmnxOamTraceRouteObjs 19 }

tmnxOamLTtraceResultsTable       OBJECT-TYPE
    SYNTAX      SEQUENCE OF TmnxOamLTtraceResultsEntry
    MAX-ACCESS  not-accessible
    STATUS      current
    DESCRIPTION
        "tmnxOamLTtraceResultsTable defines the Nokia SROS OAM Trace Route Test
         Results Table for keeping track of the status of a tmnxOamTrCtlEntry
         having tmnxOamTrCtlTestMode as ldpTreeTrace.

         An entry is added to the tmnxOamLTtraceResultsTable when an
         tmnxOamTrCtlEntry is created with  tmnxOamTrCtlTestMode having
         value 'ldpTreeTrace'.

         An entry is removed from the tmnxOamTrResultsTable when such a
         corresponding entry, tmnxOamTrCtlEntry, is deleted."
    ::= { tmnxOamTraceRouteObjs 20 }

tmnxOamLTtraceResultsEntry       OBJECT-TYPE
    SYNTAX      TmnxOamLTtraceResultsEntry
    MAX-ACCESS  not-accessible
    STATUS      current
    DESCRIPTION
        "tmnxOamLTtraceResultsEntry represents a row in the
         tmnxOamLTtraceResultsTable.  The two indices of the
         tmnxOamLTtraceResultsTable are the same as that in the
         tmnxOamTrCtlTable in order for a tmnxOamLTtraceResultsEntry to
         correspond to the tmnxOamTrCtlEntry that caused it to be
         created."
    INDEX       {
        tmnxOamTrCtlOwnerIndex,
        tmnxOamTrCtlTestIndex
    }
    ::= { tmnxOamLTtraceResultsTable 1 }

TmnxOamLTtraceResultsEntry       ::= SEQUENCE
{
    tmnxOamLTtraceResultsDisPaths    Unsigned32,
    tmnxOamLTtraceResultsFailedHops  Unsigned32,
    tmnxOamLTtraceResultsDisState    INTEGER,
    tmnxOamLTtraceResultsDisStatus   TmnxOamLTtraceDisStatusBits
}

tmnxOamLTtraceResultsDisPaths    OBJECT-TYPE
    SYNTAX      Unsigned32
    MAX-ACCESS  read-only
    STATUS      current
    DESCRIPTION
        "The value of tmnxOamLTtraceResultsDisPaths indicates the number of
         discovered ECMP paths in this OAM LDP Tree discovery test."
    ::= { tmnxOamLTtraceResultsEntry 2 }

tmnxOamLTtraceResultsFailedHops  OBJECT-TYPE
    SYNTAX      Unsigned32
    MAX-ACCESS  read-only
    STATUS      current
    DESCRIPTION
        "The value of tmnxOamLTtraceResultsFailedHops indicates the number of
         hops from which no successful response was received during this OAM
         LDP Tree discovery test."
    ::= { tmnxOamLTtraceResultsEntry 3 }

tmnxOamLTtraceResultsDisState    OBJECT-TYPE
    SYNTAX      INTEGER {
        initial    (0),
        inProgress (1),
        done       (2)
    }
    MAX-ACCESS  read-only
    STATUS      current
    DESCRIPTION
        "The value of tmnxOamLTtraceResultsDisState indicates the current state
         of the discovery process for the LDP IP prefix
         (tmnxOamLTtraceCtlLdpPrefix) in this OAM LDP Tree discovery test."
    ::= { tmnxOamLTtraceResultsEntry 4 }

tmnxOamLTtraceResultsDisStatus   OBJECT-TYPE
    SYNTAX      TmnxOamLTtraceDisStatusBits
    MAX-ACCESS  read-only
    STATUS      current
    DESCRIPTION
        "The value of tmnxOamLTtraceResultsDisStatus indicates the current
         discovery status bits for the LDP IP prefix
         (tmnxOamLTtraceCtlLdpPrefix) in this OAM LDP Tree discovery test."
    ::= { tmnxOamLTtraceResultsEntry 5 }

tmnxOamLTtraceHopInfoTable       OBJECT-TYPE
    SYNTAX      SEQUENCE OF TmnxOamLTtraceHopInfoEntry
    MAX-ACCESS  not-accessible
    STATUS      current
    DESCRIPTION
        "tmnxOamLTtraceHopInfoTable defines the Nokia SROS OAM LDP Trace Hops
         table for keeping track of the results of an LDP Tree Trace test on a
         per hop basis.

         An entry is added to the tmnxOamLTtraceHopInfoTable when a
         hop is discovered after setting the tmnxOamTrCtlAdminStatus
         object of the tmnxOamTrCtlEntry (having tmnxOamTrCtlTestMode
         as ldpTreeTrace) to 'enabled(1)'.  An entry is removed from the
         tmnxOamLTtraceHopInfoTable when its corresponding tmnxOamTrCtlEntry
         is deleted."
    ::= { tmnxOamTraceRouteObjs 21 }

tmnxOamLTtraceHopInfoEntry       OBJECT-TYPE
    SYNTAX      TmnxOamLTtraceHopInfoEntry
    MAX-ACCESS  not-accessible
    STATUS      current
    DESCRIPTION
        "tmnxOamLTtraceHopInfoEntry represents a row in the
         tmnxOamLTtraceHopInfoTable. The first two indices of the
         tmnxOamLTtraceHopInfoTable are the same as the tmnxOamTrCtlTable in
         order for a tmnxOamLTtraceHopInfoEntry to correspond to the
         tmnxOamTrCtlEntry that caused it to be created. The third index
         element, tmnxOamLTtraceHopIndex, selects a hop in an Nokia SROS LDP
         Tree Trace discovered path."
    INDEX       {
        tmnxOamTrCtlOwnerIndex,
        tmnxOamTrCtlTestIndex,
        tmnxOamLTtraceHopIndex
    }
    ::= { tmnxOamLTtraceHopInfoTable 1 }

TmnxOamLTtraceHopInfoEntry       ::= SEQUENCE
{
    tmnxOamLTtraceHopIndex           Unsigned32,
    tmnxOamLTtraceUpStreamHopIndex   Unsigned32,
    tmnxOamLTtraceHopAddrType        InetAddressType,
    tmnxOamLTtraceHopAddr            InetAddress,
    tmnxOamLTtraceHopDstAddrType     InetAddressType,
    tmnxOamLTtraceHopDstAddr         InetAddress,
    tmnxOamLTtraceHopEgrNhAddrType   InetAddressType,
    tmnxOamLTtraceHopEgrNhAddr       InetAddress,
    tmnxOamLTtraceHopDisTtl          Unsigned32,
    tmnxOamLTtraceHopLastRc          TmnxOamPingRtnCode,
    tmnxOamLTtraceHopDiscoveryState  INTEGER,
    tmnxOamLTtraceHopDiscoveryTime   TimeStamp,
    tmnxOamLTtraceHopLabel1          MplsLabel,
    tmnxOamLTtraceHopLabel2          MplsLabel,
    tmnxOamLTtraceHopLabel3          MplsLabel,
    tmnxOamLTtraceHopLabel4          MplsLabel,
    tmnxOamLTtraceHopLabel5          MplsLabel,
    tmnxOamLTtraceHopLabel6          MplsLabel,
    tmnxOamLTtraceHopIfAddrType      InetAddressType,
    tmnxOamLTtraceHopIfAddress       InetAddress,
    tmnxOamLTtraceHopRouterIdType    InetAddressType,
    tmnxOamLTtraceHopRouterId        InetAddress
}

tmnxOamLTtraceHopIndex           OBJECT-TYPE
    SYNTAX      Unsigned32
    MAX-ACCESS  not-accessible
    STATUS      current
    DESCRIPTION
        "The value of tmnxOamLTtraceHopIndex indicates the hop index for an
         Nokia SROS OAM Trace hop for an LDP Tree Trace test. The hop index
         values are assigned starting at 1."
    ::= { tmnxOamLTtraceHopInfoEntry 1 }

tmnxOamLTtraceUpStreamHopIndex   OBJECT-TYPE
    SYNTAX      Unsigned32
    MAX-ACCESS  read-only
    STATUS      current
    DESCRIPTION
        "The value of tmnxOamLTtraceUpStreamHopIndex indicates the
         hop index (tmnxOamLTtraceHopIndex) of its upstream hop
         discovered during the LDP Tree Trace test.  The value of
         tmnxOamLTtraceUpStreamHopIndex is 0 for the hops which are
         the root of the different discovered paths for the LDP
         Tree Trace test."
    ::= { tmnxOamLTtraceHopInfoEntry 2 }

tmnxOamLTtraceHopAddrType        OBJECT-TYPE
    SYNTAX      InetAddressType
    MAX-ACCESS  read-only
    STATUS      current
    DESCRIPTION
        "The value of tmnxOamLTtraceHopAddrType indicates the type of Internet
         address stored in tmnxOamLTtraceHopAddr."
    ::= { tmnxOamLTtraceHopInfoEntry 3 }

tmnxOamLTtraceHopAddr            OBJECT-TYPE
    SYNTAX      InetAddress (SIZE (0|4|16))
    MAX-ACCESS  read-only
    STATUS      current
    DESCRIPTION
        "The value of tmnxOamLTtraceHopAddr indicates the IP address of a hop
         for a given LDP based LSP associated with the OAM LDP Tree trace test."
    ::= { tmnxOamLTtraceHopInfoEntry 4 }

tmnxOamLTtraceHopDstAddrType     OBJECT-TYPE
    SYNTAX      InetAddressType
    MAX-ACCESS  read-only
    STATUS      current
    DESCRIPTION
        "The value of tmnxOamLTtraceHopDstAddrType indicates the type of
         Internet address stored in tmnxOamLTtraceHopDstAddr."
    ::= { tmnxOamLTtraceHopInfoEntry 5 }

tmnxOamLTtraceHopDstAddr         OBJECT-TYPE
    SYNTAX      InetAddress (SIZE (0|4|16))
    MAX-ACCESS  read-only
    STATUS      current
    DESCRIPTION
        "The value of tmnxOamLTtraceHopDstAddr indicates the destination IP
         address (127 Address) of a path associated with the hop."
    ::= { tmnxOamLTtraceHopInfoEntry 6 }

tmnxOamLTtraceHopEgrNhAddrType   OBJECT-TYPE
    SYNTAX      InetAddressType
    MAX-ACCESS  read-only
    STATUS      current
    DESCRIPTION
        "The value of tmnxOamLTtraceHopEgrNhAddrType indicates the type of
         Internet address stored in tmnxOamLTtraceHopEgrNhAddr."
    ::= { tmnxOamLTtraceHopInfoEntry 7 }

tmnxOamLTtraceHopEgrNhAddr       OBJECT-TYPE
    SYNTAX      InetAddress (SIZE (0|4|16))
    MAX-ACCESS  read-only
    STATUS      current
    DESCRIPTION
        "The value of tmnxOamLTtraceHopEgrNhAddr indicates the
         next hop  IP address (wrt the ingress router), which is used
         to reach this Hop (tmnxOamLTtraceHopAddr)."
    ::= { tmnxOamLTtraceHopInfoEntry 8 }

tmnxOamLTtraceHopDisTtl          OBJECT-TYPE
    SYNTAX      Unsigned32
    MAX-ACCESS  read-only
    STATUS      current
    DESCRIPTION
        "The value of tmnxOamLTtraceHopDisTtl indicates the label time-to-live
         value used to discover this hop."
    ::= { tmnxOamLTtraceHopInfoEntry 9 }

tmnxOamLTtraceHopLastRc          OBJECT-TYPE
    SYNTAX      TmnxOamPingRtnCode
    MAX-ACCESS  read-only
    STATUS      current
    DESCRIPTION
        "The value of tmnxOamLTtraceHopLastRc indicates the OAM return code
         received in the OAM trace response."
    ::= { tmnxOamLTtraceHopInfoEntry 10 }

tmnxOamLTtraceHopDiscoveryState  OBJECT-TYPE
    SYNTAX      INTEGER {
        inProgress       (0),
        doneOk           (1),
        doneTimeout      (2),
        doneLoopDetected (3),
        doneExpiredTtl   (4)
    }
    MAX-ACCESS  read-only
    STATUS      current
    DESCRIPTION
        "The value of tmnxOamLTtraceHopDiscoveryState indicates the current
         discovery state of this hop."
    ::= { tmnxOamLTtraceHopInfoEntry 11 }

tmnxOamLTtraceHopDiscoveryTime   OBJECT-TYPE
    SYNTAX      TimeStamp
    MAX-ACCESS  read-only
    STATUS      current
    DESCRIPTION
        "The value of tmnxOamLTtraceHopDiscoveryTime indicates the sysUpTime
         when the hop was discovered."
    ::= { tmnxOamLTtraceHopInfoEntry 12 }

tmnxOamLTtraceHopLabel1          OBJECT-TYPE
    SYNTAX      MplsLabel
    MAX-ACCESS  read-only
    STATUS      current
    DESCRIPTION
        "The value of tmnxOamLTtraceHopLabel1 indicates the first (top of the
         label stack) label for this hop."
    ::= { tmnxOamLTtraceHopInfoEntry 13 }

tmnxOamLTtraceHopLabel2          OBJECT-TYPE
    SYNTAX      MplsLabel
    MAX-ACCESS  read-only
    STATUS      current
    DESCRIPTION
        "The value of tmnxOamLTtraceHopLabel2 indicates the second label for
         this hop."
    ::= { tmnxOamLTtraceHopInfoEntry 14 }

tmnxOamLTtraceHopLabel3          OBJECT-TYPE
    SYNTAX      MplsLabel
    MAX-ACCESS  read-only
    STATUS      current
    DESCRIPTION
        "The value of tmnxOamLTtraceHopLabel3 indicates the third label for
         this hop."
    ::= { tmnxOamLTtraceHopInfoEntry 15 }

tmnxOamLTtraceHopLabel4          OBJECT-TYPE
    SYNTAX      MplsLabel
    MAX-ACCESS  read-only
    STATUS      current
    DESCRIPTION
        "The value of tmnxOamLTtraceHopLabel4 indicates the fourth label for
         this hop."
    ::= { tmnxOamLTtraceHopInfoEntry 16 }

tmnxOamLTtraceHopLabel5          OBJECT-TYPE
    SYNTAX      MplsLabel
    MAX-ACCESS  read-only
    STATUS      current
    DESCRIPTION
        "The value of tmnxOamLTtraceHopLabel5 indicates the fifth label for
         this hop."
    ::= { tmnxOamLTtraceHopInfoEntry 17 }

tmnxOamLTtraceHopLabel6          OBJECT-TYPE
    SYNTAX      MplsLabel
    MAX-ACCESS  read-only
    STATUS      current
    DESCRIPTION
        "The value of tmnxOamLTtraceHopLabel6 indicates the sixth label for
         this hop."
    ::= { tmnxOamLTtraceHopInfoEntry 18 }

tmnxOamLTtraceHopIfAddrType      OBJECT-TYPE
    SYNTAX      InetAddressType
    MAX-ACCESS  read-only
    STATUS      current
    DESCRIPTION
        "The value of tmnxOamLTtraceHopIfAddrType indicates the IP address type
         for the interface IP address for this hop."
    ::= { tmnxOamLTtraceHopInfoEntry 19 }

tmnxOamLTtraceHopIfAddress       OBJECT-TYPE
    SYNTAX      InetAddress (SIZE (0|4|16))
    MAX-ACCESS  read-only
    STATUS      current
    DESCRIPTION
        "The value of tmnxOamLTtraceHopIfAddress indicates the IP Address for
         the interface for this hop."
    ::= { tmnxOamLTtraceHopInfoEntry 20 }

tmnxOamLTtraceHopRouterIdType    OBJECT-TYPE
    SYNTAX      InetAddressType
    MAX-ACCESS  read-only
    STATUS      current
    DESCRIPTION
        "The value of tmnxOamLTtraceHopRouterIdType indicates the IP address
         type for the Router ID for this hop."
    ::= { tmnxOamLTtraceHopInfoEntry 21 }

tmnxOamLTtraceHopRouterId        OBJECT-TYPE
    SYNTAX      InetAddress (SIZE (0|4|16))
    MAX-ACCESS  read-only
    STATUS      current
    DESCRIPTION
        "The value of tmnxOamLTtraceHopRouterId indicates the IP Address for
         the Router ID for this hop."
    ::= { tmnxOamLTtraceHopInfoEntry 22 }

tmnxOamLTtraceAutoConfigTable    OBJECT-TYPE
    SYNTAX      SEQUENCE OF TmnxOamLTtraceAutoConfigEntry
    MAX-ACCESS  not-accessible
    STATUS      current
    DESCRIPTION
        "tmnxOamLTtraceAutoConfigTable contains an entry for configuration
         information about each instance of Automatic (background) LDP Tree
         Trace."
    ::= { tmnxOamTraceRouteObjs 22 }

tmnxOamLTtraceAutoConfigEntry    OBJECT-TYPE
    SYNTAX      TmnxOamLTtraceAutoConfigEntry
    MAX-ACCESS  not-accessible
    STATUS      current
    DESCRIPTION
        "tmnxOamLTtraceAutoConfigEntry represents a row in the
         tmnxOamLTtraceAutoConfigTable.  Each entry represents the
         Automatic LDP Tree Trace instance running on a virtual router.

          A row entry can be created and deleted through the
          tmnxOamLTtraceAutoRowStatus object."
    INDEX       { vRtrID }
    ::= { tmnxOamLTtraceAutoConfigTable 1 }

TmnxOamLTtraceAutoConfigEntry    ::= SEQUENCE
{
    tmnxOamLTtraceAutoRowStatus      RowStatus,
    tmnxOamLTtraceAutoLastChanged    TimeStamp,
    tmnxOamLTtraceAutoStorageType    StorageType,
    tmnxOamLTtraceAutoAdminState     TmnxAdminState,
    tmnxOamLTtraceAutoFcName         TFCName,
    tmnxOamLTtraceAutoProfile        TProfile,
    tmnxOamLTtraceAutoDiscIntvl      Unsigned32,
    tmnxOamLTtraceAutoMaxPath        Unsigned32,
    tmnxOamLTtraceAutoTrMaxTtl       Unsigned32,
    tmnxOamLTtraceAutoTrTimeOut      Unsigned32,
    tmnxOamLTtraceAutoTrMaxFailures  Unsigned32,
    tmnxOamLTtraceAutoPolicy1        TPolicyStatementNameOrEmpty,
    tmnxOamLTtraceAutoPolicy2        TPolicyStatementNameOrEmpty,
    tmnxOamLTtraceAutoPolicy3        TPolicyStatementNameOrEmpty,
    tmnxOamLTtraceAutoPolicy4        TPolicyStatementNameOrEmpty,
    tmnxOamLTtraceAutoPolicy5        TPolicyStatementNameOrEmpty,
    tmnxOamLTtraceAutoProbeIntvl     Unsigned32,
    tmnxOamLTtraceAutoPrTimeOut      Unsigned32,
    tmnxOamLTtraceAutoPrMaxFailures  Unsigned32
}

tmnxOamLTtraceAutoRowStatus      OBJECT-TYPE
    SYNTAX      RowStatus
    MAX-ACCESS  read-create
    STATUS      current
    DESCRIPTION
        "The value of tmnxOamLTtraceAutoRowStatus specifies the row status of
         the Auto LDP Tree Trace instance for the virtual router.

         A row with default attribute values is created by setting
         tmnxOamLTtraceAutoRowStatus to 'createAndGo'. A row entry can be
         destroyed by setting tmnxOamLTtraceAutoRowStatus to 'destroy'. An
         attempt to destroy a row will fail if tmnxOamLTtraceAutoAdminState is
         not set to 'outOfService'.

         Deletion of an entry in this table results in deletion of all the
         corresponding tables: tmnxOamLTtraceAutoStatusTable,
         tmnxOamLTtraceFecInfoTable, and tmnxOamLTtracePathInfoTable."
    ::= { tmnxOamLTtraceAutoConfigEntry 1 }

tmnxOamLTtraceAutoLastChanged    OBJECT-TYPE
    SYNTAX      TimeStamp
    MAX-ACCESS  read-only
    STATUS      current
    DESCRIPTION
        "The value of tmnxOamLTtraceAutoLastChanged indicates the last time the
         value of a writable object in this row was modified."
    ::= { tmnxOamLTtraceAutoConfigEntry 2 }

tmnxOamLTtraceAutoStorageType    OBJECT-TYPE
    SYNTAX      StorageType
    MAX-ACCESS  read-create
    STATUS      obsolete
    DESCRIPTION
        "The value of tmnxOamLTtraceAutoStorageType specifies the storage type
         for this conceptual row. Conceptual rows having the value 'permanent'
         need not allow write-access to any columnar objects in the row.

         This object was marked obsolete in SROS Release 14.0 R1.  There is no
         replacement object."
    DEFVAL      { volatile }
    ::= { tmnxOamLTtraceAutoConfigEntry 3 }

tmnxOamLTtraceAutoAdminState     OBJECT-TYPE
    SYNTAX      TmnxAdminState
    MAX-ACCESS  read-create
    STATUS      current
    DESCRIPTION
        "The value of tmnxOamLTtraceAutoAdminState specifies the state based on
         which the Auto LDP Tree Discovery process starts or stops.

         When the tmnxOamLTtraceAutoAdminState becomes 'inService', the Auto
         LDP Tree Discovery process starts, and periodic path-probing on the
         previously discovered paths, if any, continues. When the
         tmnxOamLTtraceAutoAdminState becomes 'outOfService', the Auto LDP Tree
         Discovery process and periodic path-probing on the discovered paths
         stop.

         At the start of the Auto discovery process, it selects the address
         FECs imported from LDP peers (TIMETRA-LDP-MIB:: vRtrLdpAddrFecTable)
         provided the FECs pass the configured policies
         (tmnxOamLTtraceAutoPolicy1..tmnxOamLTtraceAutoPolicy5). For all the
         FECs (tmnxOamLTtraceAutoTotalFecs), it automatically creates entries
         from the tmnxOamLTtraceFecInfoTable. As a part of the auto discovery
         process, it creates entries from the tmnxOamLTtracePathInfoTable for
         each discovered path."
    DEFVAL      { outOfService }
    ::= { tmnxOamLTtraceAutoConfigEntry 4 }

tmnxOamLTtraceAutoFcName         OBJECT-TYPE
    SYNTAX      TFCName
    MAX-ACCESS  read-create
    STATUS      current
    DESCRIPTION
        "The value of tmnxOamLTtraceAutoFcName specifies the forwarding class
         of the MPLS Echo request packets.

         The forwarding class name must be one of those defined in the
         tFCNameTable in TIMETRA-QOS-MIB.  The agent creates predefined
         entries in the tFCNameTable for 'premium', 'assured', and 'be'
         (for best-effort) forwarding classes.  The actual forwarding
         class encoding is controlled by the network egress LSP-EXP
         mappings."
    DEFVAL      { "be" }
    ::= { tmnxOamLTtraceAutoConfigEntry 5 }

tmnxOamLTtraceAutoProfile        OBJECT-TYPE
    SYNTAX      TProfile
    MAX-ACCESS  read-create
    STATUS      current
    DESCRIPTION
        "The value of tmnxOamLTtraceAutoProfile specifies the profile value to
         be used with the forwarding class specified in
         tmnxOamLTtraceAutoFcName.

         The profile value must be consistent with the specified forwarding
         class:
            'assured' = 'in' or 'out'
            'premium' = 'in'
            'be' = 'out'"
    DEFVAL      { out }
    ::= { tmnxOamLTtraceAutoConfigEntry 6 }

tmnxOamLTtraceAutoDiscIntvl      OBJECT-TYPE
    SYNTAX      Unsigned32 (60..1440)
    UNITS       "minutes"
    MAX-ACCESS  read-create
    STATUS      current
    DESCRIPTION
        "The value of tmnxOamLTtraceAutoDiscIntvl specifies number of minutes
         to wait before repeating LDP Tree Auto Discovery process."
    DEFVAL      { 60 }
    ::= { tmnxOamLTtraceAutoConfigEntry 7 }

tmnxOamLTtraceAutoMaxPath        OBJECT-TYPE
    SYNTAX      Unsigned32 (1..128)
    MAX-ACCESS  read-create
    STATUS      current
    DESCRIPTION
        "The value of tmnxOamLTtraceAutoMaxPath specifies the maximum number of
         paths that can be discovered for a selected IP Address FEC
         (tmnxOamLTtraceAutoTotalFecs)."
    DEFVAL      { 128 }
    ::= { tmnxOamLTtraceAutoConfigEntry 8 }

tmnxOamLTtraceAutoTrMaxTtl       OBJECT-TYPE
    SYNTAX      Unsigned32 (1..255)
    UNITS       "time-to-live value"
    MAX-ACCESS  read-create
    STATUS      current
    DESCRIPTION
        "The value of tmnxOamLTtraceAutoTrMaxTtl specifies the maximum label
         time-to-live value for an LSP trace request during the tree discovery."
    DEFVAL      { 30 }
    ::= { tmnxOamLTtraceAutoConfigEntry 9 }

tmnxOamLTtraceAutoTrTimeOut      OBJECT-TYPE
    SYNTAX      Unsigned32 (1..60)
    UNITS       "seconds"
    MAX-ACCESS  read-create
    STATUS      current
    DESCRIPTION
        "The value of tmnxOamLTtraceAutoTrTimeOut specifies the time-out value,
         in seconds, for an lsp trace request during the tree discovery."
    DEFVAL      { 30 }
    ::= { tmnxOamLTtraceAutoConfigEntry 10 }

tmnxOamLTtraceAutoTrMaxFailures  OBJECT-TYPE
    SYNTAX      Unsigned32 (1..10)
    UNITS       "timeouts"
    MAX-ACCESS  read-create
    STATUS      current
    DESCRIPTION
        "The value of tmnxOamLTtraceAutoTrMaxFailures specifies the maximum
         number of consecutive timeouts allowed before terminating an lsp trace
         request to a hop."
    DEFVAL      { 3 }
    ::= { tmnxOamLTtraceAutoConfigEntry 11 }

tmnxOamLTtraceAutoPolicy1        OBJECT-TYPE
    SYNTAX      TPolicyStatementNameOrEmpty
    MAX-ACCESS  read-create
    STATUS      current
    DESCRIPTION
        "The value of tmnxOamLTtraceAutoPolicy1 specifies the first policy used
         to filter LDP imported Address FECs."
    DEFVAL      { ''H }
    ::= { tmnxOamLTtraceAutoConfigEntry 12 }

tmnxOamLTtraceAutoPolicy2        OBJECT-TYPE
    SYNTAX      TPolicyStatementNameOrEmpty
    MAX-ACCESS  read-create
    STATUS      current
    DESCRIPTION
        "The value of tmnxOamLTtraceAutoPolicy2 specifies the second policy
         used to filter LDP imported Address FECs."
    DEFVAL      { ''H }
    ::= { tmnxOamLTtraceAutoConfigEntry 13 }

tmnxOamLTtraceAutoPolicy3        OBJECT-TYPE
    SYNTAX      TPolicyStatementNameOrEmpty
    MAX-ACCESS  read-create
    STATUS      current
    DESCRIPTION
        "The value of tmnxOamLTtraceAutoPolicy3 specifies the third policy used
         to filter LDP imported Address FECs."
    DEFVAL      { ''H }
    ::= { tmnxOamLTtraceAutoConfigEntry 14 }

tmnxOamLTtraceAutoPolicy4        OBJECT-TYPE
    SYNTAX      TPolicyStatementNameOrEmpty
    MAX-ACCESS  read-create
    STATUS      current
    DESCRIPTION
        "The value of tmnxOamLTtraceAutoPolicy4 specifies the fourth policy
         used to filter LDP imported Address FECs."
    DEFVAL      { ''H }
    ::= { tmnxOamLTtraceAutoConfigEntry 15 }

tmnxOamLTtraceAutoPolicy5        OBJECT-TYPE
    SYNTAX      TPolicyStatementNameOrEmpty
    MAX-ACCESS  read-create
    STATUS      current
    DESCRIPTION
        "The value of tmnxOamLTtraceAutoPolicy5 specifies the fifth policy used
         to filter LDP imported Address FECs."
    DEFVAL      { ''H }
    ::= { tmnxOamLTtraceAutoConfigEntry 16 }

tmnxOamLTtraceAutoProbeIntvl     OBJECT-TYPE
    SYNTAX      Unsigned32 (1..60)
    UNITS       "minutes"
    MAX-ACCESS  read-create
    STATUS      current
    DESCRIPTION
        "The value of tmnxOamLTtraceAutoProbeIntvl specifies the number of
         minutes to wait before repeating probing (pinging) a discovered path."
    DEFVAL      { 1 }
    ::= { tmnxOamLTtraceAutoConfigEntry 17 }

tmnxOamLTtraceAutoPrTimeOut      OBJECT-TYPE
    SYNTAX      Unsigned32 (1..3)
    UNITS       "minutes"
    MAX-ACCESS  read-create
    STATUS      current
    DESCRIPTION
        "The value of tmnxOamLTtraceAutoPrTimeOut specifies the time-out value,
         in minutes, for a ping request during probing.
         tmnxOamLTtraceAutoPrTimeOut cannot be greater than
         tmnxOamLTtraceAutoProbeIntvl."
    DEFVAL      { 1 }
    ::= { tmnxOamLTtraceAutoConfigEntry 18 }

tmnxOamLTtraceAutoPrMaxFailures  OBJECT-TYPE
    SYNTAX      Unsigned32 (1..10)
    UNITS       "timeouts"
    MAX-ACCESS  read-create
    STATUS      current
    DESCRIPTION
        "The value of tmnxOamLTtraceAutoPrMaxFailures specifies the maximum
         number of consecutive timeouts allowed before failing a path probe
         (ping)."
    DEFVAL      { 3 }
    ::= { tmnxOamLTtraceAutoConfigEntry 19 }

tmnxOamLTtraceAutoStatusTable    OBJECT-TYPE
    SYNTAX      SEQUENCE OF TmnxOamLTtraceAutoStatusEntry
    MAX-ACCESS  not-accessible
    STATUS      current
    DESCRIPTION
        "tmnxOamLTtraceAutoStatusTable contains an entry for operational
         information about each instance of Automatic (background) LDP Tree
         Trace."
    ::= { tmnxOamTraceRouteObjs 23 }

tmnxOamLTtraceAutoStatusEntry    OBJECT-TYPE
    SYNTAX      TmnxOamLTtraceAutoStatusEntry
    MAX-ACCESS  not-accessible
    STATUS      current
    DESCRIPTION
        "tmnxOamLTtraceAutoStatusEntry represents a row in the
         tmnxOamLTtraceAutoStatusTable.

         Entries cannot be created or deleted via SNMP Set operations. An entry
         is created whenever a row is created in tmnxOamLTtraceAutoConfigTable."
    INDEX       { vRtrID }
    ::= { tmnxOamLTtraceAutoStatusTable 1 }

TmnxOamLTtraceAutoStatusEntry    ::= SEQUENCE
{
    tmnxOamLTtraceAutoDiscoveryState INTEGER,
    tmnxOamLTtraceAutoTotalFecs      Unsigned32,
    tmnxOamLTtraceAutoDisFecs        Unsigned32,
    tmnxOamLTtraceAutoLastDisStart   TimeStamp,
    tmnxOamLTtraceAutoLastDisEnd     TimeStamp,
    tmnxOamLTtraceAutoLastDisDur     Unsigned32
}

tmnxOamLTtraceAutoDiscoveryState OBJECT-TYPE
    SYNTAX      INTEGER {
        initial    (0),
        inProgress (1),
        done       (2),
        halt       (3)
    }
    MAX-ACCESS  read-only
    STATUS      current
    DESCRIPTION
        "The value of tmnxOamLTtraceAutoDiscoveryState indicates the current
         state of the discovery process."
    ::= { tmnxOamLTtraceAutoStatusEntry 1 }

tmnxOamLTtraceAutoTotalFecs      OBJECT-TYPE
    SYNTAX      Unsigned32
    MAX-ACCESS  read-only
    STATUS      current
    DESCRIPTION
        "The value of tmnxOamLTtraceAutoTotalFecs indicates the number of
         Address FECs that have been selected for discovery during the current
         discovery process.

         An Address FEC imported from an LDP peer
         (TIMETRA-LDP-MIB::vRtrLdpAddrFecTable) is selected if it passes the
         associated policies (tmnxOamLTtraceAutoPolicy1..
         tmnxOamLTtraceAutoPolicy5)."
    ::= { tmnxOamLTtraceAutoStatusEntry 2 }

tmnxOamLTtraceAutoDisFecs        OBJECT-TYPE
    SYNTAX      Unsigned32
    MAX-ACCESS  read-only
    STATUS      current
    DESCRIPTION
        "The value of tmnxOamLTtraceAutoDisFecs indicates the number of
         selected Address FECs that have been discovered successfully during
         the current discovery process."
    ::= { tmnxOamLTtraceAutoStatusEntry 3 }

tmnxOamLTtraceAutoLastDisStart   OBJECT-TYPE
    SYNTAX      TimeStamp
    MAX-ACCESS  read-only
    STATUS      current
    DESCRIPTION
        "The value of tmnxOamLTtraceAutoLastDisStart indicates the
         sysUpTime when the last Auto discovery process started.  If
         no discovery process has started, the value will be 0."
    ::= { tmnxOamLTtraceAutoStatusEntry 4 }

tmnxOamLTtraceAutoLastDisEnd     OBJECT-TYPE
    SYNTAX      TimeStamp
    MAX-ACCESS  read-only
    STATUS      current
    DESCRIPTION
        "The value of tmnxOamLTtraceAutoLastDisEnd indicates the sysUpTime when
         the last Auto discovery process ended. Before the first discovery
         process ends, it would be 0. At the end of a discovery this value is
         set. This value is not reset during starting/restarting."
    ::= { tmnxOamLTtraceAutoStatusEntry 5 }

tmnxOamLTtraceAutoLastDisDur     OBJECT-TYPE
    SYNTAX      Unsigned32
    UNITS       "seconds"
    MAX-ACCESS  read-only
    STATUS      current
    DESCRIPTION
        "The value of tmnxOamLTtraceAutoLastDisDur indicates the time
         (in seconds) it took to finish the last discovery process.  If no test
         has been finished, the value is 0.  This value is updated only when
         a discovery ends."
    ::= { tmnxOamLTtraceAutoStatusEntry 6 }

tmnxOamLTtraceFecInfoTable       OBJECT-TYPE
    SYNTAX      SEQUENCE OF TmnxOamLTtraceFecInfoEntry
    MAX-ACCESS  not-accessible
    STATUS      current
    DESCRIPTION
        "tmnxOamLTtraceFecInfoTable contains entries for the operational
         information about the automatically selected FECs."
    ::= { tmnxOamTraceRouteObjs 24 }

tmnxOamLTtraceFecInfoEntry       OBJECT-TYPE
    SYNTAX      TmnxOamLTtraceFecInfoEntry
    MAX-ACCESS  not-accessible
    STATUS      current
    DESCRIPTION
        "tmnxOamLTtraceFecInfoEntry represents a row in the
         tmnxOamLTtraceFecInfoTable.

         Entries cannot be created and deleted via SNMP SET operations."
    INDEX       {
        vRtrID,
        tmnxOamLTtraceFecPrefixType,
        tmnxOamLTtraceFecPrefix,
        tmnxOamLTtraceFecPrefLen
    }
    ::= { tmnxOamLTtraceFecInfoTable 1 }

TmnxOamLTtraceFecInfoEntry       ::= SEQUENCE
{
    tmnxOamLTtraceFecPrefixType      InetAddressType,
    tmnxOamLTtraceFecPrefix          InetAddress,
    tmnxOamLTtraceFecPrefLen         InetAddressPrefixLength,
    tmnxOamLTtraceFecDiscoveryState  INTEGER,
    tmnxOamLTtraceFecDisStatusBits   TmnxOamLTtraceDisStatusBits,
    tmnxOamLTtraceFecDisPaths        Unsigned32,
    tmnxOamLTtraceFecFailedHops      Unsigned32,
    tmnxOamLTtraceFecLastDisEnd      TimeStamp,
    tmnxOamLTtraceFecFailedProbes    Unsigned32,
    tmnxOamLTtraceFecProbeState      INTEGER,
    tmnxOamLTtraceFecSendErrProbes   Unsigned32
}

tmnxOamLTtraceFecPrefixType      OBJECT-TYPE
    SYNTAX      InetAddressType
    MAX-ACCESS  not-accessible
    STATUS      current
    DESCRIPTION
        "The value of tmnxOamLTtraceFecPrefixType specifies the type of
         remote IP address stored in tmnxOamLTtraceFecPrefix.  Currently
         only ipv4 type is supported."
    ::= { tmnxOamLTtraceFecInfoEntry 1 }

tmnxOamLTtraceFecPrefix          OBJECT-TYPE
    SYNTAX      InetAddress (SIZE (0|4|16))
    MAX-ACCESS  not-accessible
    STATUS      current
    DESCRIPTION
        "The value of tmnxOamLTtraceFecPrefix indicates the Internet address
         prefix for an LDP based LSP associated with the OAM LDP Tree trace
         test."
    ::= { tmnxOamLTtraceFecInfoEntry 2 }

tmnxOamLTtraceFecPrefLen         OBJECT-TYPE
    SYNTAX      InetAddressPrefixLength
    MAX-ACCESS  not-accessible
    STATUS      current
    DESCRIPTION
        "The value of tmnxOamLTtraceFecPrefLen indicates the Internet address
         prefix length for the LDP based LSP associated with the OAM LDP Tree
         trace test."
    ::= { tmnxOamLTtraceFecInfoEntry 3 }

tmnxOamLTtraceFecDiscoveryState  OBJECT-TYPE
    SYNTAX      INTEGER {
        initial    (0),
        inProgress (1),
        done       (2)
    }
    MAX-ACCESS  read-only
    STATUS      current
    DESCRIPTION
        "The value of tmnxOamLTtraceFecDiscoveryState indicates the current
         state of the discovery process for the Address FEC."
    ::= { tmnxOamLTtraceFecInfoEntry 4 }

tmnxOamLTtraceFecDisStatusBits   OBJECT-TYPE
    SYNTAX      TmnxOamLTtraceDisStatusBits
    MAX-ACCESS  read-only
    STATUS      current
    DESCRIPTION
        "The value of tmnxOamLTtraceFecDisStatusBits indicates the current
         discovery status bits for the Address FEC."
    ::= { tmnxOamLTtraceFecInfoEntry 5 }

tmnxOamLTtraceFecDisPaths        OBJECT-TYPE
    SYNTAX      Unsigned32
    MAX-ACCESS  read-only
    STATUS      current
    DESCRIPTION
        "The value of tmnxOamLTtraceFecDisPaths indicates the number of
         discovered ECMP paths for the Address FEC."
    ::= { tmnxOamLTtraceFecInfoEntry 6 }

tmnxOamLTtraceFecFailedHops      OBJECT-TYPE
    SYNTAX      Unsigned32
    MAX-ACCESS  read-only
    STATUS      current
    DESCRIPTION
        "The value of tmnxOamLTtraceFecFailedHops indicates the number of hops
         from which no successful response was received."
    ::= { tmnxOamLTtraceFecInfoEntry 7 }

tmnxOamLTtraceFecLastDisEnd      OBJECT-TYPE
    SYNTAX      TimeStamp
    MAX-ACCESS  read-only
    STATUS      current
    DESCRIPTION
        "The value of tmnxOamLTtraceFecLastDisEnd indicates the sysUpTime when
         the FEC was last discovered."
    ::= { tmnxOamLTtraceFecInfoEntry 8 }

tmnxOamLTtraceFecFailedProbes    OBJECT-TYPE
    SYNTAX      Unsigned32
    MAX-ACCESS  read-only
    STATUS      current
    DESCRIPTION
        "The value of tmnxOamLTtraceFecFailedProbes indicates the number of
         discovered paths which are in failed probing state."
    ::= { tmnxOamLTtraceFecInfoEntry 9 }

tmnxOamLTtraceFecProbeState      OBJECT-TYPE
    SYNTAX      INTEGER {
        oK              (0),
        partiallyFailed (1),
        failed          (2)
    }
    MAX-ACCESS  read-only
    STATUS      current
    DESCRIPTION
        "The value of tmnxOamLTtraceFecProbeState indicates the current overall
         probing state for the discovered paths of the Address FEC. The
         tmnxOamLTtraceFecProbeState is considered as 'oK' when probing on all
         the associated discovered paths is OK. It is considered as 'failed'
         when probing on all the associated discovered paths failed. It is
         considered as partially failed when probing on one or more, but not
         all, discovered paths failed."
    ::= { tmnxOamLTtraceFecInfoEntry 10 }

tmnxOamLTtraceFecSendErrProbes   OBJECT-TYPE
    SYNTAX      Unsigned32
    MAX-ACCESS  read-only
    STATUS      current
    DESCRIPTION
        "The value of tmnxOamLTtraceFecSendErrProbes indicates the number of
         discovered paths which are experiencing problems in sending probe
         (ping) requests."
    ::= { tmnxOamLTtraceFecInfoEntry 11 }

tmnxOamLTtracePathInfoTable      OBJECT-TYPE
    SYNTAX      SEQUENCE OF TmnxOamLTtracePathInfoEntry
    MAX-ACCESS  not-accessible
    STATUS      current
    DESCRIPTION
        "tmnxOamLTtracePathInfoTable contains entries with operational
         information about the automatically discovered ECMP paths."
    ::= { tmnxOamTraceRouteObjs 25 }

tmnxOamLTtracePathInfoEntry      OBJECT-TYPE
    SYNTAX      TmnxOamLTtracePathInfoEntry
    MAX-ACCESS  not-accessible
    STATUS      current
    DESCRIPTION
        "tmnxOamLTtracePathInfoEntry represents a row in the
         tmnxOamLTtracePathInfoTable.

         Entries cannot be created and deleted via SNMP SET operations."
    INDEX       {
        vRtrID,
        tmnxOamLTtraceFecPrefixType,
        tmnxOamLTtraceFecPrefix,
        tmnxOamLTtraceFecPrefLen,
        tmnxOamLTtracePathDstAddrType,
        tmnxOamLTtracePathDstAddr
    }
    ::= { tmnxOamLTtracePathInfoTable 1 }

TmnxOamLTtracePathInfoEntry      ::= SEQUENCE
{
    tmnxOamLTtracePathDstAddrType    InetAddressType,
    tmnxOamLTtracePathDstAddr        InetAddress,
    tmnxOamLTtracePathRemAddrType    InetAddressType,
    tmnxOamLTtracePathRemoteAddr     InetAddress,
    tmnxOamLTtracePathEgrNhAddrType  InetAddressType,
    tmnxOamLTtracePathEgrNhAddr      InetAddress,
    tmnxOamLTtracePathDisTtl         Unsigned32,
    tmnxOamLTtracePathLastDisTime    TimeStamp,
    tmnxOamLTtracePathLastRc         TmnxOamPingRtnCode,
    tmnxOamLTtracePathProbeState     INTEGER,
    tmnxOamLTtracePathProbeTmOutCnt  Unsigned32,
    tmnxOamLTtracePathProbeSendErr   INTEGER
}

tmnxOamLTtracePathDstAddrType    OBJECT-TYPE
    SYNTAX      InetAddressType
    MAX-ACCESS  not-accessible
    STATUS      current
    DESCRIPTION
        "The value of tmnxOamLTtracePathDstAddrType indicates the type of
         Internet address stored in tmnxOamLTtracePathDstAddr."
    ::= { tmnxOamLTtracePathInfoEntry 1 }

tmnxOamLTtracePathDstAddr        OBJECT-TYPE
    SYNTAX      InetAddress (SIZE (0|4|16))
    MAX-ACCESS  not-accessible
    STATUS      current
    DESCRIPTION
        "The value of tmnxOamLTtracePathDstAddr indicates the destination IP
         address (127 Address) of a path for a given LDP based LSP associated
         with the OAM LDP Tree trace test."
    ::= { tmnxOamLTtracePathInfoEntry 2 }

tmnxOamLTtracePathRemAddrType    OBJECT-TYPE
    SYNTAX      InetAddressType
    MAX-ACCESS  read-only
    STATUS      current
    DESCRIPTION
        "The value of tmnxOamLTtracePathRemAddrType indicates the type of
         Internet address stored in tmnxOamLTtracePathRemoteAddr."
    ::= { tmnxOamLTtracePathInfoEntry 3 }

tmnxOamLTtracePathRemoteAddr     OBJECT-TYPE
    SYNTAX      InetAddress (SIZE (0|4|16))
    MAX-ACCESS  read-only
    STATUS      current
    DESCRIPTION
        "The value of tmnxOamLTtracePathRemoteAddr indicates the associated
         interface IP address or the router ID of the egress router."
    ::= { tmnxOamLTtracePathInfoEntry 4 }

tmnxOamLTtracePathEgrNhAddrType  OBJECT-TYPE
    SYNTAX      InetAddressType
    MAX-ACCESS  read-only
    STATUS      current
    DESCRIPTION
        "The value of tmnxOamLTtracePathEgrNhAddrType indicates the type of
         Internet address stored in tmnxOamLTtracePathEgrNhAddr."
    ::= { tmnxOamLTtracePathInfoEntry 5 }

tmnxOamLTtracePathEgrNhAddr      OBJECT-TYPE
    SYNTAX      InetAddress (SIZE (0|4|16))
    MAX-ACCESS  read-only
    STATUS      current
    DESCRIPTION
        "The value of tmnxOamLTtracePathEgrNhAddr indicates the next hop IP
         address (wrt the ingress router) used to reach the associated ECMP
         path endpoint."
    ::= { tmnxOamLTtracePathInfoEntry 6 }

tmnxOamLTtracePathDisTtl         OBJECT-TYPE
    SYNTAX      Unsigned32
    MAX-ACCESS  read-only
    STATUS      current
    DESCRIPTION
        "The value of tmnxOamLTtracePathDisTtl indicates the label time-to-live
         value used to discover the egress router for the path."
    ::= { tmnxOamLTtracePathInfoEntry 7 }

tmnxOamLTtracePathLastDisTime    OBJECT-TYPE
    SYNTAX      TimeStamp
    MAX-ACCESS  read-only
    STATUS      current
    DESCRIPTION
        "The value of tmnxOamLTtracePathLastDisTime indicates the sysUpTime
         when the path was last discovered."
    ::= { tmnxOamLTtracePathInfoEntry 8 }

tmnxOamLTtracePathLastRc         OBJECT-TYPE
    SYNTAX      TmnxOamPingRtnCode
    MAX-ACCESS  read-only
    STATUS      current
    DESCRIPTION
        "The value of tmnxOamLTtracePathLastRc indicates the OAM return code
         received in the OAM ping response."
    ::= { tmnxOamLTtracePathInfoEntry 9 }

tmnxOamLTtracePathProbeState     OBJECT-TYPE
    SYNTAX      INTEGER {
        oK     (0),
        failed (1)
    }
    MAX-ACCESS  read-only
    STATUS      current
    DESCRIPTION
        "The value of tmnxOamLTtracePathProbeState indicates the current
         probing (ping) state for the discovered ECMP path. The
         tmnxOamLTtracePathProbeState is considered as 'failed' when number of
         consecutive timeouts for the ping request reached its maximum allowed
         limit (tmnxOamLTtraceAutoPrMaxFailures). The
         tmnxOamLTtracePathProbeState is considered as 'oK' after receiving a
         successful ping response for the associated path."
    ::= { tmnxOamLTtracePathInfoEntry 10 }

tmnxOamLTtracePathProbeTmOutCnt  OBJECT-TYPE
    SYNTAX      Unsigned32
    MAX-ACCESS  read-only
    STATUS      current
    DESCRIPTION
        "The value of tmnxOamLTtracePathProbeTmOutCnt indicates the number of
         consecutive timeouts for the associated ping request. This
         tmnxOamLTtracePathProbeTmOutCnt is reset to 0 after receiving a
         successful ping response from the path destination."
    ::= { tmnxOamLTtracePathInfoEntry 11 }

tmnxOamLTtracePathProbeSendErr   OBJECT-TYPE
    SYNTAX      INTEGER {
        oK     (0),
        failed (1)
    }
    MAX-ACCESS  read-only
    STATUS      current
    DESCRIPTION
        "The value of tmnxOamLTtracePathProbeSendErr indicates the state of the
         last path probe (ping) request.

         The tmnxOamLTtracePathProbeSendErr is considered as 'failed' if the
         last probe (ping) request could not be sent due to some local failure
         else it is 'oK'."
    ::= { tmnxOamLTtracePathInfoEntry 12 }

tmnxOamVccvTrCtlTable            OBJECT-TYPE
    SYNTAX      SEQUENCE OF TmnxOamVccvTrCtlEntry
    MAX-ACCESS  not-accessible
    STATUS      current
    DESCRIPTION
        "Each row in tmnxOamVccvTrCtlTable contains the VCCV-specific
         configuration information needed to launch a VCCV (Virtual Circuit
         Connectivity Verification) trace route test.  The rest of the
         configuration information needed to launch the test resides in the
         corresponding row of tmnxOamTrCtlTable.

         Results of VCCV trace route tests are stored in tmnxOamTrResultsTable,
         tmnxOamTrProbeHistoryTable, and tmnxOamVccvTrNextPwSegmentTable.

         Four types of VCCV trace route tests are supported:  AII Type 2,
         FEC-128 Pseudowire, Spoke SDP FEC, and Transport Profile Static.  AII
         Type 2 and Spoke SDP FEC offer two ways to specify a VCCV trace route
         FEC-129 Pseudowire test.

         In the Transport Profile Static case, the test type is configured
         (using tmnxOamVccvTrCtlTestSubMode).  In the other three cases, the
         test type is not configured (i.e. the default
         tmnxOamVccvTrCtlTestSubMode value 'unspecified(1)' is used).

         The following table has a row for each VCCV trace route test type,
         showing the mandatory and optional objects applicable to the test
         type. Abbreviated VCCV trace route test type names are used.

         Test
         Type   Mandatory Objects               Optional Objects
         ------ ------------------------------ ---------------------------------
         aiiTY2 tmnxOamVccvTrCtlSaiiAcId        tmnxOamVccvTrCtlReplyMode
                tmnxOamVccvTrCtlSaiiGlobalId
                tmnxOamVccvTrCtlSaiiPrefix
                tmnxOamVccvTrCtlTaiiAcId
                tmnxOamVccvTrCtlTaiiGlobalId
                tmnxOamVccvTrCtlTaiiPrefix

         FEC128 tmnxOamVccvTrCtlSdpIdVcId       tmnxOamVccvTrCtlReplyMode
                                               *tmnxOamVccvTrCtlSwitTgtFecType
                                               *tmnxOamVccvTrTgStaticCtlAgi
                                               *tmnxOamVccvTrTgStaticCtlSaiiGlbl
                                               *tmnxOamVccvTrTgStaticCtlSaiiNode
                                               *tmnxOamVccvTrTgStaticCtlSaiiAcId
                                               *tmnxOamVccvTrTgStaticCtlTaiiGlbl
                                               *tmnxOamVccvTrTgStaticCtlTaiiNode
                                               *tmnxOamVccvTrTgStaticCtlTaiiAcId


         sdpFEC tmnxOamVccvTrCtlSpokeSdpId     *tmnxOamVccvTrCtlSaiiAcId
                                               *tmnxOamVccvTrCtlSaiiGlobalId
                                               *tmnxOamVccvTrCtlSaiiPrefix
                                               *tmnxOamVccvTrCtlTaiiAcId
                                               *tmnxOamVccvTrCtlTaiiGlobalId
                                               *tmnxOamVccvTrCtlTaiiPrefix
                                                tmnxOamVccvTrCtlReplyMode

         TPST   tmnxOamVccvTrCtlSdpIdVcId      *tmnxOamTrCtlSrcAddrType
                tmnxOamVccvTrCtlTestSubMode    *tmnxOamTrCtlSrcAddress
                                                tmnxOamVccvTrCtlAssocChannel
                                               #tmnxOamVccvTrCtlSwitTgtFecType
                                               #tmnxOamVccvTrTgFec128CtlSrcAddrT
                                               #tmnxOamVccvTrTgFec128CtlSrcAddr
                                               #tmnxOamVccvTrTgFec128CtlDstAddrT
                                               #tmnxOamVccvTrTgFec128CtlDstAddr
                                               #tmnxOamVccvTrTgFec128CtlPwId
                                               #tmnxOamVccvTrTgFec128CtlPwType

         ALL    N/A                             tmnxOamTrCtlDataSize
                                                tmnxOamTrCtlFcName
                                                tmnxOamTrCtlInitialTtl
                                                tmnxOamTrCtlInterval
                                                tmnxOamTrCtlMaxFailures
                                                tmnxOamTrCtlMaxTtl
                                                tmnxOamTrCtlProbesPerHop
                                                tmnxOamTrCtlProfile
                                                tmnxOamTrCtlTimeOut
         ------ ------------------------------ ---------------------------------

         In the table above,
         1.  The optional objects in the ALL row apply to all four VCCV trace
             route test types.
         2.  The characters '*' and '#' each mark an independent set of optional
             objects which must all be specified, or must all be unspecified.

         When an object combination other than a combination listed above is
         specified, values will be rejected or ignored, or the test will fail."
    REFERENCE
        "RFC 5085:  Pseudowire Virtual Circuit Connectivity Verification (VCCV):
         A Control Channel for Pseudowires"
    ::= { tmnxOamTraceRouteObjs 26 }

tmnxOamVccvTrCtlEntry            OBJECT-TYPE
    SYNTAX      TmnxOamVccvTrCtlEntry
    MAX-ACCESS  not-accessible
    STATUS      current
    DESCRIPTION
        "The system creates a row in tmnxOamVccvTrCtlTable when a row is
         created in tmnxOamTrCtlTable with tmnxOamTrCtlTestMode set to
         'vccvTraceRoute'.

         The system deletes a row in tmnxOamVccvTrCtlTable when the
         corresponding row in tmnxOamTrCtlTable is deleted."
    INDEX       {
        tmnxOamTrCtlOwnerIndex,
        tmnxOamTrCtlTestIndex
    }
    ::= { tmnxOamVccvTrCtlTable 1 }

TmnxOamVccvTrCtlEntry            ::= SEQUENCE
{
    tmnxOamVccvTrCtlSdpIdVcId        SdpBindId,
    tmnxOamVccvTrCtlReplyMode        INTEGER,
    tmnxOamVccvTrCtlSpokeSdpId       TmnxSpokeSdpIdOrZero,
    tmnxOamVccvTrCtlSaiiGlobalId     TmnxPwGlobalIdOrZero,
    tmnxOamVccvTrCtlSaiiPrefix       Unsigned32,
    tmnxOamVccvTrCtlSaiiAcId         Unsigned32,
    tmnxOamVccvTrCtlTaiiGlobalId     TmnxPwGlobalIdOrZero,
    tmnxOamVccvTrCtlTaiiPrefix       Unsigned32,
    tmnxOamVccvTrCtlTaiiAcId         Unsigned32,
    tmnxOamVccvTrCtlTestSubMode      TmnxOamVccvTestSubMode,
    tmnxOamVccvTrCtlAssocChannel     TmnxOamVccvAssocChannel,
    tmnxOamVccvTrCtlSwitTgtFecType   TmnxOamVccvSwitTgtFecType
}

tmnxOamVccvTrCtlSdpIdVcId        OBJECT-TYPE
    SYNTAX      SdpBindId
    MAX-ACCESS  read-create
    STATUS      current
    DESCRIPTION
        "The value of tmnxOamVccvTrCtlSdpIdVcId specifies the SDP binding of
         the pseudowire to be tested by a VCCV trace route test.

         The all-zeros value indicates an unused SDP binding.

         The supported object combinations for VCCV trace route tests are
         listed in the tmnxOamVccvTrCtlTable DESCRIPTION clause."
    DEFVAL      { '0000000000000000'h }
    ::= { tmnxOamVccvTrCtlEntry 1 }

tmnxOamVccvTrCtlReplyMode        OBJECT-TYPE
    SYNTAX      INTEGER {
        ip             (2),
        controlChannel (4)
    }
    MAX-ACCESS  read-create
    STATUS      current
    DESCRIPTION
        "The value of tmnxOamVccvTrCtlReplyMode specifies the band to be used by
         the echo reply.
             ip (2)                 out-of-band reply
             controlChannel (4)     inband reply

         The supported object combinations for VCCV trace route tests are
         listed in the tmnxOamVccvTrCtlTable DESCRIPTION clause."
    REFERENCE
        "RFC 4379, 'Detecting Multi-Protocol Label Switched (MPLS) Data Plane
         Failures', Section 3 ('Packet Format')."
    DEFVAL      { controlChannel }
    ::= { tmnxOamVccvTrCtlEntry 2 }

tmnxOamVccvTrCtlSpokeSdpId       OBJECT-TYPE
    SYNTAX      TmnxSpokeSdpIdOrZero
    MAX-ACCESS  read-create
    STATUS      current
    DESCRIPTION
        "The value of tmnxOamVccvTrCtlSpokeSdpId specifies the spoke SDP
         identifier to be used when performing a VCCV trace route test on a FEC
         129 pseudowire.

         A value of zero indicates that no spoke SDP identifier has been
         configured.

         The supported object combinations for VCCV trace route tests are
         listed in the tmnxOamVccvTrCtlTable DESCRIPTION clause."
    DEFVAL      { 0 }
    ::= { tmnxOamVccvTrCtlEntry 3 }

tmnxOamVccvTrCtlSaiiGlobalId     OBJECT-TYPE
    SYNTAX      TmnxPwGlobalIdOrZero
    MAX-ACCESS  read-create
    STATUS      current
    DESCRIPTION
        "The value of tmnxOamVccvTrCtlSaiiGlobalId specifies the global
         identifier of the Source Attachment Individual Identifier (SAII) to be
         used when testing a FEC 129 AII Type 2 pseudowire.

         A value of zero indicates that no global identifier has been
         configured.

         The supported object combinations for VCCV trace route tests are
         listed in the tmnxOamVccvTrCtlTable DESCRIPTION clause."
    REFERENCE
        "RFC 5003, 'Attachment Individual Identifier (AII) Types for
         Aggregation', Section 3.2, 'AII Type 2'"
    DEFVAL      { 0 }
    ::= { tmnxOamVccvTrCtlEntry 4 }

tmnxOamVccvTrCtlSaiiPrefix       OBJECT-TYPE
    SYNTAX      Unsigned32
    MAX-ACCESS  read-create
    STATUS      current
    DESCRIPTION
        "The value of tmnxOamVccvTrCtlSaiiPrefix specifies the prefix of the
         Source Attachment Individual Identifier (SAII) to be used when testing
         a FEC 129 AII Type 2 pseudowire.

         A value of zero indicates that no prefix has been configured.

         The supported object combinations for VCCV trace route tests are
         listed in the tmnxOamVccvTrCtlTable DESCRIPTION clause."
    REFERENCE
        "RFC 5003, 'Attachment Individual Identifier (AII) Types for
         Aggregation', Section 3.2, 'AII Type 2'"
    DEFVAL      { 0 }
    ::= { tmnxOamVccvTrCtlEntry 5 }

tmnxOamVccvTrCtlSaiiAcId         OBJECT-TYPE
    SYNTAX      Unsigned32
    MAX-ACCESS  read-create
    STATUS      current
    DESCRIPTION
        "The value of tmnxOamVccvTrCtlSaiiAcId specifies the attachment circuit
         identifier of the Source Attachment Individual Identifier (SAII) to be
         used when testing a FEC 129 AII Type 2 pseudowire.

         A value of zero indicates that no attachment circuit identifier has
         been configured.

         The supported object combinations for VCCV trace route tests are
         listed in the tmnxOamVccvTrCtlTable DESCRIPTION clause."
    REFERENCE
        "RFC 5003, 'Attachment Individual Identifier (AII) Types for
         Aggregation', Section 3.2, 'AII Type 2'"
    DEFVAL      { 0 }
    ::= { tmnxOamVccvTrCtlEntry 6 }

tmnxOamVccvTrCtlTaiiGlobalId     OBJECT-TYPE
    SYNTAX      TmnxPwGlobalIdOrZero
    MAX-ACCESS  read-create
    STATUS      current
    DESCRIPTION
        "The value of tmnxOamVccvTrCtlTaiiGlobalId specifies the global
         identifier of the Target Attachment Individual Identifier (TAII) to be
         used when testing a FEC 129 AII Type 2 pseudowire.

         A value of zero indicates that no global identifier has been
         configured.

         The supported object combinations for VCCV trace route tests are
         listed in the tmnxOamVccvTrCtlTable DESCRIPTION clause."
    REFERENCE
        "RFC 5003, 'Attachment Individual Identifier (AII) Types for
         Aggregation', Section 3.2, 'AII Type 2'"
    DEFVAL      { 0 }
    ::= { tmnxOamVccvTrCtlEntry 7 }

tmnxOamVccvTrCtlTaiiPrefix       OBJECT-TYPE
    SYNTAX      Unsigned32
    MAX-ACCESS  read-create
    STATUS      current
    DESCRIPTION
        "The value of tmnxOamVccvTrCtlTaiiPrefix specifies the prefix of the
         Target Attachment Individual Identifier (TAII) to be used when testing
         a FEC 129 AII Type 2 pseudowire.

         A value of zero indicates that no prefix has been configured.

         The supported object combinations for VCCV trace route tests are
         listed in the tmnxOamVccvTrCtlTable DESCRIPTION clause."
    REFERENCE
        "RFC 5003, 'Attachment Individual Identifier (AII) Types for
         Aggregation', Section 3.2, 'AII Type 2'"
    DEFVAL      { 0 }
    ::= { tmnxOamVccvTrCtlEntry 8 }

tmnxOamVccvTrCtlTaiiAcId         OBJECT-TYPE
    SYNTAX      Unsigned32
    MAX-ACCESS  read-create
    STATUS      current
    DESCRIPTION
        "The value of tmnxOamVccvTrCtlTaiiAcId specifies the attachment circuit
         identifier of the Target Attachment Individual Identifier (TAII) to be
         used when testing a FEC 129 AII Type 2 pseudowire.

         A value of zero indicates that no attachment circuit identifier has
         been configured.

         The supported object combinations for VCCV trace route tests are
         listed in the tmnxOamVccvTrCtlTable DESCRIPTION clause."
    REFERENCE
        "RFC 5003, 'Attachment Individual Identifier (AII) Types for
         Aggregation', Section 3.2, 'AII Type 2'"
    DEFVAL      { 0 }
    ::= { tmnxOamVccvTrCtlEntry 9 }

tmnxOamVccvTrCtlTestSubMode      OBJECT-TYPE
    SYNTAX      TmnxOamVccvTestSubMode
    MAX-ACCESS  read-create
    STATUS      current
    DESCRIPTION
        "The value of tmnxOamVccvTrCtlTestSubMode specifies the type of VCCV
         trace route test to perform.

         When this object is 'unspecified(1)', the type of VCCV trace route
         test to be performed is determined when the test is started, from the
         set of tmnxOamVccvTrCtlTable objects configured with non-default
         values.

         If there is a mismatch between tmnxOamVccvTrCtlTestSubMode and the type
         of the pseudowire to be tested, the test will fail.  For example, if
         tmnxOamVccvTrCtlTestSubMode is 'static(2)', and there is no
         TIMETRA-SDP-MIB::sdpBindPwPathTable row for the test's SDP binding,
         the test will fail.

         The supported object combinations for VCCV trace route tests are
         listed in the tmnxOamVccvTrCtlTable DESCRIPTION clause."
    DEFVAL      { unspecified }
    ::= { tmnxOamVccvTrCtlEntry 10 }

tmnxOamVccvTrCtlAssocChannel     OBJECT-TYPE
    SYNTAX      TmnxOamVccvAssocChannel
    MAX-ACCESS  read-create
    STATUS      current
    DESCRIPTION
        "The value of tmnxOamVccvTrCtlAssocChannel specifies the launched echo
         request's usage of the Associated Channel (ACH) mechanism, when
         performing an MPLS-TP VCCV trace route test.

         When tmnxOamVccvTrCtlTestSubMode is 'static(2)', the default value for
         tmnxOamVccvTrCtlAssocChannel is 'nonIp(2)'.

         The supported object combinations for VCCV trace route tests are
         listed in the tmnxOamVccvTrCtlTable DESCRIPTION clause."
    DEFVAL      { notApplicable }
    ::= { tmnxOamVccvTrCtlEntry 11 }

tmnxOamVccvTrCtlSwitTgtFecType   OBJECT-TYPE
    SYNTAX      TmnxOamVccvSwitTgtFecType
    MAX-ACCESS  read-create
    STATUS      current
    DESCRIPTION
        "The value of tmnxOamVccvTrCtlSwitTgtFecType specifies the type of
         downstream FEC (Forward Equivalence Class) segment to be tested.

         This object must be set to a non-default value when the path to be
         tested starts with a FEC segment, and switches to a FEC segment with a
         different type.  For example, if the path to be tested starts with a
         static FEC, and switches to FEC 128, this object must be set to
         'fec128(2)'."
    DEFVAL      { none }
    ::= { tmnxOamVccvTrCtlEntry 12 }

tmnxOamVccvTrNextPwSegmentTable  OBJECT-TYPE
    SYNTAX      SEQUENCE OF TmnxOamVccvTrNextPwSegmentEntry
    MAX-ACCESS  not-accessible
    STATUS      current
    DESCRIPTION
        "Defines a table for storing the results of an OAM 'vccvTraceRoute'
         probe operation where a VCCV next hop list is returned.

         An entry in this table is created when the result of an OAM
         'vccvTraceRoute' probe is determined. An entry is removed from this
         table when its corresponding tmnxOamTrCtlEntry is deleted."
    ::= { tmnxOamTraceRouteObjs 27 }

tmnxOamVccvTrNextPwSegmentEntry  OBJECT-TYPE
    SYNTAX      TmnxOamVccvTrNextPwSegmentEntry
    MAX-ACCESS  not-accessible
    STATUS      current
    DESCRIPTION
        "Defines an entry in the tmnxOamVccvTrNextPwSegmentTable. The first two
         index elements identify the tmnxOamTrCtlEntry that a
         tmnxOamVccvTrNextPwSegmentEntry belongs to.  The third index element
         identifies an OAM trace route test run.  The fourth, fifth and sixth
         index elements select a single OAM 'vccvTraceRoute' reply."
    INDEX       {
        tmnxOamTrCtlOwnerIndex,
        tmnxOamTrCtlTestIndex,
        tmnxOamTrResultsTestRunIndex,
        tmnxOamTrProbeHistoryIndex,
        tmnxOamTrProbeHistoryHopIndex,
        tmnxOamTrProbeHistoryProbeIndex
    }
    ::= { tmnxOamVccvTrNextPwSegmentTable 1 }

TmnxOamVccvTrNextPwSegmentEntry  ::= SEQUENCE
{
    tmnxOamVccvTrNextPwID            TmnxVcIdOrNone,
    tmnxOamVccvTrNextPwType          SdpBindVcType,
    tmnxOamVccvTrNextSenderAddrType  InetAddressType,
    tmnxOamVccvTrNextSenderAddr      InetAddress,
    tmnxOamVccvTrNextRemoteAddrType  InetAddressType,
    tmnxOamVccvTrNextRemoteAddr      InetAddress,
    tmnxOamVccvTrNextSaiiGlobalId    TmnxPwGlobalIdOrZero,
    tmnxOamVccvTrNextSaiiPrefix      Unsigned32,
    tmnxOamVccvTrNextSaiiAcId        Unsigned32,
    tmnxOamVccvTrNextTaiiGlobalId    TmnxPwGlobalIdOrZero,
    tmnxOamVccvTrNextTaiiPrefix      Unsigned32,
    tmnxOamVccvTrNextTaiiAcId        Unsigned32,
    tmnxOamVccvTrNextTpAgi           OCTET STRING,
    tmnxOamVccvTrNextTpSaiiGlobalId  TmnxMplsTpGlobalID,
    tmnxOamVccvTrNextTpSaiiNodeId    TmnxMplsTpNodeID,
    tmnxOamVccvTrNextTpSaiiAcId      Unsigned32,
    tmnxOamVccvTrNextTpTaiiGlobalId  TmnxMplsTpGlobalID,
    tmnxOamVccvTrNextTpTaiiNodeId    TmnxMplsTpNodeID,
    tmnxOamVccvTrNextTpTaiiAcId      Unsigned32
}

tmnxOamVccvTrNextPwID            OBJECT-TYPE
    SYNTAX      TmnxVcIdOrNone
    MAX-ACCESS  read-only
    STATUS      current
    DESCRIPTION
        "The value of tmnxOamVccvTrNextPwID indicates the next-hop pseudo-wire
         in the trace route operation for a specific 'vccvTraceRoute' probe
         reply. A value of '0' indicates that there are no further next-hops
         for a specific trace route operation."
    ::= { tmnxOamVccvTrNextPwSegmentEntry 1 }

tmnxOamVccvTrNextPwType          OBJECT-TYPE
    SYNTAX      SdpBindVcType
    MAX-ACCESS  read-only
    STATUS      current
    DESCRIPTION
        "The value of tmnxOamVccvTrNextPwType indicates the next-hop
         pseudo-wire type in the trace route operation for a specific
         'vccvTraceRoute' probe reply."
    ::= { tmnxOamVccvTrNextPwSegmentEntry 2 }

tmnxOamVccvTrNextSenderAddrType  OBJECT-TYPE
    SYNTAX      InetAddressType
    MAX-ACCESS  read-only
    STATUS      current
    DESCRIPTION
        "The value of tmnxOamVccvTrNextSenderAddrType indicates the next-hop
         sender IP address type in the trace route operation for a specific
         'vccvTraceRoute' probe reply."
    ::= { tmnxOamVccvTrNextPwSegmentEntry 3 }

tmnxOamVccvTrNextSenderAddr      OBJECT-TYPE
    SYNTAX      InetAddress (SIZE (0|4|16))
    MAX-ACCESS  read-only
    STATUS      current
    DESCRIPTION
        "The value of tmnxOamVccvTrNextSenderAddr indicates the next-hop sender
         IP address in the trace route operation for a specific
         'vccvTraceRoute' probe reply."
    ::= { tmnxOamVccvTrNextPwSegmentEntry 4 }

tmnxOamVccvTrNextRemoteAddrType  OBJECT-TYPE
    SYNTAX      InetAddressType
    MAX-ACCESS  read-only
    STATUS      current
    DESCRIPTION
        "The value of tmnxOamVccvTrNextRemoteAddrType indicates the next-hop
         remote IP address type in the trace route operation for a specific
         'vccvTraceRoute' probe reply."
    ::= { tmnxOamVccvTrNextPwSegmentEntry 5 }

tmnxOamVccvTrNextRemoteAddr      OBJECT-TYPE
    SYNTAX      InetAddress (SIZE (0|4|16))
    MAX-ACCESS  read-only
    STATUS      current
    DESCRIPTION
        "The value of tmnxOamVccvTrNextRemoteAddr indicates the next-hop remote
         IP address in the trace route operation for a specific
         'vccvTraceRoute' probe reply."
    ::= { tmnxOamVccvTrNextPwSegmentEntry 6 }

tmnxOamVccvTrNextSaiiGlobalId    OBJECT-TYPE
    SYNTAX      TmnxPwGlobalIdOrZero
    MAX-ACCESS  read-only
    STATUS      current
    DESCRIPTION
        "The value of tmnxOamVccvTrNextSaiiGlobalId indicates the global
         identifier of the Source Attachment Individual Identifier (SAII) of a
         specific 'vccvTraceRoute' probe reply.

         A non-zero value is returned if a FEC 129 AII Type 2 pseudowire was
         probed.  Otherwise, zero is returned."
    REFERENCE
        "RFC 5003 Section 3.2"
    ::= { tmnxOamVccvTrNextPwSegmentEntry 7 }

tmnxOamVccvTrNextSaiiPrefix      OBJECT-TYPE
    SYNTAX      Unsigned32
    MAX-ACCESS  read-only
    STATUS      current
    DESCRIPTION
        "The value of tmnxOamVccvTrNextSaiiPrefix indicates the prefix of the
         Source Attachment Individual Identifier (SAII) of a specific
         'vccvTraceRoute' probe reply.

         A non-zero value is returned if a FEC 129 AII Type 2 pseudowire was
         probed.  Otherwise, zero is returned."
    REFERENCE
        "RFC 5003 Section 3.2"
    ::= { tmnxOamVccvTrNextPwSegmentEntry 8 }

tmnxOamVccvTrNextSaiiAcId        OBJECT-TYPE
    SYNTAX      Unsigned32
    MAX-ACCESS  read-only
    STATUS      current
    DESCRIPTION
        "The value of tmnxOamVccvTrNextSaiiAcId indicates the attachment
         circuit identifier of the Source Attachment Individual Identifier
         (SAII) of a specific 'vccvTraceRoute' probe reply.

         A non-zero value is returned if a FEC 129 AII Type 2 pseudowire was
         probed.  Otherwise, zero is returned."
    REFERENCE
        "RFC 5003 Section 3.2"
    ::= { tmnxOamVccvTrNextPwSegmentEntry 9 }

tmnxOamVccvTrNextTaiiGlobalId    OBJECT-TYPE
    SYNTAX      TmnxPwGlobalIdOrZero
    MAX-ACCESS  read-only
    STATUS      current
    DESCRIPTION
        "The value of tmnxOamVccvTrNextTaiiGlobalId indicates the global
         identifier of the Target Attachment Individual Identifier (TAII) of a
         specific 'vccvTraceRoute' probe reply.

         A non-zero value is returned if a FEC 129 AII Type 2 pseudowire was
         probed.  Otherwise, zero is returned."
    REFERENCE
        "RFC 5003 Section 3.2"
    ::= { tmnxOamVccvTrNextPwSegmentEntry 10 }

tmnxOamVccvTrNextTaiiPrefix      OBJECT-TYPE
    SYNTAX      Unsigned32
    MAX-ACCESS  read-only
    STATUS      current
    DESCRIPTION
        "The value of tmnxOamVccvTrNextTaiiPrefix indicates the prefix of the
         Target Attachment Individual Identifier (TAII) of a specific
         'vccvTraceRoute' probe reply.

         A non-zero value is returned if a FEC 129 AII Type 2 pseudowire was
         probed.  Otherwise, zero is returned."
    REFERENCE
        "RFC 5003 Section 3.2"
    ::= { tmnxOamVccvTrNextPwSegmentEntry 11 }

tmnxOamVccvTrNextTaiiAcId        OBJECT-TYPE
    SYNTAX      Unsigned32
    MAX-ACCESS  read-only
    STATUS      current
    DESCRIPTION
        "The value of tmnxOamVccvTrNextTaiiAcId indicates the attachment
         circuit identifier of the Target Attachment Individual Identifier
         (TAII) of a specific 'vccvTraceRoute' probe reply.

         A non-zero value is returned if a FEC 129 AII Type 2 pseudowire was
         probed.  Otherwise, zero is returned."
    REFERENCE
        "RFC 5003 Section 3.2"
    ::= { tmnxOamVccvTrNextPwSegmentEntry 12 }

tmnxOamVccvTrNextTpAgi           OBJECT-TYPE
    SYNTAX      OCTET STRING (SIZE (8))
    MAX-ACCESS  read-only
    STATUS      current
    DESCRIPTION
        "The value of tmnxOamVccvTrNextTpAgi indicates the Service Identifier
         field of the RFC 6426 Static Pseudowire Sub-TLV of the reply PDU.

         If a pseudowire other than an MPLS-TP pseudowire was probed, the
         all-zeros value is returned."
    REFERENCE
        "RFC 6426, 'MPLS On-Demand Connectivity Verification and Route Tracing',
         section 2.3.2, 'Static Pseudowire Sub-TLV'."
    ::= { tmnxOamVccvTrNextPwSegmentEntry 13 }

tmnxOamVccvTrNextTpSaiiGlobalId  OBJECT-TYPE
    SYNTAX      TmnxMplsTpGlobalID
    MAX-ACCESS  read-only
    STATUS      current
    DESCRIPTION
        "The value of tmnxOamVccvTrNextTpSaiiGlobalId indicates the Source
         Global ID field of the RFC 6426 Static Pseudowire Sub-TLV of the reply
         PDU.

         If a pseudowire other than an MPLS-TP pseudowire was probed, zero is
         returned."
    REFERENCE
        "RFC 6426, 'MPLS On-Demand Connectivity Verification and Route Tracing',
         section 2.3.2, 'Static Pseudowire Sub-TLV'."
    ::= { tmnxOamVccvTrNextPwSegmentEntry 14 }

tmnxOamVccvTrNextTpSaiiNodeId    OBJECT-TYPE
    SYNTAX      TmnxMplsTpNodeID
    MAX-ACCESS  read-only
    STATUS      current
    DESCRIPTION
        "The value of tmnxOamVccvTrNextTpSaiiNodeId indicates the Source Node
         ID field of the RFC 6426 Static Pseudowire Sub-TLV of the reply PDU.

         If a pseudowire other than an MPLS-TP pseudowire was probed, zero is
         returned."
    REFERENCE
        "RFC 6426, 'MPLS On-Demand Connectivity Verification and Route Tracing',
         section 2.3.2, 'Static Pseudowire Sub-TLV'."
    ::= { tmnxOamVccvTrNextPwSegmentEntry 15 }

tmnxOamVccvTrNextTpSaiiAcId      OBJECT-TYPE
    SYNTAX      Unsigned32
    MAX-ACCESS  read-only
    STATUS      current
    DESCRIPTION
        "The value of tmnxOamVccvTrNextTpSaiiAcId indicates the Source
         Attachment Circuit ID field of the RFC 6426 Static Pseudowire Sub-TLV
         of the reply PDU.

         If a pseudowire other than an MPLS-TP pseudowire was probed, zero is
         returned."
    REFERENCE
        "RFC 6426, 'MPLS On-Demand Connectivity Verification and Route Tracing',
         section 2.3.2, 'Static Pseudowire Sub-TLV'."
    ::= { tmnxOamVccvTrNextPwSegmentEntry 16 }

tmnxOamVccvTrNextTpTaiiGlobalId  OBJECT-TYPE
    SYNTAX      TmnxMplsTpGlobalID
    MAX-ACCESS  read-only
    STATUS      current
    DESCRIPTION
        "The value of tmnxOamVccvTrNextTpTaiiGlobalId indicates the Destination
         Global ID field of the RFC 6426 Static Pseudowire Sub-TLV of the reply
         PDU.

         If a pseudowire other than an MPLS-TP pseudowire was probed, zero is
         returned."
    REFERENCE
        "RFC 6426, 'MPLS On-Demand Connectivity Verification and Route Tracing',
         section 2.3.2, 'Static Pseudowire Sub-TLV'."
    ::= { tmnxOamVccvTrNextPwSegmentEntry 17 }

tmnxOamVccvTrNextTpTaiiNodeId    OBJECT-TYPE
    SYNTAX      TmnxMplsTpNodeID
    MAX-ACCESS  read-only
    STATUS      current
    DESCRIPTION
        "The value of tmnxOamVccvTrNextTpTaiiNodeId indicates the Destination
         Node ID field of the RFC 6426 Static Pseudowire Sub-TLV of the reply
         PDU.

         If a pseudowire other than an MPLS-TP pseudowire was probed, zero is
         returned."
    REFERENCE
        "RFC 6426, 'MPLS On-Demand Connectivity Verification and Route Tracing',
         section 2.3.2, 'Static Pseudowire Sub-TLV'."
    ::= { tmnxOamVccvTrNextPwSegmentEntry 18 }

tmnxOamVccvTrNextTpTaiiAcId      OBJECT-TYPE
    SYNTAX      Unsigned32
    MAX-ACCESS  read-only
    STATUS      current
    DESCRIPTION
        "The value of tmnxOamVccvTrNextTpTaiiAcId indicates the Destination
         Attachment Circuit ID field of the RFC 6426 Static Pseudowire Sub-TLV
         of the reply PDU.

         If a pseudowire other than an MPLS-TP pseudowire was probed, zero is
         returned."
    REFERENCE
        "RFC 6426, 'MPLS On-Demand Connectivity Verification and Route Tracing',
         section 2.3.2, 'Static Pseudowire Sub-TLV'."
    ::= { tmnxOamVccvTrNextPwSegmentEntry 19 }

tmnxOamP2mpLspTrCtlTable         OBJECT-TYPE
    SYNTAX      SEQUENCE OF TmnxOamP2mpLspTrCtlEntry
    MAX-ACCESS  not-accessible
    STATUS      current
    DESCRIPTION
        "Defines the Nokia SROS OAM P2MP LSP Trace Control Table
         for providing, via SNMP, the capability of performing Nokia
         SROS OAM 'p2mpLspTrace' test operations for a single leaf
         egress node of an P2MP LSP.  The results of these tests are
         stored in the tmnxOamTrResultsTable and the
         tmnxOamTrProbeHistoryTable."
    ::= { tmnxOamTraceRouteObjs 28 }

tmnxOamP2mpLspTrCtlEntry         OBJECT-TYPE
    SYNTAX      TmnxOamP2mpLspTrCtlEntry
    MAX-ACCESS  not-accessible
    STATUS      current
    DESCRIPTION
        "Defines an entry in the tmnxOamP2mpLspTrCtlTable.  The first index
         element, tmnxOamTrCtlOwnerIndex, is of type SnmpAdminString,
         a textual convention that allows for use of the SNMPv3
         View-Based Access Control Model (RFC 2575 [11], VACM)
         and allows a management application to identify its entries.
         The second index, tmnxOamTrCtlTestIndex, enables the same
         management application to have multiple outstanding requests."
    INDEX       {
        tmnxOamTrCtlOwnerIndex,
        tmnxOamTrCtlTestIndex
    }
    ::= { tmnxOamP2mpLspTrCtlTable 1 }

TmnxOamP2mpLspTrCtlEntry         ::= SEQUENCE
{
    tmnxOamP2mpLspTrCtlLspName       TLNamedItemOrEmpty,
    tmnxOamP2mpLspTrCtlInstName      TNamedItemOrEmpty,
    tmnxOamP2mpLspTrCtlLeafIpAddr    InetAddress,
    tmnxOamP2mpLspTrCtlLeafIpAddrType InetAddressType
}

tmnxOamP2mpLspTrCtlLspName       OBJECT-TYPE
    SYNTAX      TLNamedItemOrEmpty
    MAX-ACCESS  read-write
    STATUS      current
    DESCRIPTION
        "Administrative name of the target P2MP Labeled Switch Path (LSP) for
         this OAM P2MP LSP Trace test. This parameter is mandatory."
    DEFVAL      { ''H }
    ::= { tmnxOamP2mpLspTrCtlEntry 1 }

tmnxOamP2mpLspTrCtlInstName      OBJECT-TYPE
    SYNTAX      TNamedItemOrEmpty
    MAX-ACCESS  read-write
    STATUS      current
    DESCRIPTION
        "This parameter identifies an instance of a P2MP LSP, either a primary
         or secondary instance of a P2MP LSP Tree."
    DEFVAL      { ''H }
    ::= { tmnxOamP2mpLspTrCtlEntry 2 }

tmnxOamP2mpLspTrCtlLeafIpAddr    OBJECT-TYPE
    SYNTAX      InetAddress (SIZE (0|4|16))
    MAX-ACCESS  read-write
    STATUS      current
    DESCRIPTION
        "The value of tmnxOamP2mpLspTrCtlLeafIpAddr specifies the Internet
         address of the egress leaf node of a P2MP LSP Tree. This parameter is
         mandatory."
    DEFVAL      { ''H }
    ::= { tmnxOamP2mpLspTrCtlEntry 3 }

tmnxOamP2mpLspTrCtlLeafIpAddrType OBJECT-TYPE
    SYNTAX      InetAddressType
    MAX-ACCESS  read-write
    STATUS      current
    DESCRIPTION
        "The value of tmnxOamP2mpLspTrCtlLeafIpAddrType specifies the type of
         Internet address stored in tmnxOamP2mpLspTrCtlLeafIpAddr."
    DEFVAL      { unknown }
    ::= { tmnxOamP2mpLspTrCtlEntry 4 }

tmnxOamP2mpLspTrMapTable         OBJECT-TYPE
    SYNTAX      SEQUENCE OF TmnxOamP2mpLspTrMapEntry
    MAX-ACCESS  not-accessible
    STATUS      current
    DESCRIPTION
        "Defines a table for storing the results of an OAM 'p2mpLspTrace'
         probe operation when a Downstream Mapping TLV was returned.  Each row
         represents a single label map within the returned downstream mapping
         TLV.

         An entry in this table is created when the result of an OAM
         'p2mpLspTrace' probe is determined.

         An entry is removed from this table when its corresponding
         tmnxOamTrCtlEntry is deleted."
    REFERENCE
        "RFC 4379 Section 3.3"
    ::= { tmnxOamTraceRouteObjs 29 }

tmnxOamP2mpLspTrMapEntry         OBJECT-TYPE
    SYNTAX      TmnxOamP2mpLspTrMapEntry
    MAX-ACCESS  not-accessible
    STATUS      current
    DESCRIPTION
        "Defines an entry in the tmnxOamP2mpLspTrMapTable.  The first two
         index elements identify the tmnxOamTrCtlEntry that a
         tmnxOamP2mpLspTrMapEntry belongs to.  The third index element
         identifies an OAM trace route test run.  The fourth index element
         selects the group of responses associated with a specific
         probe attempt. The fifth and sixth indexes select the hop and
         the probe at that hop for a particular Nokia SROS OAM
         Trace Route operation. The seventh index selects a single downstream
         L2 map entry within the specific probe reply."
    INDEX       {
        tmnxOamTrCtlOwnerIndex,
        tmnxOamTrCtlTestIndex,
        tmnxOamTrResultsTestRunIndex,
        tmnxOamTrProbeHistoryIndex,
        tmnxOamTrProbeHistoryHopIndex,
        tmnxOamTrProbeHistoryProbeIndex,
        tmnxOamP2mpLspTrMapIndex
    }
    ::= { tmnxOamP2mpLspTrMapTable 1 }

TmnxOamP2mpLspTrMapEntry         ::= SEQUENCE
{
    tmnxOamP2mpLspTrMapIndex         Unsigned32,
    tmnxOamP2mpLspTrMapDSIPv4Addr    IpAddress,
    tmnxOamP2mpLspTrMapAddrType      TmnxOamAddressType,
    tmnxOamP2mpLspTrMapDSIfAddr      Unsigned32,
    tmnxOamP2mpLspTrMapMTU           Unsigned32,
    tmnxOamP2mpLspTrMapP2mpBranch    TruthValue,
    tmnxOamP2mpLspTrMapP2mpBud       TruthValue
}

tmnxOamP2mpLspTrMapIndex         OBJECT-TYPE
    SYNTAX      Unsigned32 (1..4294967295)
    MAX-ACCESS  not-accessible
    STATUS      current
    DESCRIPTION
        "The value of tmnxOamP2mpLspTrMapIndex specifies a single L2 mapping
         entry within a specific 'p2mpLspTrace' probe reply.

         The agent starts assigning tmnxOamP2mpLspTrMapIndex values at 1."
    ::= { tmnxOamP2mpLspTrMapEntry 1 }

tmnxOamP2mpLspTrMapDSIPv4Addr    OBJECT-TYPE
    SYNTAX      IpAddress
    MAX-ACCESS  read-only
    STATUS      current
    DESCRIPTION
        "The value of tmnxOamP2mpLspTrMapDSIPv4Addr indicates the IPv4 address
         of the downstream LSR that this entry in the tmnxOamP2mpLspTrMapTable
         describes.  If the interface to the downstream LSR is numbered,
         then the tmnxOamP2mpLspTrMapDSIPv4Addr can either be the downstream
         LSR's Router ID or the interface address of the downstream LSR.

         If the interface to the downstream LSR is unnumbered, the value of
         tmnxOamP2mpLspTrMapDSIPv4Addr indicates the downstream LSR's Router
         ID."
    ::= { tmnxOamP2mpLspTrMapEntry 2 }

tmnxOamP2mpLspTrMapAddrType      OBJECT-TYPE
    SYNTAX      TmnxOamAddressType
    MAX-ACCESS  read-only
    STATUS      current
    DESCRIPTION
        "The value of tmnxOamP2mpLspTrMapAddrType indicates the type of
         downstream interface address specified by tmnxOamP2mpLspTrMapDSIfAddr.
         The only valid values for tmnxOamP2mpLspTrMapAddrType are
         'ipv4Address', 'ipv4Unnumbered', 'ipv6Address' and 'ipv6Unnumbered'."
    ::= { tmnxOamP2mpLspTrMapEntry 3 }

tmnxOamP2mpLspTrMapDSIfAddr      OBJECT-TYPE
    SYNTAX      Unsigned32
    MAX-ACCESS  read-only
    STATUS      current
    DESCRIPTION
        "When tmnxOamP2mpLspTrMapAddrType has a value of 'ipv4Address'
         tmnxOamP2mpLspTrMapDSIfAddr indicates the downstream LSR's
         interface address.  When tmnxOamP2mpLspTrMapAddrType has a value
         of 'unnumbered', tmnxOamP2mpLspTrMapDSIfAddr indicates the index
         assigned by the upstream LSR to the interface."
    ::= { tmnxOamP2mpLspTrMapEntry 4 }

tmnxOamP2mpLspTrMapMTU           OBJECT-TYPE
    SYNTAX      Unsigned32 (0..65535)
    MAX-ACCESS  read-only
    STATUS      current
    DESCRIPTION
        "The value of tmnxOamP2mpLspTrMapMTU indicates the largest MPLS frame
         (including the label stack) that fits on the interface to the
         downstream LSR."
    ::= { tmnxOamP2mpLspTrMapEntry 5 }

tmnxOamP2mpLspTrMapP2mpBranch    OBJECT-TYPE
    SYNTAX      TruthValue
    MAX-ACCESS  read-only
    STATUS      current
    DESCRIPTION
        "When the value of tmnxOamP2mpLspTrMapP2mpBranch is 'true', the
         'p2mpLspTrace' response indicates that the responding router is a
         branch node of the P2MP LSP tree."
    ::= { tmnxOamP2mpLspTrMapEntry 6 }

tmnxOamP2mpLspTrMapP2mpBud       OBJECT-TYPE
    SYNTAX      TruthValue
    MAX-ACCESS  read-only
    STATUS      current
    DESCRIPTION
        "When the value of tmnxOamP2mpLspTrMapP2mpBud is 'true', the
         'p2mpLspTrace' response indicates that the responding router is a bud
         node of the P2MP LSP tree."
    ::= { tmnxOamP2mpLspTrMapEntry 7 }

tmnxOamP2mpLspTrDSLabelTable     OBJECT-TYPE
    SYNTAX      SEQUENCE OF TmnxOamP2mpLspTrDSLabelEntry
    MAX-ACCESS  not-accessible
    STATUS      current
    DESCRIPTION
        "Defines a table for storing the results of an OAM 'p2mpLspTrace'
         probe operation when a Downstream Mapping TLV was
         returned.  Each row represents a single downstream label within a
         returned downstream L2 mapping TLV.

         An entry in this table is created when the result of an OAM
         'p2mpLspTrace' probe is determined. An entry is removed from this
         table when its corresponding tmnxOamTrCtlEntry is deleted."
    ::= { tmnxOamTraceRouteObjs 30 }

tmnxOamP2mpLspTrDSLabelEntry     OBJECT-TYPE
    SYNTAX      TmnxOamP2mpLspTrDSLabelEntry
    MAX-ACCESS  not-accessible
    STATUS      current
    DESCRIPTION
        "Defines an entry in the tmnxOamP2mpLspTrDSLabelTable.  The first
         two index elements identify the tmnxOamTrCtlEntry that a
         tmnxOamLspTrMapEntry belongs to.  The third index element
         identifies a OAM trace route test run. The fourth index element
         selects the group of responses associated with a specific
         probe attempt. The fifth and sixth indexes select the hop and
         the probe at that hop for a particular Nokia SROS OAM
         Trace Route operation. The seventh index selects a single downstream
         L2 map entry within the specific probe reply.  The eighth index
         selects successive downstream L2 label entries contained in a
         specific probe reply."
    INDEX       {
        tmnxOamTrCtlOwnerIndex,
        tmnxOamTrCtlTestIndex,
        tmnxOamTrResultsTestRunIndex,
        tmnxOamTrProbeHistoryIndex,
        tmnxOamTrProbeHistoryHopIndex,
        tmnxOamTrProbeHistoryProbeIndex,
        tmnxOamLspTrMapIndex,
        tmnxOamP2mpLspTrDSLabelIndex
    }
    ::= { tmnxOamP2mpLspTrDSLabelTable 1 }

TmnxOamP2mpLspTrDSLabelEntry     ::= SEQUENCE
{
    tmnxOamP2mpLspTrDSLabelIndex     Unsigned32,
    tmnxOamP2mpLspTrDSLabelLabel     MplsLabel,
    tmnxOamP2mpLspTrDSLabelProtocol  TmnxOamSignalProtocol
}

tmnxOamP2mpLspTrDSLabelIndex     OBJECT-TYPE
    SYNTAX      Unsigned32 (1..4294967295)
    MAX-ACCESS  not-accessible
    STATUS      current
    DESCRIPTION
        "The tmnxOamP2mpLspTrDSLabelIndex selects a single downstream L2 label
         entry within a specific L2 mapping entry reply.

         The agent starts assigning tmnxOamP2mpLspTrDSLabelIndex values at 1."
    ::= { tmnxOamP2mpLspTrDSLabelEntry 1 }

tmnxOamP2mpLspTrDSLabelLabel     OBJECT-TYPE
    SYNTAX      MplsLabel
    MAX-ACCESS  read-only
    STATUS      current
    DESCRIPTION
        "The value of tmnxOamP2mpLspTrDSLabelLabel is the label used by the
         downstream router specified by this downstream L2 label entry."
    ::= { tmnxOamP2mpLspTrDSLabelEntry 2 }

tmnxOamP2mpLspTrDSLabelProtocol  OBJECT-TYPE
    SYNTAX      TmnxOamSignalProtocol
    MAX-ACCESS  read-only
    STATUS      current
    DESCRIPTION
        "The value of tmnxOamP2mpLspTrDSLabelProtocol is the signaling protocol
         used by the router for the label specified by this downstream L2 label
         entry."
    ::= { tmnxOamP2mpLspTrDSLabelEntry 3 }

tmnxOamEthCfmTrCtlTable          OBJECT-TYPE
    SYNTAX      SEQUENCE OF TmnxOamEthCfmTrCtlEntry
    MAX-ACCESS  not-accessible
    STATUS      current
    DESCRIPTION
        "tmnxOamEthCfmTrCtlTable contains Ethernet CFM-specific configuration
         information for 'ethCfmLinkTrace' tests.

         This table extends the tmnxOamTrCtlTable.  A row is automatically
         created in this table when a row in tmnxOamTrCtlTable has
         tmnxOamTrCtlTestMode set to 'ethCfmLinkTrace'.  Deleting a row in
         tmnxOamTrCtlTable automatically deletes the row (if any) with the same
         index values in tmnxOamEthCfmTrCtlTable.

         Test results are stored in tmnxOamTrResultsTable,
         tmnxOamTrProbeHistoryTable, tmnxOamTrHopsTable, and
         tmnxOamEthCfmTrPrHistTable."
    ::= { tmnxOamTraceRouteObjs 31 }

tmnxOamEthCfmTrCtlEntry          OBJECT-TYPE
    SYNTAX      TmnxOamEthCfmTrCtlEntry
    MAX-ACCESS  not-accessible
    STATUS      current
    DESCRIPTION
        "tmnxOamEthCfmTrCtlEntry defines an entry in the
         tmnxOamEthCfmTrCtlTable.  Each index is an object in
         tmnxOamTrCtlTable."
    INDEX       {
        tmnxOamTrCtlOwnerIndex,
        tmnxOamTrCtlTestIndex
    }
    ::= { tmnxOamEthCfmTrCtlTable 1 }

TmnxOamEthCfmTrCtlEntry          ::= SEQUENCE
{
    tmnxOamEthCfmTrCtlTgtMacAddr     MacAddress,
    tmnxOamEthCfmTrCtlSrcMdIndex     Unsigned32,
    tmnxOamEthCfmTrCtlSrcMaIndex     Unsigned32,
    tmnxOamEthCfmTrCtlSrcMepId       Dot1agCfmMepIdOrZero,
    tmnxOamEthCfmTrCtlRemoteMepId    Dot1agCfmMepIdOrZero
}

tmnxOamEthCfmTrCtlTgtMacAddr     OBJECT-TYPE
    SYNTAX      MacAddress
    MAX-ACCESS  read-create
    STATUS      current
    DESCRIPTION
        "The value of tmnxOamEthCfmTrCtlTgtMacAddr specifies the destination
         MAC address for the test.

         A non-zero destination MAC address is required in each test frame sent
         for the test.  The destination MAC address can be specified directly
         (using this object) or indirectly (see the DESCRIPTION of
         tmnxOamEthCfmTrCtlRemoteMepId).

         Exactly one of tmnxOamEthCfmTrCtlTgtMacAddr and
         tmnxOamEthCfmTrCtlRemoteMepId must be assigned a non-default value.
         Otherwise, an attempt to administratively enable the test (using
         tmnxOamSaaCtlAdminStatus) will fail."
    DEFVAL      { '000000000000'H }
    ::= { tmnxOamEthCfmTrCtlEntry 1 }

tmnxOamEthCfmTrCtlSrcMdIndex     OBJECT-TYPE
    SYNTAX      Unsigned32
    MAX-ACCESS  read-create
    STATUS      current
    DESCRIPTION
        "The value of tmnxOamEthCfmTrCtlSrcMdIndex specifies the source CFM
         maintenance domain index for the test.  Zero is the null CFM
         maintenance domain index."
    DEFVAL      { 0 }
    ::= { tmnxOamEthCfmTrCtlEntry 2 }

tmnxOamEthCfmTrCtlSrcMaIndex     OBJECT-TYPE
    SYNTAX      Unsigned32
    MAX-ACCESS  read-create
    STATUS      current
    DESCRIPTION
        "The value of tmnxOamEthCfmTrCtlSrcMaIndex specifies the source CFM
         maintenance association index for the test.  Zero is the null CFM
         maintenance association index."
    DEFVAL      { 0 }
    ::= { tmnxOamEthCfmTrCtlEntry 3 }

tmnxOamEthCfmTrCtlSrcMepId       OBJECT-TYPE
    SYNTAX      Dot1agCfmMepIdOrZero
    MAX-ACCESS  read-create
    STATUS      current
    DESCRIPTION
        "The value of tmnxOamEthCfmTrCtlSrcMepId specifies the source
         Maintenance association End Point Identifier (MEP ID) for the test.
         Zero is the null MEP ID."
    DEFVAL      { 0 }
    ::= { tmnxOamEthCfmTrCtlEntry 4 }

tmnxOamEthCfmTrCtlRemoteMepId    OBJECT-TYPE
    SYNTAX      Dot1agCfmMepIdOrZero
    MAX-ACCESS  read-create
    STATUS      current
    DESCRIPTION
        "The value of tmnxOamEthCfmTrCtlRemoteMepId specifies the remote
         Maintenance association End Point Identifier (MEP ID) for the test.

         A non-zero destination MAC address is required in each test frame sent
         for the test.  The destination MAC address can be specified directly
         (using tmnxOamEthCfmTrCtlTgtMacAddr) or indirectly (using this object).

         Exactly one of tmnxOamEthCfmTrCtlTgtMacAddr and
         tmnxOamEthCfmTrCtlRemoteMepId must be assigned a non-default value.
         Otherwise, an attempt to administratively enable the test (using
         tmnxOamSaaCtlAdminStatus) will fail.

         Suppose this object is assigned a non-default value.  Then, at the
         start of each test run, SROS reads
         TIMETRA-IEEE8021-CFM-MIB::tmnxDot1agCfmLearnedRmtMacAddr to find the
         destination MAC address to use for the test run.

         The following index values are used for the read:
            tmnxOamEthCfmTrCtlSrcMdIndex,
            tmnxOamEthCfmTrCtlSrcMaIndex,
            tmnxOamEthCfmTrCtlSrcMepId,
            tmnxOamEthCfmTrCtlRemoteMepId.

         If the search fails to find a destination MAC address, no test frames
         will be sent for the test run.  The number of frames to be sent during
         a test run is configured using tmnxOamTrCtlProbesPerHop,
         tmnxOamTrCtlInitialTtl, and tmnxOamTrCtlMaxTtl.

         Configuring tmnxOamEthCfmTrCtlRemoteMepId (instead of
         tmnxOamEthCfmTrCtlDestMacAddr) has the following advantage: if the
         hardware hosting the test's far end is replaced (meaning a new
         destination MAC address is present), the test does not need to be
         reconfigured."
    DEFVAL      { 0 }
    ::= { tmnxOamEthCfmTrCtlEntry 5 }

tmnxOamEthCfmTrPrHistTable       OBJECT-TYPE
    SYNTAX      SEQUENCE OF TmnxOamEthCfmTrPrHistEntry
    MAX-ACCESS  not-accessible
    STATUS      current
    DESCRIPTION
        "tmnxOamEthCfmTrPrHistTable contains Ethernet CFM-specific probe
         history for 'ethCfmLinkTrace' tests.

         This table extends the tmnxOamTrProbeHistoryTable.  A row is
         automatically created in this table when a row is created in
         tmnxOamTrProbeHistoryTable for a test with tmnxOamTrCtlTestMode set to
         'ethCfmLinkTrace'.  Deleting a row in tmnxOamTrProbeHistoryTable
         automatically deletes the row (if any) with the same index values in
         tmnxOamEthCfmTrPrHistTable."
    ::= { tmnxOamTraceRouteObjs 32 }

tmnxOamEthCfmTrPrHistEntry       OBJECT-TYPE
    SYNTAX      TmnxOamEthCfmTrPrHistEntry
    MAX-ACCESS  not-accessible
    STATUS      current
    DESCRIPTION
        "Defines an entry in the tmnxOamEthCfmTrPrHistTable.  The indices are
         the same as the tmnxOamTrProbeHistoryTable indices."
    INDEX       {
        tmnxOamTrCtlOwnerIndex,
        tmnxOamTrCtlTestIndex,
        tmnxOamTrResultsTestRunIndex,
        tmnxOamTrProbeHistoryIndex,
        tmnxOamTrProbeHistoryHopIndex,
        tmnxOamTrProbeHistoryProbeIndex
    }
    ::= { tmnxOamEthCfmTrPrHistTable 1 }

TmnxOamEthCfmTrPrHistEntry       ::= SEQUENCE
{
    tmnxOamEthCfmTrPrHistIngressMac  MacAddress,
    tmnxOamEthCfmTrPrHistEgressMac   MacAddress,
    tmnxOamEthCfmTrPrHistRelayAction INTEGER,
    tmnxOamEthCfmTrPrHistForwarded   TruthValue,
    tmnxOamEthCfmTrPrHistTerminalMep TruthValue
}

tmnxOamEthCfmTrPrHistIngressMac  OBJECT-TYPE
    SYNTAX      MacAddress
    MAX-ACCESS  read-only
    STATUS      current
    DESCRIPTION
        "The value of tmnxOamEthCfmTrPrHistIngressMac indicates the ingress MAC
         address of the probe."
    ::= { tmnxOamEthCfmTrPrHistEntry 1 }

tmnxOamEthCfmTrPrHistEgressMac   OBJECT-TYPE
    SYNTAX      MacAddress
    MAX-ACCESS  read-only
    STATUS      current
    DESCRIPTION
        "The value of tmnxOamEthCfmTrPrHistEgressMac indicates the egress MAC
         address of the probe."
    ::= { tmnxOamEthCfmTrPrHistEntry 2 }

tmnxOamEthCfmTrPrHistRelayAction OBJECT-TYPE
    SYNTAX      INTEGER {
        unknown (0),
        rlyHit  (1),
        rlyFdb  (2),
        rlyMpdb (3)
    }
    MAX-ACCESS  read-only
    STATUS      current
    DESCRIPTION
        "The value of tmnxOamEthCfmTrPrHistRelayAction indicates the value of
         the Relay Action field in the Link Trace Reply.  'unknown(0)' is
         returned when a Link Trace Reply has not arrived, or the Relay Action
         field in the Link Trace Reply is outside the expected range."
    ::= { tmnxOamEthCfmTrPrHistEntry 3 }

tmnxOamEthCfmTrPrHistForwarded   OBJECT-TYPE
    SYNTAX      TruthValue
    MAX-ACCESS  read-only
    STATUS      current
    DESCRIPTION
        "The value of tmnxOamEthCfmTrPrHistForwarded indicates if a Link Trace
         Message was forwarded by the responding Maintenance Point (MP), as
         returned in the 'FwdYes' flag of the Flags field of the Link Trace
         Reply."
    REFERENCE
        "Modeled on the dot1agCfmLtrForwarded object in IEEE8021-CFM-MIB."
    ::= { tmnxOamEthCfmTrPrHistEntry 4 }

tmnxOamEthCfmTrPrHistTerminalMep OBJECT-TYPE
    SYNTAX      TruthValue
    MAX-ACCESS  read-only
    STATUS      current
    DESCRIPTION
        "The value of tmnxOamEthCfmTrPrHistTerminalMep indicates whether the
         forwarded Link Trace Message reached a MEP enclosing its MA, as
         returned in the Terminal MEP flag of the Flags field of the Link Trace
         Reply."
    REFERENCE
        "Modeled on the dot1agCfmLtrTerminalMep object in IEEE8021-CFM-MIB."
    ::= { tmnxOamEthCfmTrPrHistEntry 5 }

tmnxOamLspTrFecStackTable        OBJECT-TYPE
    SYNTAX      SEQUENCE OF TmnxOamLspTrFecStackEntry
    MAX-ACCESS  not-accessible
    STATUS      current
    DESCRIPTION
        "tmnxOamLspTrFecStackTable has a row for each RFC 6424 FEC (Forwarding
         Equivalence Class) Stack Change sub-TLV present in a currently managed
         'lspTraceRoute' reply PDU.

         The FEC Stack Change sub-TLV is a component of the RFC 6424 Downstream
         Detailed Mapping TLV.

         An 'lspTraceRoute' reply PDU can contain several Downstream Detailed
         Mapping TLVs.  A Downstream Detailed Mapping TLV can contain several
         FEC Stack Change sub-TLVs.

         The set of tmnxOamLspTrFecStackTable rows for a reply PDU holds the
         set of FEC stack changes recorded in the reply PDU, including
         information about MPLS tunnels and/or LSP stitching on the tested LSP."
    REFERENCE
        "RFC 6424, 'Mechanism for Performing Label Switched Path Ping (LSP Ping)
         over MPLS Tunnels', Section 3.3, 'Downstream Detailed Mapping TLV'.
         RFC 4379, 'Detecting Multi-Protocol Label Switched (MPLS) Data Plane
         Failures', Section 3.2, 'Target FEC Stack'."
    ::= { tmnxOamTraceRouteObjs 33 }

tmnxOamLspTrFecStackEntry        OBJECT-TYPE
    SYNTAX      TmnxOamLspTrFecStackEntry
    MAX-ACCESS  not-accessible
    STATUS      current
    DESCRIPTION
        "A row in tmnxOamLspTrFecStackTable is created by the system for each
         RFC 6424 FEC Stack Change sub-TLV present in a currently managed
         'lspTraceRoute' reply PDU.

         A row is deleted when the corresponding tmnxOamTrCtlTable row is
         deleted.

         The first six indices specify an 'lspTraceRoute' reply PDU.

         The first seven indices specify an RFC 6424 Downstream Detailed
         Mapping TLV within an 'lspTraceRoute' reply PDU.

         The eight indices specify an RFC 6424 FEC Stack Change sub-TLV within
         a Downstream Detailed Mapping TLV within an 'lspTraceRoute' reply PDU."
    INDEX       {
        tmnxOamTrCtlOwnerIndex,
        tmnxOamTrCtlTestIndex,
        tmnxOamTrResultsTestRunIndex,
        tmnxOamTrProbeHistoryIndex,
        tmnxOamTrProbeHistoryHopIndex,
        tmnxOamTrProbeHistoryProbeIndex,
        tmnxOamLspTrMapIndex,
        tmnxOamLspTrFecStackFecIndex
    }
    ::= { tmnxOamLspTrFecStackTable 1 }

TmnxOamLspTrFecStackEntry        ::= SEQUENCE
{
    tmnxOamLspTrFecStackFecIndex     Unsigned32,
    tmnxOamLspTrFecStackOperType     INTEGER,
    tmnxOamLspTrFecStackFecSubType   TNamedItemOrEmpty,
    tmnxOamLspTrFecStackPrefixType   InetAddressType,
    tmnxOamLspTrFecStackPrefix       InetAddress,
    tmnxOamLspTrFecStackPrefixLen    InetAddressPrefixLength,
    tmnxOamLspTrFecStackRemPeerAddrT InetAddressType,
    tmnxOamLspTrFecStackRemPeerAddr  InetAddress
}

tmnxOamLspTrFecStackFecIndex     OBJECT-TYPE
    SYNTAX      Unsigned32 (1..8)
    MAX-ACCESS  not-accessible
    STATUS      current
    DESCRIPTION
        "The value of tmnxOamLspTrFecStackFecIndex specifies one RFC 6424 FEC
         Stack Change sub-TLV within the specified Downstream Detailed Mapping
         TLV."
    ::= { tmnxOamLspTrFecStackEntry 1 }

tmnxOamLspTrFecStackOperType     OBJECT-TYPE
    SYNTAX      INTEGER {
        push (1),
        pop  (2)
    }
    MAX-ACCESS  read-only
    STATUS      current
    DESCRIPTION
        "The value of tmnxOamLspTrFecStackOperType indicates the value of the
         following Operation Type field (where +-> indicates encapsulation):
             'lspTraceRoute' reply PDU
             +-> RFC 6424 Downstream Detailed Mapping TLV
                 +-> RFC 6424 FEC Stack Change sub-TLV
                     +-> Operation Type field."
    ::= { tmnxOamLspTrFecStackEntry 2 }

tmnxOamLspTrFecStackFecSubType   OBJECT-TYPE
    SYNTAX      TNamedItemOrEmpty
    MAX-ACCESS  read-only
    STATUS      current
    DESCRIPTION
        "The value of tmnxOamLspTrFecStackFecSubType indicates the value of the
         following Sub-Type field (where +-> indicates encapsulation):
             'lspTraceRoute' reply PDU
             +-> RFC 6424 Downstream Detailed Mapping TLV
                 +-> RFC 6424 FEC Stack Change sub-TLV
                     +-> RFC 4379 Target FEC Stack TLV
                         +-> RFC 4379 FEC-type-specific sub-TLV
                             (e.g. BGP labeled IPv4 prefix sub-TLV)
                             +-> Sub-Type field.

         This object maps the numeric value in the Sub-Type field to an ASCII
         string.  The following examples illustrate the mapping.

         Sub-Type Field   tmnxOamLspTrFecStackFecSubType
         --------------   ------------------------------
         1                'LDP IPv4 prefix (1)'
         3                'RSVP IPv4 LSP (3)'
         12               'BGP labeled IPv4 prefix (12)'
         16               'Nil FEC (16)'
         99               'Unknown (99)'"
    ::= { tmnxOamLspTrFecStackEntry 3 }

tmnxOamLspTrFecStackPrefixType   OBJECT-TYPE
    SYNTAX      InetAddressType
    MAX-ACCESS  read-only
    STATUS      current
    DESCRIPTION
        "The value of tmnxOamLspTrFecStackPrefixType indicates the type of
         address stored in tmnxOamLspTrFecStackPrefix."
    ::= { tmnxOamLspTrFecStackEntry 4 }

tmnxOamLspTrFecStackPrefix       OBJECT-TYPE
    SYNTAX      InetAddress (SIZE (0|4|16))
    MAX-ACCESS  read-only
    STATUS      current
    DESCRIPTION
        "The value of tmnxOamLspTrFecStackPrefix indicates the value of an IP
         prefix (or IP address) field with the following encapsulation
         (where +-> indicates encapsulation):
             'lspTraceRoute' reply PDU
             +-> RFC 6424 Downstream Detailed Mapping TLV
                 +-> RFC 6424 FEC Stack Change sub-TLV
                     +-> RFC 4379 Target FEC Stack TLV
                         +-> RFC 4379 FEC-type-specific sub-TLV
                             (e.g. LDP IPv4 Prefix sub-TLV)
                             +-> FEC-type-specific IP prefix field.

         For example, the value returned could be the content of one of the
         fields shown in the following table.

         Field                RFC 4379 Sub-TLV
         ------------------   -----------------------
         Extended Tunnel ID   RSVP IPv4 LSP
         IPv4 Prefix          BGP Labeled IPv4 Prefix
         IPv4 Prefix          LDP IPv4 Prefix

         If no IP prefix field is present in the reply PDU,
         tmnxOamLspTrFecStackPrefixType contains 'unknown(1)'."
    ::= { tmnxOamLspTrFecStackEntry 5 }

tmnxOamLspTrFecStackPrefixLen    OBJECT-TYPE
    SYNTAX      InetAddressPrefixLength
    MAX-ACCESS  read-only
    STATUS      current
    DESCRIPTION
        "The value of tmnxOamLspTrFecStackPrefixLen indicates the value of an IP
         prefix length field with the following encapsulation (where +->
         indicates encapsulation):
             'lspTraceRoute' reply PDU
             +-> RFC 6424 Downstream Detailed Mapping TLV
                 +-> RFC 6424 FEC Stack Change sub-TLV
                     +-> RFC 4379 Target FEC Stack TLV
                         +-> RFC 4379 FEC-type-specific sub-TLV
                             (e.g. LDP IPv4 Prefix sub-TLV)
                             +-> FEC-type-specific IP prefix length field.

         For example, the value returned could be the content of one of the
         fields shown in the following table.

         Field           RFC 4379 Sub-TLV
         -------------   -----------------------
         Prefix Length   BGP Labeled IPv4 Prefix
         Prefix Length   LDP IPv4 Prefix

         If no relevant IP prefix length field is present in the reply PDU,
         tmnxOamLspTrFecStackPrefixLen contains 32 (for an IPv4 address), or
         128 (for an IPv6 address)."
    ::= { tmnxOamLspTrFecStackEntry 6 }

tmnxOamLspTrFecStackRemPeerAddrT OBJECT-TYPE
    SYNTAX      InetAddressType
    MAX-ACCESS  read-only
    STATUS      current
    DESCRIPTION
        "The value of tmnxOamLspTrFecStackRemPeerAddrT indicates the type of
         address stored in tmnxOamLspTrFecStackRemPeerAddr."
    ::= { tmnxOamLspTrFecStackEntry 7 }

tmnxOamLspTrFecStackRemPeerAddr  OBJECT-TYPE
    SYNTAX      InetAddress (SIZE (0|4|16))
    MAX-ACCESS  read-only
    STATUS      current
    DESCRIPTION
        "The value of tmnxOamLspTrFecStackRemPeerAddr indicates the value
         contained in the remote peer address field with the following
         encapsulation (where +-> indicates encapsulation):
             'lspTraceRoute' reply PDU
             +-> RFC 6424 Downstream Detailed Mapping TLV
                 +-> RFC 6424 FEC Stack Change sub-TLV
                     +-> Remote Peer Address field."
    ::= { tmnxOamLspTrFecStackEntry 8 }

tmnxOamVccvTrTgFec128CtlTable    OBJECT-TYPE
    SYNTAX      SEQUENCE OF TmnxOamVccvTrTgFec128CtlEntry
    MAX-ACCESS  not-accessible
    STATUS      current
    DESCRIPTION
        "tmnxOamVccvTrTgFec128CtlTable contains the target information for VCCV
         (Virtual Circuit Connectivity Verification) trace route tests which
         switch to downstream FEC (Forward Equivalence Class) 128 segments."
    REFERENCE
        "RFC 4379, 'Detecting Multi-Protocol Label Switched (MPLS) Data Plane
         Failures', Section 3.2.9 ('FEC 128 Pseudowire (Current)')."
    ::= { tmnxOamTraceRouteObjs 34 }

tmnxOamVccvTrTgFec128CtlEntry    OBJECT-TYPE
    SYNTAX      TmnxOamVccvTrTgFec128CtlEntry
    MAX-ACCESS  not-accessible
    STATUS      current
    DESCRIPTION
        "tmnxOamVccvTrTgFec128CtlEntry contains the target information for a
         VCCV trace route test which switches to a downstream FEC 128 segment.

         The values in a row are used to fill a 'FEC 128 Pseudowire' sub-TLV
         (Type, Length, Value) within the 'Target FEC Stack' TLV within the
         launched VCCV trace route request.

         A row is created when the test's tmnxOamVccvTrCtlSwitTgtFecType is set
         to 'fec128(2)'.

         A row is destroyed when the tmnxOamVccvTrCtlTable row is destroyed.

         All the objects in a row must be set in one SNMP Set PDU.  Otherwise,
         the SNMP Set PDU will be rejected."
    REFERENCE
        "RFC 4379, 'Detecting Multi-Protocol Label Switched (MPLS) Data Plane
         Failures', Section 3.2.9 ('FEC 128 Pseudowire (Current)')."
    INDEX       {
        tmnxOamTrCtlOwnerIndex,
        tmnxOamTrCtlTestIndex
    }
    ::= { tmnxOamVccvTrTgFec128CtlTable 1 }

TmnxOamVccvTrTgFec128CtlEntry    ::= SEQUENCE
{
    tmnxOamVccvTrTgFec128CtlSrcAddrT InetAddressType,
    tmnxOamVccvTrTgFec128CtlSrcAddr  InetAddress,
    tmnxOamVccvTrTgFec128CtlDstAddrT InetAddressType,
    tmnxOamVccvTrTgFec128CtlDstAddr  InetAddress,
    tmnxOamVccvTrTgFec128CtlPwId     Unsigned32,
    tmnxOamVccvTrTgFec128CtlPwType   Unsigned32
}

tmnxOamVccvTrTgFec128CtlSrcAddrT OBJECT-TYPE
    SYNTAX      InetAddressType
    MAX-ACCESS  read-write
    STATUS      current
    DESCRIPTION
        "The value of tmnxOamVccvTrTgFec128CtlSrcAddrT specifies the address
         type of tmnxOamVccvTrTgFec128CtlSrcAddr."
    DEFVAL      { unknown }
    ::= { tmnxOamVccvTrTgFec128CtlEntry 1 }

tmnxOamVccvTrTgFec128CtlSrcAddr  OBJECT-TYPE
    SYNTAX      InetAddress (SIZE (0|4|16))
    MAX-ACCESS  read-write
    STATUS      current
    DESCRIPTION
        "The value of tmnxOamVccvTrTgFec128CtlSrcAddr specifies the value to be
         copied into the Sender's PE Address (Sender's Provider Edge Address)
         field of the 'FEC 128 Pseudowire' sub-TLV within the 'Target FEC
         Stack' TLV within the launched VCCV trace route request."
    REFERENCE
        "RFC 4379, 'Detecting Multi-Protocol Label Switched (MPLS) Data Plane
         Failures', Section 3.2.9 ('FEC 128 Pseudowire (Current)')."
    DEFVAL      { ''H }
    ::= { tmnxOamVccvTrTgFec128CtlEntry 2 }

tmnxOamVccvTrTgFec128CtlDstAddrT OBJECT-TYPE
    SYNTAX      InetAddressType
    MAX-ACCESS  read-write
    STATUS      current
    DESCRIPTION
        "The value of tmnxOamVccvTrTgFec128CtlDstAddrT specifies the address
         type of tmnxOamVccvTrTgFec128CtlDstAddr."
    DEFVAL      { unknown }
    ::= { tmnxOamVccvTrTgFec128CtlEntry 3 }

tmnxOamVccvTrTgFec128CtlDstAddr  OBJECT-TYPE
    SYNTAX      InetAddress (SIZE (0|4|16))
    MAX-ACCESS  read-write
    STATUS      current
    DESCRIPTION
        "The value of tmnxOamVccvTrTgFec128CtlDstAddr specifies the value to be
         copied into the 'Remote PE Address' (Remote Provider Edge Address)
         field of the 'FEC 128 Pseudowire' sub-TLV within the 'Target FEC
         Stack' TLV within the launched VCCV trace route request."
    REFERENCE
        "RFC 4379, 'Detecting Multi-Protocol Label Switched (MPLS) Data Plane
         Failures', Section 3.2.9 ('FEC 128 Pseudowire (Current)')."
    DEFVAL      { ''H }
    ::= { tmnxOamVccvTrTgFec128CtlEntry 4 }

tmnxOamVccvTrTgFec128CtlPwId     OBJECT-TYPE
    SYNTAX      Unsigned32
    MAX-ACCESS  read-write
    STATUS      current
    DESCRIPTION
        "The value of tmnxOamVccvTrTgFec128CtlPwId specifies the value to be
         copied into the 'PW ID' (Pseudowire Identifier) field of the 'FEC 128
         Pseudowire' sub-TLV within the 'Target FEC Stack' TLV within the
         launched VCCV trace route request.

         Zero indicates no Pseudowire Identifier has been configured."
    REFERENCE
        "RFC 4379, 'Detecting Multi-Protocol Label Switched (MPLS) Data Plane
         Failures', Section 3.2.9 ('FEC 128 Pseudowire (Current)')."
    DEFVAL      { 0 }
    ::= { tmnxOamVccvTrTgFec128CtlEntry 5 }

tmnxOamVccvTrTgFec128CtlPwType   OBJECT-TYPE
    SYNTAX      Unsigned32 (0..65535)
    MAX-ACCESS  read-write
    STATUS      current
    DESCRIPTION
        "The value of tmnxOamVccvTrTgFec128CtlPwType specifies the value to be
         copied into the 'PW Type' (Pseudowire Type) field of the 'FEC 128
         Pseudowire' sub-TLV within the 'Target FEC Stack' TLV within the
         launched VCCV trace route request.  The code points are defined in RFC
         4446.

         SROS supports services corresponding to the following RFC 4446 PW Type
         code points.

         PW Type    Description
         -------    ---------------------------------------
          2         ATM AAL5 SDU VCC transport
          3         ATM transparent cell transport
          5         Ethernet
          9         ATM n-to-one VCC cell transport
         10         ATM n-to-one VPC cell transport
         17         Structure-agnostic E1 over packet
         18         Structure-agnostic T1 (DS1) over packet
         21         CES over PSN basic mode
         23         CES over PSN TDM with CAS

         Zero indicates no Pseudowire Type has been configured."
    REFERENCE
        "RFC 4379, 'Detecting Multi-Protocol Label Switched (MPLS) Data Plane
         Failures', Section 3.2.9 ('FEC 128 Pseudowire (Current)').
         RFC 4446, 'IANA Allocations for Pseudowire Edge to Edge Emulation
         (PWE3)', Section 3.2, 'MPLS Pseudowire Type'."
    DEFVAL      { 0 }
    ::= { tmnxOamVccvTrTgFec128CtlEntry 6 }

tmnxOamVccvTrTgStaticCtlTable    OBJECT-TYPE
    SYNTAX      SEQUENCE OF TmnxOamVccvTrTgStaticCtlEntry
    MAX-ACCESS  not-accessible
    STATUS      current
    DESCRIPTION
        "tmnxOamVccvTrTgStaticCtlTable contains the target information for VCCV
         (Virtual Circuit Connectivity Verification) trace route tests which
         switch to downstream static (i.e. MPLS-TP) segments."
    REFERENCE
        "RFC 6426, 'MPLS On-Demand Connectivity Verification and Route Tracing',
         section 2.3.2, 'Static Pseudowire Sub-TLV'."
    ::= { tmnxOamTraceRouteObjs 35 }

tmnxOamVccvTrTgStaticCtlEntry    OBJECT-TYPE
    SYNTAX      TmnxOamVccvTrTgStaticCtlEntry
    MAX-ACCESS  not-accessible
    STATUS      current
    DESCRIPTION
        "tmnxOamVccvTrTgStaticCtlEntry contains the target information for a
         VCCV trace route test which switches to a downstream static (i.e.
         MPLS-TP) segment.

         The values in a row are used to fill a 'Static Pseudowire' sub-TLV
         (Type, Length, Value) within the 'Target FEC Stack' TLV within the
         launched VCCV trace route request.

         A row is created when the test's tmnxOamVccvTrCtlSwitTgtFecType is set
         to 'static(3)'.

         A row is destroyed when the tmnxOamVccvTrCtlTable row is destroyed.

         All the objects in a row must be set in one SNMP Set PDU.  Otherwise,
         the SNMP Set PDU will be rejected."
    REFERENCE
        "RFC 6426, 'MPLS On-Demand Connectivity Verification and Route Tracing',
         section 2.3.2, 'Static Pseudowire Sub-TLV'."
    INDEX       {
        tmnxOamTrCtlOwnerIndex,
        tmnxOamTrCtlTestIndex
    }
    ::= { tmnxOamVccvTrTgStaticCtlTable 1 }

TmnxOamVccvTrTgStaticCtlEntry    ::= SEQUENCE
{
    tmnxOamVccvTrTgStaticCtlAgi      TmnxVPNRouteDistinguisher,
    tmnxOamVccvTrTgStaticCtlSaiiGlbl TmnxPwGlobalIdOrZero,
    tmnxOamVccvTrTgStaticCtlSaiiNode TmnxMplsTpNodeID,
    tmnxOamVccvTrTgStaticCtlSaiiAcId Unsigned32,
    tmnxOamVccvTrTgStaticCtlTaiiGlbl TmnxPwGlobalIdOrZero,
    tmnxOamVccvTrTgStaticCtlTaiiNode TmnxMplsTpNodeID,
    tmnxOamVccvTrTgStaticCtlTaiiAcId Unsigned32
}

tmnxOamVccvTrTgStaticCtlAgi      OBJECT-TYPE
    SYNTAX      TmnxVPNRouteDistinguisher
    MAX-ACCESS  read-write
    STATUS      current
    DESCRIPTION
        "The value of tmnxOamVccvTrTgStaticCtlAgi specifies the value to be
         copied into the 'Service Identifier' field of the 'Static Pseudowire'
         sub-TLV within the 'Target FEC Stack' TLV within the launched VCCV
         trace route request.  As specified in RFC 6426, the 'Service
         Identifier' field may be filled with an AGI (Attachment Group
         Identifier).

         The all-zeroes value indicates no Service Identifier has been
         configured."
    REFERENCE
        "RFC 6426, 'MPLS On-Demand Connectivity Verification and Route Tracing',
         section 2.3.2, 'Static Pseudowire Sub-TLV'.
         RFC 4446, 'IANA Allocations for Pseudowire Edge to Edge Emulation
         (PWE3)', section 3.4.2, 'Attachment Group Identifier (AGI) Type'."
    DEFVAL      { '0000000000000000'H }
    ::= { tmnxOamVccvTrTgStaticCtlEntry 1 }

tmnxOamVccvTrTgStaticCtlSaiiGlbl OBJECT-TYPE
    SYNTAX      TmnxPwGlobalIdOrZero
    MAX-ACCESS  read-write
    STATUS      current
    DESCRIPTION
        "The value of tmnxOamVccvTrTgStaticCtlSaiiGlbl specifies the value to
         be copied into the 'Source Global ID' field of the 'Static Pseudowire'
         sub-TLV within the 'Target FEC Stack' TLV within the launched VCCV
         trace route request.

         Zero indicates no Source Global ID has been configured."
    REFERENCE
        "RFC 6426, 'MPLS On-Demand Connectivity Verification and Route Tracing',
         section 2.3.2, 'Static Pseudowire Sub-TLV'.
         RFC 6370, 'MPLS Transport Profile (MPLS-TP) Identifiers', section 3,
         'Uniquely Identifying an Operator - the Global_ID'."
    DEFVAL      { 0 }
    ::= { tmnxOamVccvTrTgStaticCtlEntry 2 }

tmnxOamVccvTrTgStaticCtlSaiiNode OBJECT-TYPE
    SYNTAX      TmnxMplsTpNodeID
    MAX-ACCESS  read-write
    STATUS      current
    DESCRIPTION
        "The value of tmnxOamVccvTrTgStaticCtlSaiiNode specifies the value to
         be copied into the 'Source Node ID' field of the 'Static Pseudowire'
         sub-TLV within the 'Target FEC Stack' TLV within the launched VCCV
         trace route request.

         Zero indicates no Source Node ID has been configured."
    REFERENCE
        "RFC 6426, 'MPLS On-Demand Connectivity Verification and Route Tracing',
         section 2.3.2, 'Static Pseudowire Sub-TLV'.
         RFC 6370, 'MPLS Transport Profile (MPLS-TP) Identifiers', section 4,
         'Node and Interface Identifiers'."
    DEFVAL      { 0 }
    ::= { tmnxOamVccvTrTgStaticCtlEntry 3 }

tmnxOamVccvTrTgStaticCtlSaiiAcId OBJECT-TYPE
    SYNTAX      Unsigned32
    MAX-ACCESS  read-write
    STATUS      current
    DESCRIPTION
        "The value of tmnxOamVccvTrTgStaticCtlSaiiAcId specifies the value to
         be copied into the 'Source AC-ID' (Source Attachment Circuit
         Identifier) field of the 'Static Pseudowire' sub-TLV within the
         'Target FEC Stack' TLV within the launched VCCV trace route request.

         Zero indicates no Source AC-ID has been configured."
    REFERENCE
        "RFC 6426, 'MPLS On-Demand Connectivity Verification and Route Tracing',
         section 2.3.2, 'Static Pseudowire Sub-TLV'.
         RFC 5003, 'Attachment Individual Identifier (AII) Types for
         Aggregation', section 3.2, 'AII Type 2'."
    DEFVAL      { 0 }
    ::= { tmnxOamVccvTrTgStaticCtlEntry 4 }

tmnxOamVccvTrTgStaticCtlTaiiGlbl OBJECT-TYPE
    SYNTAX      TmnxPwGlobalIdOrZero
    MAX-ACCESS  read-write
    STATUS      current
    DESCRIPTION
        "The value of tmnxOamVccvTrTgStaticCtlTaiiGlbl specifies the value to
         be copied into the 'Destination Global ID' field of the 'Static
         Pseudowire' sub-TLV within the 'Target FEC Stack' TLV within the
         launched VCCV trace route request.

         Zero indicates no Destination Global ID has been configured."
    REFERENCE
        "RFC 6426, 'MPLS On-Demand Connectivity Verification and Route Tracing',
         section 2.3.2, 'Static Pseudowire Sub-TLV'.
         RFC 6370, 'MPLS Transport Profile (MPLS-TP) Identifiers', section 3,
         'Uniquely Identifying an Operator - the Global_ID'."
    DEFVAL      { 0 }
    ::= { tmnxOamVccvTrTgStaticCtlEntry 5 }

tmnxOamVccvTrTgStaticCtlTaiiNode OBJECT-TYPE
    SYNTAX      TmnxMplsTpNodeID
    MAX-ACCESS  read-write
    STATUS      current
    DESCRIPTION
        "The value of tmnxOamVccvTrTgStaticCtlTaiiNode specifies the value to
         be copied into the 'Destination Node ID' field of the 'Static
         Pseudowire' sub-TLV within the 'Target FEC Stack' TLV within the
         launched VCCV trace route request.

         Zero indicates no Destination Node ID has been configured."
    REFERENCE
        "RFC 6426, 'MPLS On-Demand Connectivity Verification and Route Tracing',
         section 2.3.2, 'Static Pseudowire Sub-TLV'.
         RFC 6370, 'MPLS Transport Profile (MPLS-TP) Identifiers', section 4,
         'Node and Interface Identifiers'."
    DEFVAL      { 0 }
    ::= { tmnxOamVccvTrTgStaticCtlEntry 6 }

tmnxOamVccvTrTgStaticCtlTaiiAcId OBJECT-TYPE
    SYNTAX      Unsigned32
    MAX-ACCESS  read-write
    STATUS      current
    DESCRIPTION
        "The value of tmnxOamVccvTrTgStaticCtlTaiiAcId specifies the value to
         be copied into the 'Destination AC-ID' (Destination Attachment Circuit
         Identifier) field of the 'Static Pseudowire' sub-TLV within the
         'Target FEC Stack' TLV within the launched VCCV trace route request.

         Zero indicates no Destination AC-ID has been configured."
    REFERENCE
        "RFC 6426, 'MPLS On-Demand Connectivity Verification and Route Tracing',
         section 2.3.2, 'Static Pseudowire Sub-TLV'.
         RFC 5003, 'Attachment Individual Identifier (AII) Types for
         Aggregation', section 3.2, 'AII Type 2'."
    DEFVAL      { 0 }
    ::= { tmnxOamVccvTrTgStaticCtlEntry 7 }

tmnxOamIcmpTrLabelStackTable     OBJECT-TYPE
    SYNTAX      SEQUENCE OF TmnxOamIcmpTrLabelStackEntry
    MAX-ACCESS  not-accessible
    STATUS      current
    DESCRIPTION
        "tmnxOamIcmpTrLabelStackTable contains the information read from RFC
         4950 MPLS Label Stack Objects in ICMPv4 or ICMPv6 replies, received in
         response to locally initiated 'icmpTraceRoute(5)' tests."
    REFERENCE
        "RFC 4950, 'ICMP Extensions for Multiprotocol Label Switching', Section
         5, 'MPLS Label Stack Object'."
    ::= { tmnxOamTraceRouteObjs 36 }

tmnxOamIcmpTrLabelStackEntry     OBJECT-TYPE
    SYNTAX      TmnxOamIcmpTrLabelStackEntry
    MAX-ACCESS  not-accessible
    STATUS      current
    DESCRIPTION
        "tmnxOamIcmpTrLabelStackEntry contains the information present in one
         member of an RFC 4950 MPLS Label Stack Object, as received in one
         ICMPv4 or ICMPv6 reply (received in response to a locally initiated
         'icmpTraceRoute(5)' test).

         One ICMPv4 or ICMPv6 reply can contain at most one MPLS Label Stack
         Object.  The MPLS Label Stack Object is a structure in the reply,
         containing the MPLS encapsulation used for the test.  One MPLS Label
         Stack Object contains one or more members.

         The first six indices specify the ICMPv4 or ICMPv6 reply.  The seventh
         index specifies the member number within the MPLS Label Stack Object.

         SROS creates rows in this table when an ICMPv4 or ICMPv6 reply is
         received (in response to a locally initiated 'icmpTraceRoute(5)' test)
         containing an MPLS Label Stack Object.  One row is created for each
         member in the MPLS Label Stack Object.

         SROS destroys rows in this table when the corresponding
         tmnxOamTrProbeHistoryTable row is destroyed."
    REFERENCE
        "RFC 4950, 'ICMP Extensions for Multiprotocol Label Switching', Section
         5, 'MPLS Label Stack Object'."
    INDEX       {
        tmnxOamTrCtlOwnerIndex,
        tmnxOamTrCtlTestIndex,
        tmnxOamTrResultsTestRunIndex,
        tmnxOamTrProbeHistoryIndex,
        tmnxOamTrProbeHistoryHopIndex,
        tmnxOamTrProbeHistoryProbeIndex,
        tmnxOamIcmpTrLabelStackMemberNum
    }
    ::= { tmnxOamIcmpTrLabelStackTable 1 }

TmnxOamIcmpTrLabelStackEntry     ::= SEQUENCE
{
    tmnxOamIcmpTrLabelStackMemberNum Unsigned32,
    tmnxOamIcmpTrLabelStackLabel     Unsigned32,
    tmnxOamIcmpTrLabelStackExperimnt Unsigned32,
    tmnxOamIcmpTrLabelStackBottom    Unsigned32,
    tmnxOamIcmpTrLabelStackTtl       Unsigned32
}

tmnxOamIcmpTrLabelStackMemberNum OBJECT-TYPE
    SYNTAX      Unsigned32 (1..4294967295)
    MAX-ACCESS  not-accessible
    STATUS      current
    DESCRIPTION
        "The value of tmnxOamIcmpTrLabelStackMemberNum specifies the member
         number within an RFC 4950 MPLS Label Stack Object.

         The first member within an MPLS Label Stack Object is member number 1.
         Subsequent members (if any) are numbered consecutively."
    REFERENCE
        "RFC 4950, 'ICMP Extensions for Multiprotocol Label Switching', Section
         5, 'MPLS Label Stack Object'."
    ::= { tmnxOamIcmpTrLabelStackEntry 1 }

tmnxOamIcmpTrLabelStackLabel     OBJECT-TYPE
    SYNTAX      Unsigned32 (0..1048575)
    MAX-ACCESS  read-only
    STATUS      current
    DESCRIPTION
        "The value of tmnxOamIcmpTrLabelStackLabel indicates the Label field
         within the specified RFC 4950 MPLS Label Stack Object member."
    REFERENCE
        "RFC 4950, 'ICMP Extensions for Multiprotocol Label Switching', Section
         5, 'MPLS Label Stack Object'."
    ::= { tmnxOamIcmpTrLabelStackEntry 2 }

tmnxOamIcmpTrLabelStackExperimnt OBJECT-TYPE
    SYNTAX      Unsigned32 (0..7)
    MAX-ACCESS  read-only
    STATUS      current
    DESCRIPTION
        "The value of tmnxOamIcmpTrLabelStackExperimnt indicates the
         Experimental Use field within the specified RFC 4950 MPLS Label Stack
         Object member."
    REFERENCE
        "RFC 4950, 'ICMP Extensions for Multiprotocol Label Switching', Section
         5, 'MPLS Label Stack Object'."
    ::= { tmnxOamIcmpTrLabelStackEntry 3 }

tmnxOamIcmpTrLabelStackBottom    OBJECT-TYPE
    SYNTAX      Unsigned32 (0..1)
    MAX-ACCESS  read-only
    STATUS      current
    DESCRIPTION
        "The value of tmnxOamIcmpTrLabelStackBottom indicates the Bottom of
         Stack bit within the specified RFC 4950 MPLS Label Stack Object
         member."
    REFERENCE
        "RFC 4950, 'ICMP Extensions for Multiprotocol Label Switching', Section
         5, 'MPLS Label Stack Object'."
    ::= { tmnxOamIcmpTrLabelStackEntry 4 }

tmnxOamIcmpTrLabelStackTtl       OBJECT-TYPE
    SYNTAX      Unsigned32 (0..255)
    MAX-ACCESS  read-only
    STATUS      current
    DESCRIPTION
        "The value of tmnxOamIcmpTrLabelStackTtl indicates the Time To Live
         field within the specified RFC 4950 MPLS Label Stack Object member."
    REFERENCE
        "RFC 4950, 'ICMP Extensions for Multiprotocol Label Switching', Section
         5, 'MPLS Label Stack Object'."
    ::= { tmnxOamIcmpTrLabelStackEntry 5 }

tmnxOamSaaObjs                   OBJECT IDENTIFIER ::= { tmnxOamTestObjs 3 }

tmnxOamSaaNotifyObjects          OBJECT IDENTIFIER ::= { tmnxOamSaaObjs 1 }

tmnxOamSaaCtlTable               OBJECT-TYPE
    SYNTAX      SEQUENCE OF TmnxOamSaaCtlEntry
    MAX-ACCESS  not-accessible
    STATUS      current
    DESCRIPTION
        "tmnxOamSaaCtlTable contains configuration and status information for
         Service Assurance Agent (SAA) tests.

         A TIMETRA-OAM-TEST-MIB test has one of two retention types.
         1.  An SAA test has a tmnxOamSaaCtlTable row.  All the configuration
         information for an SAA test is retained across an SROS CPM activity
         switch or an SROS CPM reset.
         2.  An OAM test does not have a tmnxOamSaaCtlTable row.  All the
         configuration information for an OAM test is forgotten across an SROS
         CPM activity switch or an SROS CPM reset.

         The results of an SAA test (or an OAM test) are stored in the ping or
         trace route results tables (e.g. tmnxOamPingResultsTable,
         tmnxOamPingHistoryTable, tmnxOamTrResultsTable, tmnxOamTrHopsTable)."
    ::= { tmnxOamSaaObjs 2 }

tmnxOamSaaCtlEntry               OBJECT-TYPE
    SYNTAX      TmnxOamSaaCtlEntry
    MAX-ACCESS  not-accessible
    STATUS      current
    DESCRIPTION
        "tmnxOamSaaCtlEntry contains the configuration and status information
         for one SAA test.

         Rows are created and destroyed using tmnxOamSaaCtlRowStatus."
    INDEX       {
        tmnxOamSaaCtlOwnerIndex,
        tmnxOamSaaCtlTestIndex
    }
    ::= { tmnxOamSaaCtlTable 1 }

TmnxOamSaaCtlEntry               ::= SEQUENCE
{
    tmnxOamSaaCtlOwnerIndex          SnmpAdminString,
    tmnxOamSaaCtlTestIndex           SnmpAdminString,
    tmnxOamSaaCtlRowStatus           RowStatus,
    tmnxOamSaaCtlStorageType         StorageType,
    tmnxOamSaaCtlLastChanged         TimeStamp,
    tmnxOamSaaCtlAdminStatus         TmnxAdminState,
    tmnxOamSaaCtlDescr               TItemDescription,
    tmnxOamSaaCtlTestMode            TmnxOamTestMode,
    tmnxOamSaaCtlRuns                Counter32,
    tmnxOamSaaCtlFailures            Counter32,
    tmnxOamSaaCtlLastRunResult       TmnxOamTestResult,
    tmnxOamSaaCtlAcctPolicyId        Integer32,
    tmnxOamSaaCtlSuppressAccounting  TruthValue,
    tmnxOamSaaCtlContinuous          TruthValue,
    tmnxOamSaaCtlKeepProbeHistoryAdm INTEGER,
    tmnxOamSaaCtlKeepProbeHistoryOpr INTEGER
}

tmnxOamSaaCtlOwnerIndex          OBJECT-TYPE
    SYNTAX      SnmpAdminString (SIZE (1..32))
    MAX-ACCESS  not-accessible
    STATUS      current
    DESCRIPTION
        "To facilitate the provisioning of access control by a
         security administrator using the View-Based Access
         Control Model (RFC 2575, VACM) for tables in which
         multiple users may need to independently create or
         modify entries, the initial index is used as an 'owner
         index'.  Such an initial index has a syntax of
         SnmpAdminString, and can thus be trivially mapped to a
         security name or group name as defined in VACM, in
         accordance with a security policy.

         When used in conjunction with such a security policy all
         entries in the table belonging to a particular user (or
         group) will have the same value for this initial index.
         For a given user's entries in a particular table, the
         object identifiers for the information in these entries
         will have the same subidentifiers (except for the 'column'
         subidentifier) up to the end of the encoded owner index.
         To configure VACM to permit access to this portion of the
         table, one would create vacmViewTreeFamilyTable entries
         with the value of vacmViewTreeFamilySubtree including
         the owner index portion, and vacmViewTreeFamilyMask
         'wildcarding' the column subidentifier.  More elaborate
         configurations are possible."
    ::= { tmnxOamSaaCtlEntry 1 }

tmnxOamSaaCtlTestIndex           OBJECT-TYPE
    SYNTAX      SnmpAdminString (SIZE (1..32))
    MAX-ACCESS  not-accessible
    STATUS      current
    DESCRIPTION
        "The test name index of the Nokia SROS OAM Service Assurance
         Agent, SAA, test.  This is locally unique, within the scope of an
         tmnxOamSaaCtlOwnerIndex."
    ::= { tmnxOamSaaCtlEntry 2 }

tmnxOamSaaCtlRowStatus           OBJECT-TYPE
    SYNTAX      RowStatus
    MAX-ACCESS  read-create
    STATUS      current
    DESCRIPTION
        "This object allows entries to be created and deleted
         in the tmnxOamSaaCtlTable.  Deletion of an entry in this
         table results in all corresponding control and results entries
         in either the ping or traceroute tables.

         Activation of a Nokia SROS OAM ping or trace route operation is
         controlled via tmnxOamPingCtlAdminStatus or tmnxOamTrCtlAdminStatus
         and not by changing this object's value to 'active (1)'.

         An attempt to delete an entry in this table by setting this object's
         value to 'destroy (6)' will fail with an inconsistentValue error if
         the associated ping or traceroute test is in progress.

         An attempt to delete an entry in this table by setting this object's
         value to 'destroy (6)' will fail with an inconsistentValue error if
         the value of tmnxOamSaaCtlAdminStatus is not 'outOfService'.

         The operational state of an Nokia SROS OAM SAA test operation can be
         determined by examination of its associated
         tmnxOamPingResultsOperStatus or tmnxOamTrResultsOperStatus object."
    REFERENCE
        "See definition of RowStatus in RFC 2579, 'Textual
         Conventions for SMIv2.'"
    ::= { tmnxOamSaaCtlEntry 3 }

tmnxOamSaaCtlStorageType         OBJECT-TYPE
    SYNTAX      StorageType
    MAX-ACCESS  read-create
    STATUS      obsolete
    DESCRIPTION
        "The storage type for this conceptual row. Conceptual rows having the
         value 'permanent' need not allow write-access to any columnar objects
         in the row.

         This object was marked obsolete in SROS Release 14.0 R1.  There is no
         replacement object."
    DEFVAL      { nonVolatile }
    ::= { tmnxOamSaaCtlEntry 4 }

tmnxOamSaaCtlLastChanged         OBJECT-TYPE
    SYNTAX      TimeStamp
    MAX-ACCESS  read-only
    STATUS      current
    DESCRIPTION
        "The value of tmnxOamSaaCtlLastChanged indicates the time the value of
         a settable object in this row was last changed."
    ::= { tmnxOamSaaCtlEntry 5 }

tmnxOamSaaCtlAdminStatus         OBJECT-TYPE
    SYNTAX      TmnxAdminState
    MAX-ACCESS  read-create
    STATUS      current
    DESCRIPTION
        "The value of tmnxOamSaaCtlAdminStatus specifies the desired
         administrative state of the Service Assurance Agent, SAA, test.

         When the value of tmnxOamSaaCtlAdminStatus is 'outOfService', an
         attempt to start this SAA test by setting its associated
         tmnxOamPingCtlAdminStatus or tmnxOamTrCtlAdminStatus to 'enabled (1)'
         will fail with an inconsistentValue error.

         When the value of tmnxOamSaaCtlAdminStatus is 'inService' attempts to
         modify any other object in the associated tmnxOamPingCtlTable,
         tmnxOamTrCtlTable or the control table for the specific OAM test type
         will fail with an inconsistentValue error."
    DEFVAL      { outOfService }
    ::= { tmnxOamSaaCtlEntry 6 }

tmnxOamSaaCtlDescr               OBJECT-TYPE
    SYNTAX      TItemDescription
    MAX-ACCESS  read-create
    STATUS      current
    DESCRIPTION
        "The value of tmnxOamSaaCtlDescr specifies a user provided description
         string for this SAA test.  It can consist of any printable,
         seven-bit ASCII characters up to 80 characters in length."
    DEFVAL      { "" }
    ::= { tmnxOamSaaCtlEntry 7 }

tmnxOamSaaCtlTestMode            OBJECT-TYPE
    SYNTAX      TmnxOamTestMode
    MAX-ACCESS  read-only
    STATUS      current
    DESCRIPTION
        "The value of tmnxOamSaaCtlTestMode indicates the type of Service
         Assurance Agent (SAA) test to be performed.

         When the value of this object is 'notConfigured(0)', no associated row
         exists in either the tmnxOamPingCtlTable or tmnxOamTrCtlTable.

         When the value of this object is 'ping(1)', an associated row exists
         in the tmnxOamPingCtlTable.

         When the value of this object is 'traceroute(2)', an associated row
         exists in the tmnxOamTrCtlTable."
    DEFVAL      { notConfigured }
    ::= { tmnxOamSaaCtlEntry 8 }

tmnxOamSaaCtlRuns                OBJECT-TYPE
    SYNTAX      Counter32
    MAX-ACCESS  read-only
    STATUS      current
    DESCRIPTION
        "The value of tmnxOamSaaCtlRuns indicates the number of times this OAM
         SAA test has been executed."
    ::= { tmnxOamSaaCtlEntry 9 }

tmnxOamSaaCtlFailures            OBJECT-TYPE
    SYNTAX      Counter32
    MAX-ACCESS  read-only
    STATUS      current
    DESCRIPTION
        "The value of tmnxOamSaaCtlFailures indicates the number of times this
         OAM SAA test has failed."
    ::= { tmnxOamSaaCtlEntry 10 }

tmnxOamSaaCtlLastRunResult       OBJECT-TYPE
    SYNTAX      TmnxOamTestResult
    MAX-ACCESS  read-only
    STATUS      current
    DESCRIPTION
        "The value of tmnxOamSaaCtlLastRunResult indicates the completion
         status the last time this test was executed.  If this OAM test is
         currently in progress, this object indicates the result of the
         previous test run, if any."
    ::= { tmnxOamSaaCtlEntry 11 }

tmnxOamSaaCtlAcctPolicyId        OBJECT-TYPE
    SYNTAX      Integer32 (0..99)
    MAX-ACCESS  read-create
    STATUS      current
    DESCRIPTION
        "The value of tmnxOamSaaCtlAcctPolicyId specifies the accounting policy
         used to record the information obtained from the results tables.  A
         value of zero specifies no accounting policy.

         A non-zero accounting policy must be configured with the SAA record
         generation option.  For example, an attempt to set this object to 99
         will be rejected if TIMETRA-LOG-MIB::tmnxLogApRecord.99 is not
         'saa(32)'."
    DEFVAL      { 0 }
    ::= { tmnxOamSaaCtlEntry 12 }

tmnxOamSaaCtlSuppressAccounting  OBJECT-TYPE
    SYNTAX      TruthValue
    MAX-ACCESS  read-create
    STATUS      current
    DESCRIPTION
        "The value of tmnxOamSaaCtlSuppressAccounting specifies whether or not
         the updating of accounting files is suppressed. The value of 'true
         (1)' is applicable only when an accounting policy has been specified
         by tmnxOamSaaCtlAcctPolicyId.

         Upon completion of a test, this object is reset to its default value."
    DEFVAL      { false }
    ::= { tmnxOamSaaCtlEntry 13 }

tmnxOamSaaCtlContinuous          OBJECT-TYPE
    SYNTAX      TruthValue
    MAX-ACCESS  read-create
    STATUS      current
    DESCRIPTION
        "The value of tmnxOamSaaCtlContinuous specifies whether or not the SAA
         test is to be executed indefinitely.

         Setting tmnxOamSaaCtlContinuous to 'true(1)' is accepted for the
         following ping test types:
            'ethCfmLoopback    (19)',
            'ethCfmTwoWayDelay (20)',
            'ethCfmTwoWaySlm   (22)',
            'icmpPing          (15)',
            'lspPing           ( 8)'.

         Setting tmnxOamSaaCtlContinuous to 'true(1)' is accepted for the
         following trace test types:
            'ethCfmLinkTrace (9)'."
    DEFVAL      { false }
    ::= { tmnxOamSaaCtlEntry 14 }

tmnxOamSaaCtlKeepProbeHistoryAdm OBJECT-TYPE
    SYNTAX      INTEGER {
        keep (1),
        drop (2),
        auto (3)
    }
    MAX-ACCESS  read-create
    STATUS      current
    DESCRIPTION
        "The value of tmnxOamSaaCtlKeepProbeHistoryAdm specifies whether or not
         per-probe history table rows will be created for this test.  A test
         without per-probe history table rows consumes less CPM RAM.

         tmnxOamSaaCtlKeepProbeHistoryOpr is a read-only operational value
         derived from tmnxOamSaaCtlKeepProbeHistoryAdm.  The bulk of the
         tmnxOamSaaCtlKeepProbeHistoryAdm semantics are described in the
         tmnxOamSaaCtlKeepProbeHistoryOpr DESCRIPTION clause.

         An attempt to set tmnxOamSaaCtlKeepProbeHistoryAdm to 'drop(2)' when
         tmnxOamSaaCtlTestMode is not 'ping(1)' returns an 'inconsistentValue'
         error to the manager.

         When the SAA test's test mode is deconfigured (i.e.
         tmnxOamSaaCtlTestMode becomes 'notConfigured(0)'),
         tmnxOamSaaCtlKeepProbeHistoryAdm returns to its default value."
    DEFVAL      { auto }
    ::= { tmnxOamSaaCtlEntry 15 }

tmnxOamSaaCtlKeepProbeHistoryOpr OBJECT-TYPE
    SYNTAX      INTEGER {
        keep (1),
        drop (2)
    }
    MAX-ACCESS  read-only
    STATUS      current
    DESCRIPTION
        "The value of tmnxOamSaaCtlKeepProbeHistoryOpr indicates whether or not
         per-probe history table rows will be created for this test.  A test
         without per-probe history table rows consumes less CPM RAM.

         The value of tmnxOamSaaCtlKeepProbeHistoryOpr is derived from the
         value of`tmnxOamSaaCtlKeepProbeHistoryAdm, as shown in the following
         table.

         tmnxOamSaaCtlKeepProbeHistoryAdm tmnxOamSaaCtlKeepProbeHistoryOpr
         -------------------------------- --------------------------------------
         'keep(1)'                        'keep(1)'
         'drop(2)'                        'drop(2)'
         'auto(3)'                        'keep(1)' or 'drop(2)', chosen by SROS

         The history table rows created for the combinations of
         tmnxOamSaaCtlKeepProbeHistoryOpr and tmnxOamSaaCtlTestMode values are
         shown in the following table.

         Configuration Options           History Table Rows Created
         --------------------------      --------------------------
         'keep(1)', 'ping(1)'            tmnxOamPingHistoryTable or
                                         tmnxOamMacPingHistoryTable
         'keep(1)', 'traceroute(2)'      tmnxOamTrProbeHistoryTable
         'drop(2)', 'ping(1)'            none
         'drop(2)', 'traceroute(2)'      unsupported combination.

         If tmnxOamSaaCtlTestMode is 'notConfigured(0)', the value of
         tmnxOamSaaCtlKeepProbeHistoryOpr is insignificant, since a test without
         a test mode cannot be started.  When a Get is performed on
         tmnxOamSaaCtlKeepProbeHistoryOpr in this case, 'keep(1)' is returned.

         If tmnxOamSaaCtlKeepProbeHistoryAdm is 'auto(3)':
           1.  tmnxOamSaaCtlKeepProbeHistoryOpr is 'drop(2)' if
               a) the test's probe count is greater than 100, OR
               b) the test's interval is less than one second, OR
               c) tmnxOamSaaCtlTestMode is 'ping(1)' AND the test is continuous
                  (i.e. tmnxOamSaaCtlContinuous is 'true') AND an accounting
                  policy is specified (i.e. tmnxOamSaaCtlAcctPolicyId is non-
                  zero).
           2.  Otherwise,  tmnxOamSaaCtlKeepProbeHistoryOpr is 'keep(1)'."
    ::= { tmnxOamSaaCtlEntry 16 }

tmnxOamSaaThresholdTable         OBJECT-TYPE
    SYNTAX      SEQUENCE OF TmnxOamSaaThresholdEntry
    MAX-ACCESS  not-accessible
    STATUS      current
    DESCRIPTION
        "tmnxOamSaaThresholdTable contains notification threshold information
         for SAA tests."
    ::= { tmnxOamSaaObjs 3 }

tmnxOamSaaThresholdEntry         OBJECT-TYPE
    SYNTAX      TmnxOamSaaThresholdEntry
    MAX-ACCESS  not-accessible
    STATUS      current
    DESCRIPTION
        "Defines an entry in the tmnxOamSaaThresholdTable.  The first index
         element, tmnxOamSaaCtlOwnerIndex, is of type SnmpAdminString,
         a textual convention that allows for use of the SNMPv3
         View-Based Access Control Model (RFC 2575 [11], VACM)
         and allows a management application to identify its entries.
         The second index, tmnxOamSaaCtlTestIndex, enables the same
         management application to have multiple outstanding requests.
         The third index element identifies the type of statistic to be
         monitored for threshold crossing.  The fourth index element
         identifies which direction, rising or falling, to monitor."
    INDEX       {
        tmnxOamSaaCtlOwnerIndex,
        tmnxOamSaaCtlTestIndex,
        tmnxOamSaaTType,
        tmnxOamSaaTDirection
    }
    ::= { tmnxOamSaaThresholdTable 1 }

TmnxOamSaaThresholdEntry         ::= SEQUENCE
{
    tmnxOamSaaTType                  TmnxOamSaaThreshold,
    tmnxOamSaaTDirection             INTEGER,
    tmnxOamSaaTRowStatus             RowStatus,
    tmnxOamSaaTLastChanged           TimeStamp,
    tmnxOamSaaTThreshold             Unsigned32,
    tmnxOamSaaTValue                 Integer32,
    tmnxOamSaaTLastSent              TimeStamp,
    tmnxOamSaaTTestMode              TmnxOamTestMode,
    tmnxOamSaaTTestRunIndex          Unsigned32
}

tmnxOamSaaTType                  OBJECT-TYPE
    SYNTAX      TmnxOamSaaThreshold
    MAX-ACCESS  not-accessible
    STATUS      current
    DESCRIPTION
        "The value of tmnxOamSaaTType specifies the type of monitored statistic
         used to determine if a tmnxOamSaaThreshold notification is generated
         at the completion of an SAA test run."
    ::= { tmnxOamSaaThresholdEntry 1 }

tmnxOamSaaTDirection             OBJECT-TYPE
    SYNTAX      INTEGER {
        rising  (1),
        falling (2)
    }
    MAX-ACCESS  not-accessible
    STATUS      current
    DESCRIPTION
        "The value of tmnxOamSaaTDirection specifies whether to monitor this
         threshold for crossing in the rising or falling direction."
    ::= { tmnxOamSaaThresholdEntry 2 }

tmnxOamSaaTRowStatus             OBJECT-TYPE
    SYNTAX      RowStatus
    MAX-ACCESS  read-create
    STATUS      current
    DESCRIPTION
        "The value of tmnxOamSaaTRowStatus controls creation and deletion of
         row entries in the tmnxOamSaaThresholdTable.

         When a row in this table is created, tmnxOamSaaTThreshold must also be
         set or the row creation will fail with an inconsistentValue error."
    ::= { tmnxOamSaaThresholdEntry 3 }

tmnxOamSaaTLastChanged           OBJECT-TYPE
    SYNTAX      TimeStamp
    MAX-ACCESS  read-only
    STATUS      current
    DESCRIPTION
        "The value of tmnxOamSaaTLastChanged indicates the last time the value
         of tmnxOamSaaTThreshold was modified."
    ::= { tmnxOamSaaThresholdEntry 4 }

tmnxOamSaaTThreshold             OBJECT-TYPE
    SYNTAX      Unsigned32 (0..2147483647)
    MAX-ACCESS  read-create
    STATUS      current
    DESCRIPTION
        "The value of tmnxOamSaaTThreshold specifies the threshold value to
         monitor to determine when to generate a tmnxOamSaaThreshold
         notification.

         A threshold value must be set when the row entry is created."
    ::= { tmnxOamSaaThresholdEntry 5 }

tmnxOamSaaTValue                 OBJECT-TYPE
    SYNTAX      Integer32
    MAX-ACCESS  read-only
    STATUS      current
    DESCRIPTION
        "The value of tmnxOamSaaTValue indicates the value of the statistic
         that last caused a tmnxOamSaaThreshold notification to be generated."
    ::= { tmnxOamSaaThresholdEntry 6 }

tmnxOamSaaTLastSent              OBJECT-TYPE
    SYNTAX      TimeStamp
    MAX-ACCESS  read-only
    STATUS      current
    DESCRIPTION
        "The value of tmnxOamSaaTLastSent indicates the last time a
         tmnxOamSaaThreshold notification was generated as a result of crossing
         the threshold specified by the value of tmnxOamSaaTThreshold."
    ::= { tmnxOamSaaThresholdEntry 7 }

tmnxOamSaaTTestMode              OBJECT-TYPE
    SYNTAX      TmnxOamTestMode
    MAX-ACCESS  read-only
    STATUS      current
    DESCRIPTION
        "The value of tmnxOamSaaTTestMode indicates the type of Service
         Assurance Agent, SAA, test for which a tmnxOamSaaThreshold
         notification was generated as a result of crossing the threshold
         specified by the value of tmnxOamSaaTThreshold.

         When the value of this object is 'notConfigured', no associated entry
         exists in either the tmnxOamPingCtlTable or tmnxOamTrCtlTable.

         When the value of this object is 'ping', an associated test entry is
         configured in the tmnxOamPingCtlTable.

         When the value of this object is 'traceroute', an associated test
         entry is configured in the tmnxOamTrCtlTable."
    ::= { tmnxOamSaaThresholdEntry 8 }

tmnxOamSaaTTestRunIndex          OBJECT-TYPE
    SYNTAX      Unsigned32
    MAX-ACCESS  read-only
    STATUS      current
    DESCRIPTION
        "The value of tmnxOamSaaTTestRunIndex indicates the test run index of
         the Service Assurance Agent, SAA, test for which the last
         tmnxOamSaaThreshold notification was generated as a result of crossing
         the threshold specified by the value of tmnxOamSaaTThreshold.

         When the value of tmnxOamSaaTTestMode is 'ping', the value of this
         object is the value of the tmnxOamPingResultsTestRunIndex that
         identifies entries for the ping test results of the test run that
         generated the last tmnxOamSaaThreshold notification.

         When the value of tmnxOamSaaTTestMode is 'traceroute', the value of
         this object is the value of the tmnxOamTrResultsTestRunIndex that
         identifies entries for the traceroute test results of the test run
         that generated the last tmnxOamSaaThreshold notification.

         When the value of tmnxOamSaaTTestMode is 'notConfigured', the value of
         this object is zero."
    ::= { tmnxOamSaaThresholdEntry 9 }

tmnxOamMobGatewayObjs            OBJECT IDENTIFIER ::= { tmnxOamTestObjs 4 }

tmnxOamMobGtpPingCtlTable        OBJECT-TYPE
    SYNTAX      SEQUENCE OF TmnxOamMobGtpPingCtlEntry
    MAX-ACCESS  not-accessible
    STATUS      current
    DESCRIPTION
        "Defines the Nokia 7x50 SR OAM VPRN Ping Control Table for providing,
         via SNMP, the capability of performing Nokia 7x50 SR OAM 'mobGtpPing'
         test operations.

         The results of these tests are stored in the tmnxOamPingResultsTable
         and the tmnxOamTrProbeHistoryTable.  There will be no entries for
         these tests in the tmnxOamPingHistoryTable."
    ::= { tmnxOamMobGatewayObjs 1 }

tmnxOamMobGtpPingCtlEntry        OBJECT-TYPE
    SYNTAX      TmnxOamMobGtpPingCtlEntry
    MAX-ACCESS  not-accessible
    STATUS      current
    DESCRIPTION
        "Defines an entry in the tmnxOamMobGtpPingCtlTable.  The first index
         element, tmnxOamPingCtlOwnerIndex, is of type SnmpAdminString,
         a textual convention that allows for use of the SNMPv3
         View-Based Access Control Model (RFC 2575 [11], VACM)
         and allows a management application to identify its entries.
         The second index, tmnxOamPingCtlTestIndex, enables the same
         management application to have multiple outstanding requests."
    INDEX       {
        tmnxOamPingCtlOwnerIndex,
        tmnxOamPingCtlTestIndex
    }
    ::= { tmnxOamMobGtpPingCtlTable 1 }

TmnxOamMobGtpPingCtlEntry        ::= SEQUENCE
{
    tmnxOamMobGtpPingRefPointType    INTEGER,
    tmnxOamMobGtpPingVRtrId          TmnxVRtrID,
    tmnxOamMobGtpPingPort            InetPortNumber,
    tmnxOamMobGtpPingGateway         TmnxMobGwId
}

tmnxOamMobGtpPingRefPointType    OBJECT-TYPE
    SYNTAX      INTEGER {
        s11 (1),
        s5c (2),
        s1u (3),
        s5u (4),
        gnc (5),
        s8c (6),
        s8u (7),
        gpc (8)
    }
    MAX-ACCESS  read-create
    STATUS      current
    DESCRIPTION
        "The value of tmnxOamMobGtpPingRefPointType specifies the reference
         point type.

         This object is required."
    ::= { tmnxOamMobGtpPingCtlEntry 1 }

tmnxOamMobGtpPingVRtrId          OBJECT-TYPE
    SYNTAX      TmnxVRtrID
    MAX-ACCESS  read-create
    STATUS      current
    DESCRIPTION
        "The value of tmnxOamMobGtpPingVRtrId specifies the virtual router.

         This object is required."
    ::= { tmnxOamMobGtpPingCtlEntry 2 }

tmnxOamMobGtpPingPort            OBJECT-TYPE
    SYNTAX      InetPortNumber
    MAX-ACCESS  read-create
    STATUS      current
    DESCRIPTION
        "The value of tmnxOamMobGtpPingPort specifies the port number of the
         destination.

         This object is required."
    ::= { tmnxOamMobGtpPingCtlEntry 3 }

tmnxOamMobGtpPingGateway         OBJECT-TYPE
    SYNTAX      TmnxMobGwId
    MAX-ACCESS  read-create
    STATUS      current
    DESCRIPTION
        "The value of tmnxOamMobGtpPingGateway specifies the mobile gateway id.

         This object is required."
    ::= { tmnxOamMobGtpPingCtlEntry 4 }

tmnxOamGeneralObjs               OBJECT IDENTIFIER ::= { tmnxOamTestObjs 5 }

tmnxOamMplsPduTimeStampFormat    OBJECT-TYPE
    SYNTAX      INTEGER {
        rfc4379 (0),
        unix    (1)
    }
    MAX-ACCESS  read-write
    STATUS      current
    DESCRIPTION
        "The value of tmnxOamMplsPduTimeStampFormat specifies, on a system-wide
         basis:
         a) the format of the time stamp to be written into an RFC 4379 MPLS
            Echo Request PDU, when initiating a ping or trace route test,
            and
         b) the format of the time stamp to be written into an RFC 4379 MPLS
            Echo Reply PDU, when replying to an incoming MPLS Echo Request PDU,
            and
         c) the format to use when decoding the time stamps in an incoming MPLS
            Echo Request or MPLS Echo Reply PDU.

         'rfc4379(0)' specifies the RFC 4379 time stamp format.  The time
         stamp's 'seconds' field holds the integral number of seconds since
         1-Jan-1900 00:00:00 UTC.  The time stamp's 'microseconds' field
         contains a microseconds value in the range 0..999999.  This setting is
         used to interoperate with network elements which are fully compliant
         with RFC 4379 (e.g. an SROS system with the same setting, or any other
         RFC 4379 compliant router).

         'unix(1)' specifies the Unix time stamp format.  The time stamp's
         'seconds' field holds a 'Unix time', i.e. the integral number of
         seconds since 1-Jan-1970 00:00:00 UTC.  The time stamp's 'microseconds'
         field contains a microseconds value in the range 0..999999.  This
         setting is used to interoperate with network elements which send and
         expect a 1970-based timestamp in MPLS Echo Request/Reply PDUs (e.g. an
         SROS system with the same setting, or an SROS system running software
         earlier than R8.0 R4).

         Prior to SROS Release 8.0 R4, this object was not supported.  The Unix
         time stamp format was always used.

         This object is applicable for the ldpTreeTrace, lspPing,
         lspTraceRoute, p2mpLspPing, p2mpLspTrace, vccvPing, and vccvTraceRoute
         test modes only."
    REFERENCE
        "RFC 4379, Feb-2006, Section 3."
    DEFVAL      { unix }
    ::= { tmnxOamGeneralObjs 1 }

tmnxOamGeneralStats              OBJECT IDENTIFIER ::= { tmnxOamGeneralObjs 2 }

tmnxOamSysPerfOprLimitTx         OBJECT-TYPE
    SYNTAX      Gauge32
    UNITS       "echo request packets per second"
    MAX-ACCESS  read-only
    STATUS      current
    DESCRIPTION
        "The value of tmnxOamSysPerfOprLimitTx indicates this node's upper bound
         on the total echo request packet transmission rate.  Echo reply packets
         are not affected by this limit.

         The upper bound applies to echo request packets sent by the following
         test types:
         1.  Background ICMP Bridged Residential Gateway ping test.
         2.  Filter redirect policy ping test.
         3.  SDP keep-alive.
         4.  Static route CPE check.
         5.  VRRP policy host unreachable ping test.
         6.  Any OAM or SAA test configured using TIMETRA-OAM-TEST-MIB.
         7.  Any test configured using TIMETRA-OAM-PM-MIB."
    ::= { tmnxOamGeneralStats 1 }

tmnxOamSysPerfCfgLimitTx         OBJECT-TYPE
    SYNTAX      Gauge32
    UNITS       "echo request packets per second"
    MAX-ACCESS  read-only
    STATUS      current
    DESCRIPTION
        "The value of tmnxOamSysPerfCfgLimitTx indicates this node's upper bound
         on the total configured echo request packet transmission rate for a set
         of test types.  The upper bound is enforced to avoid echo request
         packet transmit overload, i.e. to ensure each enabled test can transmit
         echo request packets at the test's configured rate.  Echo reply packets
         are not affected by this limit.

         The upper bound applies to echo request packets sent by the following
         'always on' test types:
         1.  Background ICMP Bridged Residential Gateway ping test.
         2.  Filter redirect policy ping test.
         3.  SDP keep-alive.
         4.  Static route CPE check.
         5.  VRRP policy host unreachable ping test.
         6.  SAA continuous test (see tmnxOamSaaCtlContinuous).
         7.  OAM-PM proactive test (see
             TIMETRA-OAM-PM-MIB::tmnxOamPmCfgSessType).

         For example, suppose:
         a) tmnxOamSysPerfCfgLimitTx has the value 4000 echo request packets per
            second, and
         b) several SDP keep-alive sessions are enabled, totalling 1000 echo
            request packets per second, and
         c) several SAA continuous tests are enabled, totalling 3000 echo
            request packets per second.
         Then, an attempt to enable an additional SAA continuous test would be
         rejected with a 'resourceUnavailable(13)' error."
    ::= { tmnxOamGeneralStats 2 }

tmnxOamSysPerfCfgTotalTx         OBJECT-TYPE
    SYNTAX      Gauge32
    UNITS       "echo request packets per second"
    MAX-ACCESS  read-only
    STATUS      current
    DESCRIPTION
        "The value of tmnxOamSysPerfCfgTotalTx indicates this node's current
         total configured echo request packet transmission rate, for the set of
         tests listed in the tmnxOamSysPerfCfgLimitTx DESCRIPTION clause.

         For example, suppose:
         a) several SDP keep-alive sessions are enabled, totalling 1000 echo
            request packets per second, and
         b) several SAA continuous tests are enabled, totalling 2000 echo
            request packets per second, and
         c) no other relevant tests are enabled.
         Then, tmnxOamSysPerfCfgTotalTx will have the value 3000.

         The value of tmnxOamSysPerfCfgTotalTx will not exceed the value of
         tmnxOamSysPerfCfgLimitTx."
    ::= { tmnxOamGeneralStats 3 }

tmnxOamSysPerfLastClearedTime    OBJECT-TYPE
    SYNTAX      TimeStamp
    MAX-ACCESS  read-only
    STATUS      current
    DESCRIPTION
        "The value of tmnxOamSysPerfLastClearedTime indicates the sysUpTime when
         the following statistics were cleared:  tmnxOamSysPerfLocalTestTx,
         tmnxOamSysPerfRemoteTestRx, and tmnxOamSysPerfReqTypeTable.  If the
         statistics have not been cleared since the last CPM restart, zero is
         returned.

         A packet count which is time stamped by this object can be converted to
         an average packets per second value using, for example,
           pps = tmnxOamSysPerfLocalTestTx /
                 [(sysUpTime - tmnxOamSysPerfLastClearedTime)/100]."
    ::= { tmnxOamGeneralStats 4 }

tmnxOamSysPerfLocalTestTx        OBJECT-TYPE
    SYNTAX      Counter32
    UNITS       "echo request packets"
    MAX-ACCESS  read-only
    STATUS      current
    DESCRIPTION
        "The value of tmnxOamSysPerfLocalTestTx indicates this node's total
         number of echo request packets transmitted by locally initiated tests
         (since the last clear).  The test types are listed in the
         tmnxOamSysPerfOprLimitTx DESCRIPTION clause."
    ::= { tmnxOamGeneralStats 5 }

tmnxOamSysPerfRemoteTestRx       OBJECT-TYPE
    SYNTAX      Counter32
    UNITS       "echo request packets"
    MAX-ACCESS  read-only
    STATUS      current
    DESCRIPTION
        "The value of tmnxOamSysPerfRemoteTestRx indicates this node's total
         number of echo request packets received from remotely initiated tests
         (since the last clear)."
    ::= { tmnxOamGeneralStats 6 }

tmnxOamSysPerfReqTypeTable       OBJECT-TYPE
    SYNTAX      SEQUENCE OF TmnxOamSysPerfReqTypeEntry
    MAX-ACCESS  not-accessible
    STATUS      current
    DESCRIPTION
        "tmnxOamSysPerfReqTypeTable has a row for each relevant OAM echo request
         packet type.  Each row contains packet counters."
    ::= { tmnxOamGeneralStats 7 }

tmnxOamSysPerfReqTypeEntry       OBJECT-TYPE
    SYNTAX      TmnxOamSysPerfReqTypeEntry
    MAX-ACCESS  not-accessible
    STATUS      current
    DESCRIPTION
        "Rows in tmnxOamSysPerfReqTypeTable are system-generated at CPM
         restart. Rows cannot be created or destroyed using SNMP."
    INDEX       { IMPLIED tmnxOamSysPerfReqTypeName }
    ::= { tmnxOamSysPerfReqTypeTable 1 }

TmnxOamSysPerfReqTypeEntry       ::= SEQUENCE
{
    tmnxOamSysPerfReqTypeName        TNamedItem,
    tmnxOamSysPerfReqTypeLocalTestTx Counter32,
    tmnxOamSysPerfReqTypeRemoteTstRx Counter32
}

tmnxOamSysPerfReqTypeName        OBJECT-TYPE
    SYNTAX      TNamedItem
    MAX-ACCESS  not-accessible
    STATUS      current
    DESCRIPTION
        "The value of tmnxOamSysPerfReqTypeName specifies the name of an echo
         request packet type (e.g. 'ICMP').  The name is the index for the row."
    ::= { tmnxOamSysPerfReqTypeEntry 1 }

tmnxOamSysPerfReqTypeLocalTestTx OBJECT-TYPE
    SYNTAX      Counter32
    UNITS       "echo request packets"
    MAX-ACCESS  read-only
    STATUS      current
    DESCRIPTION
        "The value of tmnxOamSysPerfReqTypeLocalTestTx indicates the number of
         echo request packets transmitted by locally initiated tests (since the
         last clear) for the echo request packet type specified by
         tmnxOamSysPerfReqTypeName."
    ::= { tmnxOamSysPerfReqTypeEntry 2 }

tmnxOamSysPerfReqTypeRemoteTstRx OBJECT-TYPE
    SYNTAX      Counter32
    UNITS       "echo request packets"
    MAX-ACCESS  read-only
    STATUS      current
    DESCRIPTION
        "The value of tmnxOamSysPerfReqTypeRemoteTstRx indicates the number of
         echo request packets received from remotely initiated tests (since the
         last clear) for the echo request packet type specified by
         tmnxOamSysPerfReqTypeName."
    ::= { tmnxOamSysPerfReqTypeEntry 3 }

tmnxOamSysSessionLimit           OBJECT-TYPE
    SYNTAX      Gauge32
    UNITS       "sessions"
    MAX-ACCESS  read-only
    STATUS      current
    DESCRIPTION
        "The value of tmnxOamSysSessionLimit indicates the maximum number of
         sessions in the OAM general session pool.

         OAM general session pool sessions are allocated and freed as described
         in the tmnxOamSysSessionCount DESCRIPTION clause."
    ::= { tmnxOamGeneralStats 8 }

tmnxOamSysSessionCount           OBJECT-TYPE
    SYNTAX      Gauge32
    UNITS       "sessions"
    MAX-ACCESS  read-only
    STATUS      current
    DESCRIPTION
        "The value of tmnxOamSysSessionCount indicates the number of currently
         allocated sessions in the OAM general session pool.

         A test with one of the following test types allocates a session from
         the OAM general session pool:
         1.  Filter redirect policy ping test.
         2.  SDP keep-alive.
         3.  Static route CPE check.
         4.  VRRP policy host unreachable ping test.
         5.  Any OAM or SAA test configured using TIMETRA-OAM-TEST-MIB.
         6.  Any test configured using TIMETRA-OAM-PM-MIB.
         7.  Background ICMP Bridged Residential Gateway ping test.

         A session is allocated from the OAM general session pool when a test
         is configured (in the case of some test types) or activated (in the
         remaining cases).

         The session is freed when the test is deactivated or deleted.

         tmnxOamSysSessionCount will not exceed tmnxOamSysSessionLimit.

         Configuration or activation of a test (with a test type listed above)
         will fail when tmnxOamSysSessionCount equals tmnxOamSysSessionLimit."
    ::= { tmnxOamGeneralStats 9 }

tmnxOamSysBgIcmpBrgSessionLimit  OBJECT-TYPE
    SYNTAX      Gauge32
    UNITS       "sessions"
    MAX-ACCESS  read-only
    STATUS      current
    DESCRIPTION
        "The value of tmnxOamSysBgIcmpBrgSessionLimit indicates the maximum
         number of background ICMP Bridged Residential Gateway (BRG) OAM test
         sessions available on this node.

         Sessions are allocated and freed as described in the
         tmnxOamSysBgIcmpBrgSessionCount DESCRIPTION clause.

         tmnxOamSysSessionLimit is the limit for the other OAM session pool."
    ::= { tmnxOamGeneralStats 10 }

tmnxOamSysBgIcmpBrgSessionCount  OBJECT-TYPE
    SYNTAX      Gauge32
    UNITS       "sessions"
    MAX-ACCESS  read-only
    STATUS      current
    DESCRIPTION
        "The value of tmnxOamSysBgIcmpBrgSessionCount indicates the number of
         background ICMP Bridged Residential Gateway (BRG) OAM test sessions
         currently allocated on this node.

         One session is allocated when BRG functionality is administratively
         enabled on a group interface (using TIMETRA-SUBSCRIBER-MGMT-MIB::
         tmnxSubBrgIfAdminState).

         The session is freed when the BRG functionality is administratively
         disabled.

         tmnxOamSysBgIcmpBrgSessionCount will not exceed
         tmnxOamSysBgIcmpBrgSessionLimit.

         Creating a background ICMP BRG OAM test session will fail when
         tmnxOamSysBgIcmpBrgSessionCount equals
         tmnxOamSysBgIcmpBrgSessionLimit.

         tmnxOamSysSessionCount counts the sessions in the other OAM session
         pool."
    ::= { tmnxOamGeneralStats 11 }

tmnxOamMplsEchoDownstreamMapTlv  OBJECT-TYPE
    SYNTAX      TmnxOamMplsEchoDownMapTlv
    MAX-ACCESS  read-write
    STATUS      current
    DESCRIPTION
        "The value of tmnxOamMplsEchoDownstreamMapTlv specifies the system
         value for the type of downstream map TLV to be inserted when launching
         MPLS echo requests.

         The value of tmnxOamMplsEchoDownstreamMapTlv is used on three
         occasions:

         1.  When a background LDP tree trace test is started (using
         tmnxOamLTtraceAutoAdminState), the value of
         tmnxOamMplsEchoDownstreamMapTlv specifies the type of downstream map
         TLV used during the test.

         2.  When a test of type 'lspTraceRoute' is created, with no value
         specified for the test's tmnxOamLspTrCtlDownstreamMapTlv object,
         tmnxOamLspTrCtlDownstreamMapTlv is set to the value of
         tmnxOamMplsEchoDownstreamMapTlv.

         3.  When a test of type 'ldpTreeTrace' is created, with no value
         specified for the test's tmnxOamLTtraceCtlDownstreamMpTlv object,
         tmnxOamLTtraceCtlDownstreamMpTlv is set to the value of
         tmnxOamMplsEchoDownstreamMapTlv.

         Example usage, for the second and third cases:  suppose every node in
         this node's network supports the MPLS Echo Request/Reply DDMAP TLV, and
         the network operator wishes to use the enhanced functionality offered
         by the DDMAP TLV.  Then, setting tmnxOamMplsEchoDownstreamMapTlv to
         'ddmap(2)' simplifies configuration.  The simplification:  the
         tmnxOamLspTrCtlDownstreamMapTlv and tmnxOamLTtraceCtlDownstreamMpTlv
         objects need not be set when creating tests."
    DEFVAL      { dsmap }
    ::= { tmnxOamGeneralObjs 3 }

tmnxOamTestConformance           OBJECT IDENTIFIER ::= { tmnxSRConfs 11 }

tmnxOamPingConformance           OBJECT IDENTIFIER ::= { tmnxOamTestConformance 1 }

tmnxOamPingCompliances           OBJECT IDENTIFIER ::= { tmnxOamPingConformance 1 }

tmnxOamPing7450V4v0Compliance    MODULE-COMPLIANCE
    STATUS      obsolete
    DESCRIPTION
        "The compliance statement for management of OAM ping tests on Nokia
         7450 ESS series systems release 4.0."
    MODULE
        MANDATORY-GROUPS {
            tmnxOamPingGeneralV4v0Group,
            tmnxOamMacPingV4v0Group,
            tmnxOamLspPingV4v0Group,
            tmnxOamMfibPingV4v0Group,
            tmnxOamCpePingV4v0Group,
            tmnxOamVccvPingGroup,
            tmnxOamIcmpPingGroup,
            tmnxOamPingNotificationV4v0Group
        }
    ::= { tmnxOamPingCompliances 4 }

tmnxOamPing7750V4v0Compliance    MODULE-COMPLIANCE
    STATUS      obsolete
    DESCRIPTION
        "The compliance statement for management of OAM ping tests on Nokia
         SROS series systems release 4.0."
    MODULE
        MANDATORY-GROUPS {
            tmnxOamPingGeneralV4v0Group,
            tmnxOamMacPingV4v0Group,
            tmnxOamLspPingV4v0Group,
            tmnxOamVprnPingV4v0Group,
            tmnxOamMfibPingV4v0Group,
            tmnxOamCpePingV4v0Group,
            tmnxOamMRInfoV4v0Group,
            tmnxOamAtmPingR2r1Group,
            tmnxOamVccvPingGroup,
            tmnxOamIcmpPingGroup,
            tmnxOamPingNotificationV4v0Group
        }
    ::= { tmnxOamPingCompliances 5 }

tmnxOamPing7450V5v0Compliance    MODULE-COMPLIANCE
    STATUS      obsolete
    DESCRIPTION
        "The compliance statement for management of OAM ping tests on Nokia
         7450 ESS series systems release 5.0."
    MODULE
        MANDATORY-GROUPS {
            tmnxOamPingGeneralV4v0Group,
            tmnxOamMacPingV4v0Group,
            tmnxOamLspPingV5v0Group,
            tmnxOamMfibPingV4v0Group,
            tmnxOamCpePingV4v0Group,
            tmnxOamVccvPingV5v0Group,
            tmnxOamIcmpPingGroup,
            tmnxOamAncpTestV5v0Group,
            tmnxOamPingNotificationV5v0Group
        }
    ::= { tmnxOamPingCompliances 6 }

tmnxOamPing7750V5v0Compliance    MODULE-COMPLIANCE
    STATUS      obsolete
    DESCRIPTION
        "The compliance statement for management of OAM ping tests on Nokia
         SROS series systems release 5.0."
    MODULE
        MANDATORY-GROUPS {
            tmnxOamPingGeneralV4v0Group,
            tmnxOamMacPingV4v0Group,
            tmnxOamLspPingV5v0Group,
            tmnxOamVprnPingV4v0Group,
            tmnxOamMfibPingV4v0Group,
            tmnxOamCpePingV4v0Group,
            tmnxOamMRInfoV4v0Group,
            tmnxOamAtmPingR2r1Group,
            tmnxOamVccvPingV5v0Group,
            tmnxOamIcmpPingGroup,
            tmnxOamAncpTestV5v0Group,
            tmnxOamPingNotificationV5v0Group
        }
    ::= { tmnxOamPingCompliances 7 }

tmnxOamPing7450V6v0Compliance    MODULE-COMPLIANCE
    STATUS      obsolete
    DESCRIPTION
        "The compliance statement for management of OAM ping tests on Nokia
         7450 ESS series systems release 6.0."
    MODULE
        MANDATORY-GROUPS {
            tmnxOamPingGeneralV6v0Group,
            tmnxOamMacPingV4v0Group,
            tmnxOamLspPingV6v0Group,
            tmnxOamMfibPingV6v0Group,
            tmnxOamCpePingV4v0Group,
            tmnxOamVccvPingV5v0Group,
            tmnxOamIcmpPingGroup,
            tmnxOamAncpTestV5v0Group,
            tmnxOamPingNotificationV5v0Group
        }
    ::= { tmnxOamPingCompliances 8 }

tmnxOamPing7750V6v0Compliance    MODULE-COMPLIANCE
    STATUS      obsolete
    DESCRIPTION
        "The compliance statement for management of OAM ping tests on Nokia
         SROS series systems release 6.0."
    MODULE
        MANDATORY-GROUPS {
            tmnxOamPingGeneralV6v0Group,
            tmnxOamMacPingV4v0Group,
            tmnxOamLspPingV6v0Group,
            tmnxOamVprnPingV4v0Group,
            tmnxOamMfibPingV6v0Group,
            tmnxOamCpePingV4v0Group,
            tmnxOamMRInfoV4v0Group,
            tmnxOamAtmPingR2r1Group,
            tmnxOamVccvPingV5v0Group,
            tmnxOamIcmpPingGroup,
            tmnxOamAncpTestV5v0Group,
            tmnxOamPingNotificationV5v0Group
        }
    ::= { tmnxOamPingCompliances 9 }

tmnxOamPing7450V7v0Compliance    MODULE-COMPLIANCE
    STATUS      obsolete
    DESCRIPTION
        "The compliance statement for management of OAM ping tests on Nokia
         7450 ESS series systems release 7.0."
    MODULE
        MANDATORY-GROUPS {
            tmnxOamPingGeneralV7v0Group,
            tmnxOamMacPingV4v0Group,
            tmnxOamLspPingV6v0Group,
            tmnxOamMfibPingV6v0Group,
            tmnxOamCpePingV4v0Group,
            tmnxOamVccvPingV5v0Group,
            tmnxOamIcmpPingGroup,
            tmnxOamAncpTestV5v0Group,
            tmnxOamPingNotificationV7v0Group
        }
    ::= { tmnxOamPingCompliances 10 }

tmnxOamPing7750V7v0Compliance    MODULE-COMPLIANCE
    STATUS      obsolete
    DESCRIPTION
        "The compliance statement for management of OAM ping tests on Nokia
         7750 and 7710 SR series systems release 7.0."
    MODULE
        MANDATORY-GROUPS {
            tmnxOamPingGeneralV7v0Group,
            tmnxOamMacPingV4v0Group,
            tmnxOamLspPingV6v0Group,
            tmnxOamVprnPingV4v0Group,
            tmnxOamMfibPingV6v0Group,
            tmnxOamCpePingV4v0Group,
            tmnxOamMRInfoV4v0Group,
            tmnxOamAtmPingR2r1Group,
            tmnxOamVccvPingV5v0Group,
            tmnxOamIcmpPingGroup,
            tmnxOamAncpTestV5v0Group,
            tmnxOamPingNotificationV7v0Group,
            tmnxOamP2mpLspPingGroup
        }
    ::= { tmnxOamPingCompliances 11 }

tmnxOamPing7450V8v0Compliance    MODULE-COMPLIANCE
    STATUS      obsolete
    DESCRIPTION
        "The compliance statement for management of OAM ping tests on Nokia
         7450 ESS series systems release 8.0."
    MODULE
        MANDATORY-GROUPS {
            tmnxOamPingGeneralV8v0Group,
            tmnxOamMacPingV4v0Group,
            tmnxOamLspPingV6v0Group,
            tmnxOamMfibPingV6v0Group,
            tmnxOamCpePingV4v0Group,
            tmnxOamVccvPingV5v0Group,
            tmnxOamIcmpPingGroup,
            tmnxOamAncpTestV5v0Group,
            tmnxOamEthCfmPingV8v0Group,
            tmnxOamPingNotificationV7v0Group
        }
    ::= { tmnxOamPingCompliances 12 }

tmnxOamPing77x0V8v0Compliance    MODULE-COMPLIANCE
    STATUS      obsolete
    DESCRIPTION
        "The compliance statement for management of OAM ping tests on Nokia
         7750 and 7710 SR series systems release 8.0."
    MODULE
        MANDATORY-GROUPS {
            tmnxOamPingGeneralV8v0Group,
            tmnxOamMacPingV4v0Group,
            tmnxOamLspPingV6v0Group,
            tmnxOamVprnPingV4v0Group,
            tmnxOamMfibPingV6v0Group,
            tmnxOamCpePingV4v0Group,
            tmnxOamMRInfoV4v0Group,
            tmnxOamAtmPingR2r1Group,
            tmnxOamVccvPingV5v0Group,
            tmnxOamIcmpPingGroup,
            tmnxOamAncpTestV5v0Group,
            tmnxOamEthCfmPingV8v0Group,
            tmnxOamPingNotificationV7v0Group,
            tmnxOamP2mpLspPingGroup,
            tmnxOamP2mpLspPingV8v0Group
        }
    ::= { tmnxOamPingCompliances 13 }

tmnxOamPing7xx0V9v0Compliance    MODULE-COMPLIANCE
    STATUS      obsolete
    DESCRIPTION
        "The compliance statement for management of OAM ping tests on Nokia
         SROS series systems, release 9.0."
    MODULE
        MANDATORY-GROUPS {
            tmnxOamPingGeneralV8v0Group,
            tmnxOamMacPingV4v0Group,
            tmnxOamLspPingV6v0Group,
            tmnxOamVprnPingV4v0Group,
            tmnxOamMfibPingV6v0Group,
            tmnxOamCpePingV4v0Group,
            tmnxOamMRInfoV4v0Group,
            tmnxOamAtmPingR2r1Group,
            tmnxOamVccvPingV5v0Group,
            tmnxOamIcmpPingGroup,
            tmnxOamAncpTestV5v0Group,
            tmnxOamEthCfmPingV8v0Group,
            tmnxOamPingNotificationV7v0Group,
            tmnxOamP2mpLspPingGroup,
            tmnxOamP2mpLspPingV8v0Group,
            tmnxOamVccvPingV9v0Group
        }
    ::= { tmnxOamPingCompliances 14 }

tmnxOamPing7xx0V10v0Compliance   MODULE-COMPLIANCE
    STATUS      obsolete
    DESCRIPTION
        "The compliance statement for management of OAM ping tests on Nokia
         SROS series systems, release 10.0."
    MODULE
        MANDATORY-GROUPS {
            tmnxOamPingGeneralV10v0Group,
            tmnxOamMacPingV4v0Group,
            tmnxOamLspPingV6v0Group,
            tmnxOamVprnPingV4v0Group,
            tmnxOamMfibPingV6v0Group,
            tmnxOamCpePingV4v0Group,
            tmnxOamMRInfoV4v0Group,
            tmnxOamAtmPingR2r1Group,
            tmnxOamVccvPingV5v0Group,
            tmnxOamIcmpPingGroup,
            tmnxOamAncpTestV5v0Group,
            tmnxOamEthCfmPingV8v0Group,
            tmnxOamPingNotificationV7v0Group,
            tmnxOamP2mpLspPingGroup,
            tmnxOamP2mpLspPingV8v0Group,
            tmnxOamVccvPingV9v0Group,
            tmnxOamPingCtlV10v0Group,
            tmnxOamMobilePingGroup,
            tmnxOamP2mpLspPingV10v0Group
        }
    ::= { tmnxOamPingCompliances 15 }

tmnxOamPing7xx0V11v0Compliance   MODULE-COMPLIANCE
    STATUS      obsolete
    DESCRIPTION
        "The compliance statement for management of OAM ping tests on Nokia
         SROS series systems, release 11.0."
    MODULE
        MANDATORY-GROUPS {
            tmnxOamAncpTestV5v0Group,
            tmnxOamAtmPingR2r1Group,
            tmnxOamCpePingV4v0Group,
            tmnxOamEthCfmPingV8v0Group,
            tmnxOamIcmpPingGroup,
            tmnxOamLspPingV11v0Group,
            tmnxOamMRInfoV4v0Group,
            tmnxOamMacPingCtlV11v0Group,
            tmnxOamMacPingHistoryV11v0Group,
            tmnxOamMfibPingV6v0Group,
            tmnxOamMobilePingGroup,
            tmnxOamP2mpLspPingGroup,
            tmnxOamP2mpLspPingV10v0Group,
            tmnxOamP2mpLspPingV8v0Group,
            tmnxOamPingCtlV10v0Group,
            tmnxOamPingGeneralV10v0Group,
            tmnxOamPingNotificationV7v0Group,
            tmnxOamPingV11v0Group,
            tmnxOamVccvPingV5v0Group,
            tmnxOamVccvPingV9v0Group,
            tmnxOamVccvPingV11v0Group,
            tmnxOamVprnPingV4v0Group
        }
    ::= { tmnxOamPingCompliances 16 }

tmnxOamPing7xx0V12v0Compliance   MODULE-COMPLIANCE
    STATUS      current
    DESCRIPTION
        "The compliance statement for management of OAM ping tests on Nokia
         SROS series systems, release 12.0."
    MODULE
        MANDATORY-GROUPS {
            tmnxOamAncpTestV5v0Group,
            tmnxOamAtmPingR2r1Group,
            tmnxOamCpePingV4v0Group,
            tmnxOamEthCfmPingV8v0Group,
            tmnxOamIcmpPingGroup,
            tmnxOamLspPingV11v0Group,
            tmnxOamMRInfoV4v0Group,
            tmnxOamMacPingCtlV11v0Group,
            tmnxOamMacPingHistoryV11v0Group,
            tmnxOamMfibPingV6v0Group,
            tmnxOamMobilePingGroup,
            tmnxOamP2mpLspPingGroup,
            tmnxOamP2mpLspPingV8v0Group,
            tmnxOamP2mpLspPingV10v0Group,
            tmnxOamPingCtlV10v0Group,
            tmnxOamPingGeneralV10v0Group,
            tmnxOamPingNotificationV7v0Group,
            tmnxOamPingV11v0Group,
            tmnxOamPingV12v0Group,
            tmnxOamVccvPingV5v0Group,
            tmnxOamVccvPingV9v0Group,
            tmnxOamVccvPingV11v0Group,
            tmnxOamVprnPingV4v0Group
        }
    ::= { tmnxOamPingCompliances 17 }

tmnxOamPing7xx0V13v0Compliance   MODULE-COMPLIANCE
    STATUS      current
    DESCRIPTION
        "The compliance statement for OAM ping OBJECT-GROUPs added in Nokia
         SROS series systems, release 13.0."
    MODULE
        MANDATORY-GROUPS {
            tmnxOamPingV13v0Group
        }
    ::= { tmnxOamPingCompliances 18 }

tmnxOamPing7xx0V14v0Compliance   MODULE-COMPLIANCE
    STATUS      current
    DESCRIPTION
        "The compliance statement for OAM ping OBJECT-GROUPs added in Nokia
         SROS series systems, release 14.0."
    MODULE
        MANDATORY-GROUPS {
            tmnxOamPingV14v0Group
        }
    ::= { tmnxOamPingCompliances 19 }

tmnxOamPing7xx0V15v0Compliance   MODULE-COMPLIANCE
    STATUS      current
    DESCRIPTION
        "The compliance statement for OAM ping OBJECT-GROUPs added in Nokia
         SROS series systems, release 15.0."
    MODULE
        MANDATORY-GROUPS {
            tmnxOamPingV15v0Group
        }
    ::= { tmnxOamPingCompliances 20 }

tmnxOamPingGroups                OBJECT IDENTIFIER ::= { tmnxOamPingConformance 2 }

tmnxOamMacPingL2MapGroup         OBJECT-GROUP
    OBJECTS     {
        tmnxOamMacPingL2MapRouterID,
        tmnxOamMacPingL2MapLabel,
        tmnxOamMacPingL2MapProtocol,
        tmnxOamMacPingL2MapVCType,
        tmnxOamMacPingL2MapVCID,
        tmnxOamMacPingL2MapDirection
    }
    STATUS      obsolete
    DESCRIPTION
        "The group of optional objects to report OAM Mac Ping layer-2 mapping
         information returned in response to OAM Mac Ping tests on Nokia SROS
         series systems."
    ::= { tmnxOamPingGroups 3 }

tmnxOamAtmPingR2r1Group          OBJECT-GROUP
    OBJECTS     {
        tmnxOamAtmPingCtlPortId,
        tmnxOamAtmPingCtlVpi,
        tmnxOamAtmPingCtlVci,
        tmnxOamAtmPingCtlLpbkLocation,
        tmnxOamAtmPingCtlSegment
    }
    STATUS      current
    DESCRIPTION
        "The group of objects supporting management of OAM ATM Ping tests on
         Nokia SROS series systems."
    ::= { tmnxOamPingGroups 8 }

tmnxOamMacPingV4v0Group          OBJECT-GROUP
    OBJECTS     {
        tmnxOamMacPingCtlTargetMacAddr,
        tmnxOamMacPingCtlSourceMacAddr,
        tmnxOamMacPingCtlSendControl,
        tmnxOamMacPingCtlReplyControl,
        tmnxOamMacPingCtlTtl,
        tmnxOamMacPingCtlRegister,
        tmnxOamMacPingCtlFlood,
        tmnxOamMacPingCtlForce,
        tmnxOamMacPingCtlAge,
        tmnxOamMacPingCtlSapPortId,
        tmnxOamMacPingCtlSapEncapValue,
        tmnxOamMacPingCtlFibEntryName,
        tmnxOamMacPingHistoryResponse,
        tmnxOamMacPingHistoryOneWayTime,
        tmnxOamMacPingHistoryStatus,
        tmnxOamMacPingHistoryTime,
        tmnxOamMacPingHistoryReturnCode,
        tmnxOamMacPingHistoryAddressType,
        tmnxOamMacPingHistorySapId,
        tmnxOamMacPingHistorySdpId,
        tmnxOamMacPingHistoryAdminStatus,
        tmnxOamMacPingHistoryOperStatus,
        tmnxOamMacPingHistoryResponsePlane,
        tmnxOamMacPingHistorySize,
        tmnxOamMacPingHistoryInOneWayTime,
        tmnxOamMacPingHistorySrcAddrType,
        tmnxOamMacPingHistorySrcAddress
    }
    STATUS      obsolete
    DESCRIPTION
        "The group of objects supporting management of OAM Mac Ping tests on
         Nokia SROS series systems release 4.0."
    ::= { tmnxOamPingGroups 14 }

tmnxOamVccvPingGroup             OBJECT-GROUP
    OBJECTS     {
        tmnxOamVccvPingCtlSdpIdVcId,
        tmnxOamVccvPingCtlReplyMode
    }
    STATUS      obsolete
    DESCRIPTION
        "The group of objects supporting management of OAM VCCV Ping tests on
         Nokia SROS series systems."
    ::= { tmnxOamPingGroups 15 }

tmnxOamPingGeneralV4v0Group      OBJECT-GROUP
    OBJECTS     {
        tmnxOamPingMaxConcurrentTests,
        tmnxOamPingCtlRowStatus,
        tmnxOamPingCtlStorageType,
        tmnxOamPingCtlDescr,
        tmnxOamPingCtlTestMode,
        tmnxOamPingCtlAdminStatus,
        tmnxOamPingCtlOrigSdpId,
        tmnxOamPingCtlRespSdpId,
        tmnxOamPingCtlFcName,
        tmnxOamPingCtlProfile,
        tmnxOamPingCtlMtuStartSize,
        tmnxOamPingCtlMtuEndSize,
        tmnxOamPingCtlMtuStepSize,
        tmnxOamPingCtlServiceId,
        tmnxOamPingCtlLocalSdp,
        tmnxOamPingCtlRemoteSdp,
        tmnxOamPingCtlSize,
        tmnxOamPingCtlTimeOut,
        tmnxOamPingCtlProbeCount,
        tmnxOamPingCtlInterval,
        tmnxOamPingCtlMaxRows,
        tmnxOamPingCtlTrapGeneration,
        tmnxOamPingCtlTrapProbeFailureFilter,
        tmnxOamPingCtlTrapTestFailureFilter,
        tmnxOamPingCtlSAA,
        tmnxOamPingCtlRuns,
        tmnxOamPingCtlFailures,
        tmnxOamPingCtlLastRunResult,
        tmnxOamPingCtlLastChanged,
        tmnxOamPingCtlVRtrID,
        tmnxOamPingCtlTgtAddrType,
        tmnxOamPingCtlTgtAddress,
        tmnxOamPingCtlSrcAddrType,
        tmnxOamPingCtlSrcAddress,
        tmnxOamPingCtlDnsName,
        tmnxOamPingResultsOperStatus,
        tmnxOamPingResultsMinRtt,
        tmnxOamPingResultsMaxRtt,
        tmnxOamPingResultsAverageRtt,
        tmnxOamPingResultsRttSumOfSquares,
        tmnxOamPingResultsMtuResponseSize,
        tmnxOamPingResultsSvcPing,
        tmnxOamPingResultsProbeResponses,
        tmnxOamPingResultsSentProbes,
        tmnxOamPingResultsLastGoodProbe,
        tmnxOamPingResultsLastRespHeader,
        tmnxOamPingResultsMinTt,
        tmnxOamPingResultsMaxTt,
        tmnxOamPingResultsAverageTt,
        tmnxOamPingResultsTtSumOfSquares,
        tmnxOamPingResultsMinInTt,
        tmnxOamPingResultsMaxInTt,
        tmnxOamPingResultsAverageInTt,
        tmnxOamPingResultsInTtSumOfSqrs,
        tmnxOamPingResultsOutJitter,
        tmnxOamPingResultsInJitter,
        tmnxOamPingResultsRtJitter,
        tmnxOamPingResultsProbeTimeouts,
        tmnxOamPingResultsProbeFailures,
        tmnxOamPingHistoryResponse,
        tmnxOamPingHistoryOneWayTime,
        tmnxOamPingHistorySize,
        tmnxOamPingHistoryStatus,
        tmnxOamPingHistoryTime,
        tmnxOamPingHistoryReturnCode,
        tmnxOamPingHistAddressType,
        tmnxOamPingHistoryVersion,
        tmnxOamPingHistSapId,
        tmnxOamPingHistoryCpeMacAddr,
        tmnxOamPingHistoryRespSvcId,
        tmnxOamPingHistorySequence,
        tmnxOamPingHistoryIfIndex,
        tmnxOamPingHistoryDataLen,
        tmnxOamPingHistoryRespPlane,
        tmnxOamPingHistoryReqHdr,
        tmnxOamPingHistoryRespHdr,
        tmnxOamPingHistoryDnsAddrType,
        tmnxOamPingHistoryDnsAddress,
        tmnxOamPingHistorySrcAddrType,
        tmnxOamPingHistorySrcAddress,
        tmnxOamPingHistoryInOneWayTime
    }
    STATUS      obsolete
    DESCRIPTION
        "The group of objects supporting management of OAM ping tests general
         capabilities on Nokia SROS series systems 4.0 release"
    ::= { tmnxOamPingGroups 16 }

tmnxOamLspPingV4v0Group          OBJECT-GROUP
    OBJECTS     {
        tmnxOamLspPingCtlVRtrID,
        tmnxOamLspPingCtlLspName,
        tmnxOamLspPingCtlReturnLsp,
        tmnxOamLspPingCtlTtl,
        tmnxOamLspPingCtlPathName,
        tmnxOamLspPingCtlLdpPrefixType,
        tmnxOamLspPingCtlLdpPrefix,
        tmnxOamLspPingCtlLdpPrefixLen
    }
    STATUS      obsolete
    DESCRIPTION
        "The group of objects supporting management of OAM LSP Ping tests on
         Nokia SROS series systems 4.0 release."
    ::= { tmnxOamPingGroups 17 }

tmnxOamVprnPingV4v0Group         OBJECT-GROUP
    OBJECTS     {
        tmnxOamVprnPingCtlReplyControl,
        tmnxOamVprnPingCtlTtl,
        tmnxOamVprnPingCtlSrcAddrType,
        tmnxOamVprnPingCtlSrcAddress
    }
    STATUS      current
    DESCRIPTION
        "The group of objects supporting management of OAM VPRN Ping tests on
         Nokia SROS series systems 4.0 release."
    ::= { tmnxOamPingGroups 19 }

tmnxOamMfibPingV4v0Group         OBJECT-GROUP
    OBJECTS     {
        tmnxOamMfibPingCtlReplyControl,
        tmnxOamMfibPingCtlTtl,
        tmnxOamMfibPingCtlSrcAddrType,
        tmnxOamMfibPingCtlSrcAddress,
        tmnxOamMfibPingCtlDestAddrType,
        tmnxOamMfibPingCtlDestAddress,
        tmnxOamPingHistoryRespSvcId
    }
    STATUS      obsolete
    DESCRIPTION
        "The group of objects supporting management of OAM MFIB Ping tests on
         Nokia SROS series systems release 4.0."
    ::= { tmnxOamPingGroups 20 }

tmnxOamCpePingV4v0Group          OBJECT-GROUP
    OBJECTS     {
        tmnxOamCpePingCtlSendControl,
        tmnxOamCpePingCtlReplyControl,
        tmnxOamCpePingCtlTtl,
        tmnxOamCpePingCtlSrceMacAddr,
        tmnxOamCpePingCtlSrcAddrType,
        tmnxOamCpePingCtlSrcAddress,
        tmnxOamPingHistoryCpeMacAddr
    }
    STATUS      current
    DESCRIPTION
        "The group of objects supporting management of OAM CPE Ping tests on
         Nokia SROS series systems release 4.0."
    ::= { tmnxOamPingGroups 21 }

tmnxOamMRInfoV4v0Group           OBJECT-GROUP
    OBJECTS     {
        tmnxOamMRInfoRespCapabilities,
        tmnxOamMRInfoRespMinorVersion,
        tmnxOamMRInfoRespMajorVersion,
        tmnxOamMRInfoRespNumInterfaces,
        tmnxOamMRInfoRespIfMetric,
        tmnxOamMRInfoRespIfThreshold,
        tmnxOamMRInfoRespIfFlags,
        tmnxOamMRInfoRespIfNbrCount,
        tmnxOamMRInfoRespIfAddrType,
        tmnxOamMRInfoRespIfAddr,
        tmnxOamMRInfoRespIfNbrAddrType,
        tmnxOamMRInfoRespIfNbrAddr
    }
    STATUS      current
    DESCRIPTION
        "The group of objects supporting management of OAM Multicast Router
         Information (mrinfo) tests on Nokia SROS series systems release 4.0."
    ::= { tmnxOamPingGroups 22 }

tmnxOamIcmpPingGroup             OBJECT-GROUP
    OBJECTS     {
        tmnxOamIcmpPingCtlRapid,
        tmnxOamIcmpPingCtlTtl,
        tmnxOamIcmpPingCtlDSField,
        tmnxOamIcmpPingCtlPattern,
        tmnxOamIcmpPingCtlNhAddrType,
        tmnxOamIcmpPingCtlNhAddress,
        tmnxOamIcmpPingCtlEgrIfIndex,
        tmnxOamIcmpPingCtlEgrIfName,
        tmnxOamIcmpPingCtlBypassRouting,
        tmnxOamIcmpPingCtlDoNotFragment
    }
    STATUS      current
    DESCRIPTION
        "The group of objects supporting management of OAM ICMP Ping tests on
         Nokia SROS series systems."
    ::= { tmnxOamPingGroups 23 }

tmnxOamPingObsoleteV4v0Group     OBJECT-GROUP
    OBJECTS     {
        tmnxOamPingCtlTargetIpAddress,
        tmnxOamPingHistorySrcIpAddress,
        tmnxOamMacPingHistorySrcIpAddress,
        tmnxOamLspPingCtlLdpIpPrefix,
        tmnxOamLspPingCtlLdpIpPrefixLen,
        tmnxOamVprnPingCtlSourceIpAddr,
        tmnxOamMfibPingCtlSourceIpAddr,
        tmnxOamMfibPingCtlDestIpAddr,
        tmnxOamCpePingCtlSourceIpAddr,
        tmnxOamMRInfoRespIfAddress,
        tmnxOamMRInfoRespIfNbrAddress
    }
    STATUS      current
    DESCRIPTION
        "The group of objects supporting management of OAM ICMP Ping tests on
         Nokia SROS series systems that were made obsolete in release 4.0."
    ::= { tmnxOamPingGroups 24 }

tmnxOamPingNotificationV4v0Group NOTIFICATION-GROUP
    NOTIFICATIONS {
        tmnxOamPingProbeFailedV2,
        tmnxOamPingTestFailedV2,
        tmnxOamPingTestCompletedV2
    }
    STATUS      obsolete
    DESCRIPTION
        "The group of notifications supporting the OAM ping feature on Nokia
         SROS series systems release 4.0."
    ::= { tmnxOamPingGroups 25 }

tmnxOamPingNotificationObsoleteV4v0Group NOTIFICATION-GROUP
    NOTIFICATIONS {
        tmnxOamPingProbeFailed,
        tmnxOamPingTestFailed,
        tmnxOamPingTestCompleted
    }
    STATUS      current
    DESCRIPTION
        "The group of notifications supporting the OAM ping feature on Nokia
         SROS series systems release 4.0."
    ::= { tmnxOamPingGroups 26 }

tmnxOamLspPingV5v0Group          OBJECT-GROUP
    OBJECTS     {
        tmnxOamLspPingCtlVRtrID,
        tmnxOamLspPingCtlLspName,
        tmnxOamLspPingCtlReturnLsp,
        tmnxOamLspPingCtlTtl,
        tmnxOamLspPingCtlPathName,
        tmnxOamLspPingCtlLdpPrefixType,
        tmnxOamLspPingCtlLdpPrefix,
        tmnxOamLspPingCtlLdpPrefixLen,
        tmnxOamLspPingCtlPathDestType,
        tmnxOamLspPingCtlPathDest,
        tmnxOamLspPingCtlNhIntfName,
        tmnxOamLspPingCtlNhAddressType,
        tmnxOamLspPingCtlNhAddress
    }
    STATUS      obsolete
    DESCRIPTION
        "The group of objects supporting management of OAM LSP Ping tests on
         Nokia SROS series systems 5.0 release."
    ::= { tmnxOamPingGroups 27 }

tmnxOamVccvPingV5v0Group         OBJECT-GROUP
    OBJECTS     {
        tmnxOamVccvPingCtlSdpIdVcId,
        tmnxOamVccvPingCtlReplyMode,
        tmnxOamVccvPingCtlPwId,
        tmnxOamVccvPingCtlTtl
    }
    STATUS      current
    DESCRIPTION
        "The group of objects supporting management of OAM VCCV Ping tests on
         Nokia SROS series systems 5.0 release."
    ::= { tmnxOamPingGroups 28 }

tmnxOamAncpTestV5v0Group         OBJECT-GROUP
    OBJECTS     {
        tmnxOamAncpTestTarget,
        tmnxOamAncpTestTargetId,
        tmnxOamAncpTestcount,
        tmnxOamAncpTestTimeout,
        tmnxOamAncpHistoryAncpString,
        tmnxOamAncpHistoryAccNodeResult,
        tmnxOamAncpHistoryAccNodeCode,
        tmnxOamAncpHistoryAccNodeRspStr,
        tmnxOamVccvPingCtlTtl
    }
    STATUS      current
    DESCRIPTION
        "The group of objects supporting management of OAM ANCP tests on Nokia
         SROS series systems 5.0 release."
    ::= { tmnxOamPingGroups 29 }

tmnxOamPingNotificationV5v0Group NOTIFICATION-GROUP
    NOTIFICATIONS {
        tmnxOamPingProbeFailedV2,
        tmnxOamPingTestFailedV2,
        tmnxOamPingTestCompletedV2,
        tmnxAncpLoopbackTestCompleted
    }
    STATUS      obsolete
    DESCRIPTION
        "The group of notifications supporting the OAM ping feature on Nokia
         SROS series systems release 5.0."
    ::= { tmnxOamPingGroups 30 }

tmnxOamMfibPingV6v0Group         OBJECT-GROUP
    OBJECTS     {
        tmnxOamMfibPingCtlReplyControl,
        tmnxOamMfibPingCtlTtl,
        tmnxOamMfibPingCtlSrcAddrType,
        tmnxOamMfibPingCtlSrcAddress,
        tmnxOamMfibPingCtlDestAddrType,
        tmnxOamMfibPingCtlDestAddress,
        tmnxOamPingHistoryRespSvcId,
        tmnxOamMfibPingCtlDestMacAddr
    }
    STATUS      current
    DESCRIPTION
        "The group of objects supporting management of OAM MFIB Ping tests on
         Nokia SROS series systems release 6.0."
    ::= { tmnxOamPingGroups 31 }

tmnxOamPingGeneralV6v0Group      OBJECT-GROUP
    OBJECTS     {
        tmnxOamPingMaxConcurrentTests,
        tmnxOamPingCtlRowStatus,
        tmnxOamPingCtlStorageType,
        tmnxOamPingCtlDescr,
        tmnxOamPingCtlTestMode,
        tmnxOamPingCtlAdminStatus,
        tmnxOamPingCtlOrigSdpId,
        tmnxOamPingCtlRespSdpId,
        tmnxOamPingCtlFcName,
        tmnxOamPingCtlProfile,
        tmnxOamPingCtlMtuStartSize,
        tmnxOamPingCtlMtuEndSize,
        tmnxOamPingCtlMtuStepSize,
        tmnxOamPingCtlServiceId,
        tmnxOamPingCtlLocalSdp,
        tmnxOamPingCtlRemoteSdp,
        tmnxOamPingCtlSize,
        tmnxOamPingCtlTimeOut,
        tmnxOamPingCtlProbeCount,
        tmnxOamPingCtlInterval,
        tmnxOamPingCtlTrapGeneration,
        tmnxOamPingCtlTrapProbeFailureFilter,
        tmnxOamPingCtlTrapTestFailureFilter,
        tmnxOamPingCtlSAA,
        tmnxOamPingCtlRuns,
        tmnxOamPingCtlFailures,
        tmnxOamPingCtlLastRunResult,
        tmnxOamPingCtlLastChanged,
        tmnxOamPingCtlVRtrID,
        tmnxOamPingCtlTgtAddrType,
        tmnxOamPingCtlTgtAddress,
        tmnxOamPingCtlSrcAddrType,
        tmnxOamPingCtlSrcAddress,
        tmnxOamPingCtlDnsName,
        tmnxOamPingResultsOperStatus,
        tmnxOamPingResultsMinRtt,
        tmnxOamPingResultsMaxRtt,
        tmnxOamPingResultsAverageRtt,
        tmnxOamPingResultsRttSumOfSquares,
        tmnxOamPingResultsMtuResponseSize,
        tmnxOamPingResultsSvcPing,
        tmnxOamPingResultsProbeResponses,
        tmnxOamPingResultsSentProbes,
        tmnxOamPingResultsLastGoodProbe,
        tmnxOamPingResultsLastRespHeader,
        tmnxOamPingResultsMinTt,
        tmnxOamPingResultsMaxTt,
        tmnxOamPingResultsAverageTt,
        tmnxOamPingResultsTtSumOfSquares,
        tmnxOamPingResultsMinInTt,
        tmnxOamPingResultsMaxInTt,
        tmnxOamPingResultsAverageInTt,
        tmnxOamPingResultsInTtSumOfSqrs,
        tmnxOamPingResultsOutJitter,
        tmnxOamPingResultsInJitter,
        tmnxOamPingResultsRtJitter,
        tmnxOamPingResultsProbeTimeouts,
        tmnxOamPingResultsProbeFailures,
        tmnxOamPingHistoryResponse,
        tmnxOamPingHistoryOneWayTime,
        tmnxOamPingHistorySize,
        tmnxOamPingHistoryStatus,
        tmnxOamPingHistoryTime,
        tmnxOamPingHistoryReturnCode,
        tmnxOamPingHistAddressType,
        tmnxOamPingHistoryVersion,
        tmnxOamPingHistSapId,
        tmnxOamPingHistoryCpeMacAddr,
        tmnxOamPingHistoryRespSvcId,
        tmnxOamPingHistorySequence,
        tmnxOamPingHistoryIfIndex,
        tmnxOamPingHistoryDataLen,
        tmnxOamPingHistoryRespPlane,
        tmnxOamPingHistoryReqHdr,
        tmnxOamPingHistoryRespHdr,
        tmnxOamPingHistoryDnsAddrType,
        tmnxOamPingHistoryDnsAddress,
        tmnxOamPingHistorySrcAddrType,
        tmnxOamPingHistorySrcAddress,
        tmnxOamPingHistoryInOneWayTime,
        tmnxOamPingCtlDNSRecord
    }
    STATUS      obsolete
    DESCRIPTION
        "The group of objects supporting management of OAM ping tests general
         capabilities on Nokia SROS series systems 6.0 release"
    ::= { tmnxOamPingGroups 32 }

tmnxOamP2mpLspPingGroup          OBJECT-GROUP
    OBJECTS     {
        tmnxOamP2mpLspPingCtlLspName,
        tmnxOamP2mpLspPingCtlInstName,
        tmnxOamP2mpLspPingCtlTtl,
        tmnxOamP2mpLspPingCtlIpRowStatus,
        tmnxOamP2mpLspPingCtlIpAddrType,
        tmnxOamP2mpLspPingCtlIpAddr
    }
    STATUS      current
    DESCRIPTION
        "The group of objects supporting management of P2MP LSP Ping tests on
         Nokia SROS series systems 7.0 release."
    ::= { tmnxOamPingGroups 33 }

tmnxOamLspPingV6v0Group          OBJECT-GROUP
    OBJECTS     {
        tmnxOamLspPingCtlLspName,
        tmnxOamLspPingCtlTtl,
        tmnxOamLspPingCtlPathName,
        tmnxOamLspPingCtlLdpPrefixType,
        tmnxOamLspPingCtlLdpPrefix,
        tmnxOamLspPingCtlLdpPrefixLen,
        tmnxOamLspPingCtlPathDestType,
        tmnxOamLspPingCtlPathDest,
        tmnxOamLspPingCtlNhIntfName,
        tmnxOamLspPingCtlNhAddressType,
        tmnxOamLspPingCtlNhAddress
    }
    STATUS      obsolete
    DESCRIPTION
        "The group of objects supporting management of OAM LSP Ping tests on
         Nokia SROS series systems 6.0 release."
    ::= { tmnxOamPingGroups 34 }

tmnxOamPingGeneralV7v0Group      OBJECT-GROUP
    OBJECTS     {
        tmnxOamPingMaxConcurrentTests,
        tmnxOamPingCtlRowStatus,
        tmnxOamPingCtlStorageType,
        tmnxOamPingCtlDescr,
        tmnxOamPingCtlTestMode,
        tmnxOamPingCtlAdminStatus,
        tmnxOamPingCtlOrigSdpId,
        tmnxOamPingCtlRespSdpId,
        tmnxOamPingCtlFcName,
        tmnxOamPingCtlProfile,
        tmnxOamPingCtlMtuStartSize,
        tmnxOamPingCtlMtuEndSize,
        tmnxOamPingCtlMtuStepSize,
        tmnxOamPingCtlServiceId,
        tmnxOamPingCtlLocalSdp,
        tmnxOamPingCtlRemoteSdp,
        tmnxOamPingCtlSize,
        tmnxOamPingCtlTimeOut,
        tmnxOamPingCtlProbeCount,
        tmnxOamPingCtlInterval,
        tmnxOamPingCtlTrapGeneration,
        tmnxOamPingCtlTrapProbeFailureFilter,
        tmnxOamPingCtlTrapTestFailureFilter,
        tmnxOamPingCtlSAA,
        tmnxOamPingCtlRuns,
        tmnxOamPingCtlFailures,
        tmnxOamPingCtlLastRunResult,
        tmnxOamPingCtlLastChanged,
        tmnxOamPingCtlVRtrID,
        tmnxOamPingCtlTgtAddrType,
        tmnxOamPingCtlTgtAddress,
        tmnxOamPingCtlSrcAddrType,
        tmnxOamPingCtlSrcAddress,
        tmnxOamPingCtlDnsName,
        tmnxOamPingResultsOperStatus,
        tmnxOamPingResultsMinRtt,
        tmnxOamPingResultsMaxRtt,
        tmnxOamPingResultsAverageRtt,
        tmnxOamPingResultsRttSumOfSquares,
        tmnxOamPingResultsMtuResponseSize,
        tmnxOamPingResultsSvcPing,
        tmnxOamPingResultsProbeResponses,
        tmnxOamPingResultsSentProbes,
        tmnxOamPingResultsLastGoodProbe,
        tmnxOamPingResultsLastRespHeader,
        tmnxOamPingResultsMinTt,
        tmnxOamPingResultsMaxTt,
        tmnxOamPingResultsAverageTt,
        tmnxOamPingResultsTtSumOfSquares,
        tmnxOamPingResultsMinInTt,
        tmnxOamPingResultsMaxInTt,
        tmnxOamPingResultsAverageInTt,
        tmnxOamPingResultsInTtSumOfSqrs,
        tmnxOamPingResultsOutJitter,
        tmnxOamPingResultsInJitter,
        tmnxOamPingResultsRtJitter,
        tmnxOamPingResultsProbeTimeouts,
        tmnxOamPingResultsProbeFailures,
        tmnxOamPingHistoryResponse,
        tmnxOamPingHistoryOneWayTime,
        tmnxOamPingHistorySize,
        tmnxOamPingHistoryStatus,
        tmnxOamPingHistoryTime,
        tmnxOamPingHistoryReturnCode,
        tmnxOamPingHistAddressType,
        tmnxOamPingHistoryVersion,
        tmnxOamPingHistSapId,
        tmnxOamPingHistoryCpeMacAddr,
        tmnxOamPingHistoryRespSvcId,
        tmnxOamPingHistorySequence,
        tmnxOamPingHistoryIfIndex,
        tmnxOamPingHistoryDataLen,
        tmnxOamPingHistoryRespPlane,
        tmnxOamPingHistoryReqHdr,
        tmnxOamPingHistoryRespHdr,
        tmnxOamPingHistoryDnsAddrType,
        tmnxOamPingHistoryDnsAddress,
        tmnxOamPingHistorySrcAddrType,
        tmnxOamPingHistorySrcAddress,
        tmnxOamPingHistoryInOneWayTime,
        tmnxOamPingCtlDNSRecord,
        tmnxOamPingResultsRttOFSumSquares,
        tmnxOamPingResultsRttHCSumSquares,
        tmnxOamPingResultsTtOFSumSquares,
        tmnxOamPingResultsTtHCSumSquares,
        tmnxOamPingResultsInTtOFSumSqrs,
        tmnxOamPingResultsInTtHCSumSqrs,
        tmnxOamPingResultsTestRunResult
    }
    STATUS      obsolete
    DESCRIPTION
        "The group of objects supporting management of OAM ping tests general
         capabilities on Nokia SROS series systems 7.0 release"
    ::= { tmnxOamPingGroups 35 }

tmnxOamPingNotificationV7v0Group NOTIFICATION-GROUP
    NOTIFICATIONS {
        tmnxOamPingProbeFailedV3,
        tmnxOamPingTestFailedV3,
        tmnxOamPingTestCompletedV3,
        tmnxAncpLoopbackTestCompleted
    }
    STATUS      current
    DESCRIPTION
        "The group of notifications supporting the OAM ping feature on Nokia
         SROS series systems release 7.0."
    ::= { tmnxOamPingGroups 36 }

tmnxOamPingObsoleteV6v0Group     OBJECT-GROUP
    OBJECTS     {
        tmnxOamLspPingCtlReturnLsp,
        tmnxOamLspPingCtlVRtrID,
        tmnxOamPingCtlMaxRows
    }
    STATUS      current
    DESCRIPTION
        "The group of objects supporting management of OAM ping operations on
         Nokia SR series systems that were made obsolete in release 6.0."
    ::= { tmnxOamPingGroups 37 }

tmnxOamPingObsoleteV6v1Group     OBJECT-GROUP
    OBJECTS     {
        tmnxOamMacPingL2MapRouterID,
        tmnxOamMacPingL2MapLabel,
        tmnxOamMacPingL2MapProtocol,
        tmnxOamMacPingL2MapVCType,
        tmnxOamMacPingL2MapVCID,
        tmnxOamMacPingL2MapDirection
    }
    STATUS      current
    DESCRIPTION
        "The group of objects supporting management of OAM ping operations on
         Nokia SR series systems that were made obsolete in release 6.1."
    ::= { tmnxOamPingGroups 38 }

tmnxOamEthCfmPingV8v0Group       OBJECT-GROUP
    OBJECTS     {
        tmnxOamEthCfmPingCtlTgtMacAddr,
        tmnxOamEthCfmPingCtlSrcMdIndex,
        tmnxOamEthCfmPingCtlSrcMaIndex,
        tmnxOamEthCfmPingCtlSrcMepId
    }
    STATUS      current
    DESCRIPTION
        "The group of objects supporting management of OAM Ethernet CFM Ping
         tests on Nokia SROS series systems 8.0 release."
    ::= { tmnxOamPingGroups 39 }

tmnxOamP2mpLspPingV8v0Group      OBJECT-GROUP
    OBJECTS     {
        tmnxOamP2mpLspPingCtlP2MPId
    }
    STATUS      current
    DESCRIPTION
        "The group of objects supporting management of OAM P2MP LSP Ping tests
         on Nokia SROS series systems 8.0 release."
    ::= { tmnxOamPingGroups 40 }

tmnxOamPingGeneralV8v0Group      OBJECT-GROUP
    OBJECTS     {
        tmnxOamPingMaxConcurrentTests,
        tmnxOamPingCtlRowStatus,
        tmnxOamPingCtlStorageType,
        tmnxOamPingCtlDescr,
        tmnxOamPingCtlTestMode,
        tmnxOamPingCtlAdminStatus,
        tmnxOamPingCtlOrigSdpId,
        tmnxOamPingCtlRespSdpId,
        tmnxOamPingCtlFcName,
        tmnxOamPingCtlProfile,
        tmnxOamPingCtlMtuStartSize,
        tmnxOamPingCtlMtuEndSize,
        tmnxOamPingCtlMtuStepSize,
        tmnxOamPingCtlServiceId,
        tmnxOamPingCtlLocalSdp,
        tmnxOamPingCtlRemoteSdp,
        tmnxOamPingCtlSize,
        tmnxOamPingCtlTimeOut,
        tmnxOamPingCtlProbeCount,
        tmnxOamPingCtlInterval,
        tmnxOamPingCtlTrapGeneration,
        tmnxOamPingCtlTrapProbeFailureFilter,
        tmnxOamPingCtlTrapTestFailureFilter,
        tmnxOamPingCtlSAA,
        tmnxOamPingCtlRuns,
        tmnxOamPingCtlFailures,
        tmnxOamPingCtlLastRunResult,
        tmnxOamPingCtlLastChanged,
        tmnxOamPingCtlVRtrID,
        tmnxOamPingCtlTgtAddrType,
        tmnxOamPingCtlTgtAddress,
        tmnxOamPingCtlSrcAddrType,
        tmnxOamPingCtlSrcAddress,
        tmnxOamPingCtlDnsName,
        tmnxOamPingResultsOperStatus,
        tmnxOamPingResultsMinRtt,
        tmnxOamPingResultsMaxRtt,
        tmnxOamPingResultsAverageRtt,
        tmnxOamPingResultsRttSumOfSquares,
        tmnxOamPingResultsMtuResponseSize,
        tmnxOamPingResultsSvcPing,
        tmnxOamPingResultsProbeResponses,
        tmnxOamPingResultsSentProbes,
        tmnxOamPingResultsLastGoodProbe,
        tmnxOamPingResultsMinTt,
        tmnxOamPingResultsMaxTt,
        tmnxOamPingResultsAverageTt,
        tmnxOamPingResultsTtSumOfSquares,
        tmnxOamPingResultsMinInTt,
        tmnxOamPingResultsMaxInTt,
        tmnxOamPingResultsAverageInTt,
        tmnxOamPingResultsInTtSumOfSqrs,
        tmnxOamPingResultsOutJitter,
        tmnxOamPingResultsInJitter,
        tmnxOamPingResultsRtJitter,
        tmnxOamPingResultsProbeTimeouts,
        tmnxOamPingResultsProbeFailures,
        tmnxOamPingHistoryResponse,
        tmnxOamPingHistoryOneWayTime,
        tmnxOamPingHistorySize,
        tmnxOamPingHistoryStatus,
        tmnxOamPingHistoryTime,
        tmnxOamPingHistoryReturnCode,
        tmnxOamPingHistAddressType,
        tmnxOamPingHistoryVersion,
        tmnxOamPingHistSapId,
        tmnxOamPingHistoryCpeMacAddr,
        tmnxOamPingHistoryRespSvcId,
        tmnxOamPingHistorySequence,
        tmnxOamPingHistoryIfIndex,
        tmnxOamPingHistoryDataLen,
        tmnxOamPingHistoryRespPlane,
        tmnxOamPingHistoryReqHdr,
        tmnxOamPingHistoryRespHdr,
        tmnxOamPingHistoryDnsAddrType,
        tmnxOamPingHistoryDnsAddress,
        tmnxOamPingHistorySrcAddrType,
        tmnxOamPingHistorySrcAddress,
        tmnxOamPingHistoryInOneWayTime,
        tmnxOamPingHistoryLspName,
        tmnxOamPingHistNextHopAddrType,
        tmnxOamPingHistNextHopAddress,
        tmnxOamPingCtlDNSRecord,
        tmnxOamPingResultsRttOFSumSquares,
        tmnxOamPingResultsRttHCSumSquares,
        tmnxOamPingResultsTtOFSumSquares,
        tmnxOamPingResultsTtHCSumSquares,
        tmnxOamPingResultsInTtOFSumSqrs,
        tmnxOamPingResultsInTtHCSumSqrs,
        tmnxOamPingResultsTestRunResult
    }
    STATUS      obsolete
    DESCRIPTION
        "The group of objects supporting management of OAM ping tests general
         capabilities on Nokia SROS series systems 8.0 release"
    ::= { tmnxOamPingGroups 41 }

tmnxOamPingObsoleteV8v0Group     OBJECT-GROUP
    OBJECTS     {
        tmnxOamPingResultsLastRespHeader
    }
    STATUS      current
    DESCRIPTION
        "The group of objects supporting management of OAM ping operations on
         Nokia SR series systems that were made obsolete in release 8.0."
    ::= { tmnxOamPingGroups 42 }

tmnxOamVccvPingV9v0Group         OBJECT-GROUP
    OBJECTS     {
        tmnxOamVccvPingCtlSpokeSdpId,
        tmnxOamVccvPingCtlSaiiGlobalId,
        tmnxOamVccvPingCtlSaiiPrefix,
        tmnxOamVccvPingCtlSaiiAcId,
        tmnxOamVccvPingCtlTaiiGlobalId,
        tmnxOamVccvPingCtlTaiiPrefix,
        tmnxOamVccvPingCtlTaiiAcId
    }
    STATUS      current
    DESCRIPTION
        "The group of additional objects supporting management of OAM VCCV Ping
         tests on Nokia SROS series systems 9.0 release."
    ::= { tmnxOamPingGroups 43 }

tmnxOamPingCtlV10v0Group         OBJECT-GROUP
    OBJECTS     {
        tmnxOamPingCtlIntervalUnits
    }
    STATUS      current
    DESCRIPTION
        "The group of additional objects supporting management of OAM ping
         tests on Nokia SROS series systems, release 10.0."
    ::= { tmnxOamPingGroups 44 }

tmnxOamMobilePingGroup           OBJECT-GROUP
    OBJECTS     {
        tmnxOamMobGtpPingRefPointType,
        tmnxOamMobGtpPingVRtrId,
        tmnxOamMobGtpPingPort,
        tmnxOamMobGtpPingGateway
    }
    STATUS      current
    DESCRIPTION
        "The group of objects supporting management of OAM mobile gateway ping
         tests on Nokia 7x50 SR series systems."
    ::= { tmnxOamPingGroups 45 }

tmnxOamPingObsoleteV10v0Group    OBJECT-GROUP
    OBJECTS     {
        tmnxOamPingHistoryReqHdr
    }
    STATUS      current
    DESCRIPTION
        "The group of objects supporting management of OAM ping operations made
         obsolete in SROS Release 10.0 R1."
    ::= { tmnxOamPingGroups 46 }

tmnxOamPingGeneralV10v0Group     OBJECT-GROUP
    OBJECTS     {
        tmnxOamPingMaxConcurrentTests,
        tmnxOamPingCtlRowStatus,
        tmnxOamPingCtlTestMode,
        tmnxOamPingCtlAdminStatus,
        tmnxOamPingCtlOrigSdpId,
        tmnxOamPingCtlRespSdpId,
        tmnxOamPingCtlFcName,
        tmnxOamPingCtlProfile,
        tmnxOamPingCtlMtuStartSize,
        tmnxOamPingCtlMtuEndSize,
        tmnxOamPingCtlMtuStepSize,
        tmnxOamPingCtlServiceId,
        tmnxOamPingCtlLocalSdp,
        tmnxOamPingCtlRemoteSdp,
        tmnxOamPingCtlSize,
        tmnxOamPingCtlTimeOut,
        tmnxOamPingCtlProbeCount,
        tmnxOamPingCtlInterval,
        tmnxOamPingCtlTrapGeneration,
        tmnxOamPingCtlTrapProbeFailureFilter,
        tmnxOamPingCtlTrapTestFailureFilter,
        tmnxOamPingCtlSAA,
        tmnxOamPingCtlRuns,
        tmnxOamPingCtlFailures,
        tmnxOamPingCtlLastRunResult,
        tmnxOamPingCtlLastChanged,
        tmnxOamPingCtlVRtrID,
        tmnxOamPingCtlTgtAddrType,
        tmnxOamPingCtlTgtAddress,
        tmnxOamPingCtlSrcAddrType,
        tmnxOamPingCtlSrcAddress,
        tmnxOamPingCtlDnsName,
        tmnxOamPingResultsOperStatus,
        tmnxOamPingResultsMinRtt,
        tmnxOamPingResultsMaxRtt,
        tmnxOamPingResultsAverageRtt,
        tmnxOamPingResultsRttSumOfSquares,
        tmnxOamPingResultsMtuResponseSize,
        tmnxOamPingResultsSvcPing,
        tmnxOamPingResultsProbeResponses,
        tmnxOamPingResultsSentProbes,
        tmnxOamPingResultsLastGoodProbe,
        tmnxOamPingResultsMinTt,
        tmnxOamPingResultsMaxTt,
        tmnxOamPingResultsAverageTt,
        tmnxOamPingResultsTtSumOfSquares,
        tmnxOamPingResultsMinInTt,
        tmnxOamPingResultsMaxInTt,
        tmnxOamPingResultsAverageInTt,
        tmnxOamPingResultsInTtSumOfSqrs,
        tmnxOamPingResultsOutJitter,
        tmnxOamPingResultsInJitter,
        tmnxOamPingResultsRtJitter,
        tmnxOamPingResultsProbeTimeouts,
        tmnxOamPingResultsProbeFailures,
        tmnxOamPingHistoryResponse,
        tmnxOamPingHistoryOneWayTime,
        tmnxOamPingHistorySize,
        tmnxOamPingHistoryStatus,
        tmnxOamPingHistoryTime,
        tmnxOamPingHistoryReturnCode,
        tmnxOamPingHistAddressType,
        tmnxOamPingHistoryVersion,
        tmnxOamPingHistSapId,
        tmnxOamPingHistoryCpeMacAddr,
        tmnxOamPingHistoryRespSvcId,
        tmnxOamPingHistorySequence,
        tmnxOamPingHistoryIfIndex,
        tmnxOamPingHistoryDataLen,
        tmnxOamPingHistoryRespPlane,
        tmnxOamPingHistoryRespHdr,
        tmnxOamPingHistoryDnsAddrType,
        tmnxOamPingHistoryDnsAddress,
        tmnxOamPingHistorySrcAddrType,
        tmnxOamPingHistorySrcAddress,
        tmnxOamPingHistoryInOneWayTime,
        tmnxOamPingHistoryLspName,
        tmnxOamPingHistNextHopAddrType,
        tmnxOamPingHistNextHopAddress,
        tmnxOamPingCtlDNSRecord,
        tmnxOamPingResultsRttOFSumSquares,
        tmnxOamPingResultsRttHCSumSquares,
        tmnxOamPingResultsTtOFSumSquares,
        tmnxOamPingResultsTtHCSumSquares,
        tmnxOamPingResultsInTtOFSumSqrs,
        tmnxOamPingResultsInTtHCSumSqrs,
        tmnxOamPingResultsTestRunResult
    }
    STATUS      current
    DESCRIPTION
        "The group of objects supporting management of OAM ping tests general
         capabilities on SROS release 10.0, and still supported in the latest
         SROS release."
    ::= { tmnxOamPingGroups 47 }

tmnxOamP2mpLspPingV10v0Group     OBJECT-GROUP
    OBJECTS     {
        tmnxOamP2mpLspPingCtlSrcAddrType,
        tmnxOamP2mpLspPingCtlSrcAddr,
        tmnxOamP2mpLspPingCtlGrpAddrType,
        tmnxOamP2mpLspPingCtlGrpAddr
    }
    STATUS      current
    DESCRIPTION
        "The group of objects supporting management of OAM P2MP LSP Ping tests
         on Nokia SROS series systems 10.0 release."
    ::= { tmnxOamPingGroups 48 }

tmnxOamPingObsoleteV11v0Group    OBJECT-GROUP
    OBJECTS     {
        tmnxOamMacPingCtlFibEntryName
    }
    STATUS      current
    DESCRIPTION
        "The group of objects supporting management of OAM ping operations made
         obsolete in SROS Release 11.0 R1."
    ::= { tmnxOamPingGroups 49 }

tmnxOamMacPingCtlV11v0Group      OBJECT-GROUP
    OBJECTS     {
        tmnxOamMacPingCtlTargetMacAddr,
        tmnxOamMacPingCtlSourceMacAddr,
        tmnxOamMacPingCtlSendControl,
        tmnxOamMacPingCtlReplyControl,
        tmnxOamMacPingCtlTtl,
        tmnxOamMacPingCtlRegister,
        tmnxOamMacPingCtlFlood,
        tmnxOamMacPingCtlForce,
        tmnxOamMacPingCtlAge,
        tmnxOamMacPingCtlSapPortId,
        tmnxOamMacPingCtlSapEncapValue
    }
    STATUS      current
    DESCRIPTION
        "The group of objects supporting configuration of OAM Mac Ping tests on
         Nokia SROS series systems release 11.0."
    ::= { tmnxOamPingGroups 50 }

tmnxOamMacPingHistoryV11v0Group  OBJECT-GROUP
    OBJECTS     {
        tmnxOamMacPingHistoryResponse,
        tmnxOamMacPingHistoryOneWayTime,
        tmnxOamMacPingHistoryStatus,
        tmnxOamMacPingHistoryTime,
        tmnxOamMacPingHistoryReturnCode,
        tmnxOamMacPingHistoryAddressType,
        tmnxOamMacPingHistorySapId,
        tmnxOamMacPingHistorySdpId,
        tmnxOamMacPingHistoryAdminStatus,
        tmnxOamMacPingHistoryOperStatus,
        tmnxOamMacPingHistoryResponsePlane,
        tmnxOamMacPingHistorySize,
        tmnxOamMacPingHistoryInOneWayTime,
        tmnxOamMacPingHistorySrcAddrType,
        tmnxOamMacPingHistorySrcAddress
    }
    STATUS      current
    DESCRIPTION
        "The group of objects supporting reporting results of OAM Mac Ping
         tests on Nokia SROS series systems release 11.0."
    ::= { tmnxOamPingGroups 51 }

tmnxOamLspPingV11v0Group         OBJECT-GROUP
    OBJECTS     {
        tmnxOamLspPingCtlAssocChannel,
        tmnxOamLspPingCtlForce,
        tmnxOamLspPingCtlLdpPrefix,
        tmnxOamLspPingCtlLdpPrefixLen,
        tmnxOamLspPingCtlLdpPrefixType,
        tmnxOamLspPingCtlLspName,
        tmnxOamLspPingCtlMplsTpGlobalId,
        tmnxOamLspPingCtlMplsTpNodeId,
        tmnxOamLspPingCtlMplsTpPathType,
        tmnxOamLspPingCtlNhAddress,
        tmnxOamLspPingCtlNhAddressType,
        tmnxOamLspPingCtlNhIntfName,
        tmnxOamLspPingCtlPathDest,
        tmnxOamLspPingCtlPathDestType,
        tmnxOamLspPingCtlPathName,
        tmnxOamLspPingCtlTestSubMode,
        tmnxOamLspPingCtlTtl
    }
    STATUS      current
    DESCRIPTION
        "The group of objects supporting management of OAM LSP Ping tests on
         Nokia SROS systems, release 11.0."
    ::= { tmnxOamPingGroups 52 }

tmnxOamVccvPingV11v0Group        OBJECT-GROUP
    OBJECTS     {
        tmnxOamVccvPingCtlAssocChannel,
        tmnxOamVccvPingCtlMplsTpGlobalId,
        tmnxOamVccvPingCtlMplsTpNodeId,
        tmnxOamVccvPingCtlTestSubMode
    }
    STATUS      current
    DESCRIPTION
        "The group of additional objects supporting management of OAM VCCV Ping
         tests on Nokia SROS series systems running release 11.0."
    ::= { tmnxOamPingGroups 53 }

tmnxOamPingV11v0Group            OBJECT-GROUP
    OBJECTS     {
        tmnxOamPingHistoryRtrnSubcode,
        tmnxOamPingHistorySdpBindId,
        tmnxOamPingHistorySrcGlobalId,
        tmnxOamPingHistorySrcNodeId
    }
    STATUS      current
    DESCRIPTION
        "The group of additional objects supporting management of OAM Ping
         tests on Nokia SROS series systems running release 11.0."
    ::= { tmnxOamPingGroups 54 }

tmnxOamPingV12v0Group            OBJECT-GROUP
    OBJECTS     {
        tmnxOamVccvPgTgFec128CtlDstAddr,
        tmnxOamVccvPgTgFec128CtlDstAddrT,
        tmnxOamVccvPgTgFec128CtlPwId,
        tmnxOamVccvPgTgFec128CtlPwType,
        tmnxOamVccvPgTgFec128CtlSrcAddr,
        tmnxOamVccvPgTgFec128CtlSrcAddrT,
        tmnxOamVccvPgTgStaticCtlAgi,
        tmnxOamVccvPgTgStaticCtlSaiiAcId,
        tmnxOamVccvPgTgStaticCtlSaiiGlbl,
        tmnxOamVccvPgTgStaticCtlSaiiNode,
        tmnxOamVccvPgTgStaticCtlTaiiAcId,
        tmnxOamVccvPgTgStaticCtlTaiiGlbl,
        tmnxOamVccvPgTgStaticCtlTaiiNode,
        tmnxOamVccvPingCtlSwitTgtFecType
    }
    STATUS      current
    DESCRIPTION
        "The group of additional objects supporting management of OAM Ping
         tests on Nokia SROS series systems running release 12.0."
    ::= { tmnxOamPingGroups 55 }

tmnxOamPingV13v0Group            OBJECT-GROUP
    OBJECTS     {
        tmnxOamBfdOnLspBootStrRetryCount,
        tmnxOamBfdOnLspLspName,
        tmnxOamBfdOnLspPathState,
        tmnxOamBfdOnLspPingReturnCode,
        tmnxOamBfdOnLspPingReturnSubcode,
        tmnxOamBfdOnLspPingRxCount,
        tmnxOamBfdOnLspPingTxCount,
        tmnxOamBfdOnLspPingTxInterval,
        tmnxOamBfdOnLspRemoteAddress,
        tmnxOamBfdOnLspRemoteAddressType,
        tmnxOamBfdOnLspRemoteBfdDiscrim,
        tmnxOamPingHistoryNetworkIfName,
        tmnxOamPingResultsOutOfOrder,
        tmnxOamVxlanPingCtlEndSysMacAddr,
        tmnxOamVxlanPingCtlIFlag,
        tmnxOamVxlanPingCtlInIpDstAddr,
        tmnxOamVxlanPingCtlInIpDstAddrT,
        tmnxOamVxlanPingCtlInIpSrcAddr,
        tmnxOamVxlanPingCtlInIpSrcAddrT,
        tmnxOamVxlanPingCtlInL2DestMac,
        tmnxOamVxlanPingCtlNetworkId,
        tmnxOamVxlanPingCtlOutIpTtl,
        tmnxOamVxlanPingCtlOutSrcUdpPt,
        tmnxOamVxlanPingCtlReflectPad,
        tmnxOamVxlanPingCtlReplyMode,
        tmnxOamVxlanPingCtlTestId,
        tmnxOamVxlanPingHistNetworkId,
        tmnxOamVxlanPingHistOutIpTtl,
        tmnxOamVxlanPingHistReturnCode,
        tmnxOamVxlanPingHistRtrnSubCode,
        tmnxOamVxlanPingHistValidationRC
    }
    STATUS      current
    DESCRIPTION
        "The group of additional objects supporting management of OAM Ping
         tests on Nokia SROS series systems running release 13.0."
    ::= { tmnxOamPingGroups 56 }

tmnxOamPingObsoleteV14v0Group    OBJECT-GROUP
    OBJECTS     {
        tmnxOamPingCtlDescr,
        tmnxOamPingCtlStorageType
    }
    STATUS      current
    DESCRIPTION
        "The group of objects supporting management of OAM ping operations on
         Nokia SR series systems that were made obsolete in SROS release 14.0."
    ::= { tmnxOamPingGroups 57 }

tmnxOamPingV14v0Group            OBJECT-GROUP
    OBJECTS     {
        tmnxOamVxlanPingResOutSrcAddrTyp,
        tmnxOamVxlanPingResOutSrcAddress,
        tmnxOamP2mpLspPingCtlOptionalTLV
    }
    STATUS      current
    DESCRIPTION
        "The group of additional objects supporting management of OAM Ping
         tests on Nokia SROS series systems running release 14.0."
    ::= { tmnxOamPingGroups 58 }

tmnxOamPingV15v0Group            OBJECT-GROUP
    OBJECTS     {
        tmnxOamBfdOnLspFecType,
        tmnxOamBfdOnLspOperState,
        tmnxOamBfdOnLspPrefix,
        tmnxOamBfdOnLspPrefixLen,
        tmnxOamBfdOnLspPrefixType,
        tmnxOamBfdOnLspSessBootstrInProg,
        tmnxOamBfdOnLspSessBootstrNoPV,
        tmnxOamBfdOnLspSessBootstrSendPV,
        tmnxOamBfdOnLspSourceAddress,
        tmnxOamBfdOnLspSourceAddressType,
        tmnxOamEthCfmPingCtlRemoteMepId,
        tmnxOamLspPingCtlIgpInstance,
        tmnxOamPingCtlSubscriberName
    }
    STATUS      current
    DESCRIPTION
        "The group of additional objects supporting management of OAM Ping
         tests on Nokia SROS series systems running release 15.0."
    ::= { tmnxOamPingGroups 59 }

tmnxOamTraceRouteConformance     OBJECT IDENTIFIER ::= { tmnxOamTestConformance 2 }

tmnxOamTrCompliances             OBJECT IDENTIFIER ::= { tmnxOamTraceRouteConformance 1 }

tmnxOamTr7450V4v0Compliance      MODULE-COMPLIANCE
    STATUS      obsolete
    DESCRIPTION
        "The compliance statement for management of OAM Trace Route tests on
         Nokia 7450 ESS series systems."
    MODULE
        MANDATORY-GROUPS {
            tmnxOamTrGeneralV4v0Group,
            tmnxOamTrHopsV4v0Group,
            tmnxOamMacTrV3v0Group,
            tmnxOamLspTrV4v0Group,
            tmnxOamMcastTrV4v0Group,
            tmnxOamTrNotificationV4v0Group
        }
    ::= { tmnxOamTrCompliances 3 }

tmnxOamTr7750V4v0Compliance      MODULE-COMPLIANCE
    STATUS      obsolete
    DESCRIPTION
        "The compliance statement for management of OAM Trace Route tests on
         Nokia SROS series systems."
    MODULE
        MANDATORY-GROUPS {
            tmnxOamTrGeneralV4v0Group,
            tmnxOamTrHopsV4v0Group,
            tmnxOamMacTrV3v0Group,
            tmnxOamLspTrV4v0Group,
            tmnxOamVprnTrV4v0Group,
            tmnxOamMcastTrV4v0Group,
            tmnxOamTrNotificationV4v0Group
        }
    ::= { tmnxOamTrCompliances 4 }

tmnxOamTr7450V5v0Compliance      MODULE-COMPLIANCE
    STATUS      obsolete
    DESCRIPTION
        "The compliance statement for management of OAM Trace Route tests on
         Nokia 7450 ESS series systems."
    MODULE
        MANDATORY-GROUPS {
            tmnxOamTrGeneralV5v0Group,
            tmnxOamTrHopsV4v0Group,
            tmnxOamMacTrV3v0Group,
            tmnxOamLspTrV5v0Group,
            tmnxOamMcastTrV4v0Group,
            tmnxOamTrNotificationV5v0Group
        }
    ::= { tmnxOamTrCompliances 5 }

tmnxOamTr7750V5v0Compliance      MODULE-COMPLIANCE
    STATUS      obsolete
    DESCRIPTION
        "The compliance statement for management of OAM Trace Route tests on
         Nokia SROS series systems."
    MODULE
        MANDATORY-GROUPS {
            tmnxOamTrGeneralV5v0Group,
            tmnxOamTrHopsV4v0Group,
            tmnxOamMacTrV3v0Group,
            tmnxOamLspTrV5v0Group,
            tmnxOamVprnTrV4v0Group,
            tmnxOamMcastTrV4v0Group,
            tmnxOamTrNotificationV5v0Group
        }
    ::= { tmnxOamTrCompliances 6 }

tmnxOamTr7450V6v0Compliance      MODULE-COMPLIANCE
    STATUS      obsolete
    DESCRIPTION
        "The compliance statement for management of OAM Trace Route tests on
         Nokia 7450 ESS series systems."
    MODULE
        MANDATORY-GROUPS {
            tmnxOamTrGeneralV6v0Group,
            tmnxOamTrHopsV4v0Group,
            tmnxOamMacTrV3v0Group,
            tmnxOamLspTrV6v0Group,
            tmnxOamMcastTrV4v0Group,
            tmnxOamVccvTrV6v0Group,
            tmnxOamTrNotificationV5v0Group
        }
    ::= { tmnxOamTrCompliances 7 }

tmnxOamTr77x0V6v0Compliance      MODULE-COMPLIANCE
    STATUS      obsolete
    DESCRIPTION
        "The compliance statement for management of OAM Trace Route tests on
         Nokia 7710/7750 SR series systems."
    MODULE
        MANDATORY-GROUPS {
            tmnxOamTrGeneralV6v0Group,
            tmnxOamTrHopsV4v0Group,
            tmnxOamMacTrV3v0Group,
            tmnxOamLspTrV6v0Group,
            tmnxOamVprnTrV6v0Group,
            tmnxOamMcastTrV4v0Group,
            tmnxOamVccvTrV6v0Group,
            tmnxOamTrNotificationV5v0Group
        }
    ::= { tmnxOamTrCompliances 8 }

tmnxOamTr7450V7v0Compliance      MODULE-COMPLIANCE
    STATUS      obsolete
    DESCRIPTION
        "The compliance statement for management of OAM Trace Route tests on
         Nokia 7450 ESS series systems."
    MODULE
        MANDATORY-GROUPS {
            tmnxOamTrGeneralV7v0Group,
            tmnxOamTrHopsV4v0Group,
            tmnxOamMacTrV3v0Group,
            tmnxOamLspTrV6v0Group,
            tmnxOamMcastTrV4v0Group,
            tmnxOamVccvTrV6v0Group,
            tmnxOamTrNotificationV5v0Group
        }
    ::= { tmnxOamTrCompliances 9 }

tmnxOamTr77x0V7v0Compliance      MODULE-COMPLIANCE
    STATUS      obsolete
    DESCRIPTION
        "The compliance statement for management of OAM Trace Route tests on
         Nokia 7710/7750 SR series systems."
    MODULE
        MANDATORY-GROUPS {
            tmnxOamTrGeneralV7v0Group,
            tmnxOamTrHopsV4v0Group,
            tmnxOamMacTrV3v0Group,
            tmnxOamLspTrV6v0Group,
            tmnxOamVprnTrV6v0Group,
            tmnxOamMcastTrV4v0Group,
            tmnxOamVccvTrV6v0Group,
            tmnxOamTrNotificationV5v0Group,
            tmnxOamP2mpLspTraceGroup
        }
    ::= { tmnxOamTrCompliances 10 }

tmnxOamTr7xx0V8v0Compliance      MODULE-COMPLIANCE
    STATUS      obsolete
    DESCRIPTION
        "The compliance statement for management of OAM Trace Route tests on
         Nokia 7450/7710/7750 series systems."
    MODULE
        MANDATORY-GROUPS {
            tmnxOamTrGeneralV7v0Group,
            tmnxOamTrHopsV4v0Group,
            tmnxOamMacTrV3v0Group,
            tmnxOamLspTrV6v0Group,
            tmnxOamVprnTrV6v0Group,
            tmnxOamMcastTrV4v0Group,
            tmnxOamVccvTrV6v0Group,
            tmnxOamTrNotificationV5v0Group,
            tmnxOamP2mpLspTraceGroup,
            tmnxOamEthCfmTrV8v0Group,
            tmnxOamTrGeneralV8v0Group,
            tmnxOamTrNotificationV8v0Group
        }
    ::= { tmnxOamTrCompliances 11 }

tmnxOamTr7xx0V9v0Compliance      MODULE-COMPLIANCE
    STATUS      obsolete
    DESCRIPTION
        "The compliance statement for management of OAM Trace Route tests on
         Nokia SROS series systems, release 9.0."
    MODULE
        MANDATORY-GROUPS {
            tmnxOamEthCfmTrV8v0Group,
            tmnxOamLTtraceV9v0Group,
            tmnxOamLspTrV6v0Group,
            tmnxOamMacTrV3v0Group,
            tmnxOamMcastTrV4v0Group,
            tmnxOamP2mpLspTraceGroup,
            tmnxOamTrGeneralV7v0Group,
            tmnxOamTrGeneralV8v0Group,
            tmnxOamTrHopsV4v0Group,
            tmnxOamTrNotificationV5v0Group,
            tmnxOamTrNotificationV8v0Group,
            tmnxOamVccvTrV6v0Group,
            tmnxOamVccvTrV9v0Group,
            tmnxOamVprnTrV6v0Group
        }
    ::= { tmnxOamTrCompliances 12 }

tmnxOamTr7xx0V11v0Compliance     MODULE-COMPLIANCE
    STATUS      current
    DESCRIPTION
        "The compliance statement for management of OAM Trace Route tests on
         Nokia SROS series systems, release 11.0."
    MODULE
        MANDATORY-GROUPS {
            tmnxOamEthCfmTrV8v0Group,
            tmnxOamLTtraceV9v0Group,
            tmnxOamLspTrV6v0Group,
            tmnxOamMacTrV3v0Group,
            tmnxOamMcastTrV4v0Group,
            tmnxOamP2mpLspTraceGroup,
            tmnxOamTrGeneralV7v0Group,
            tmnxOamTrGeneralV8v0Group,
            tmnxOamTrGeneralV11v0Group,
            tmnxOamTrHopsV4v0Group,
            tmnxOamTrNotificationV5v0Group,
            tmnxOamTrNotificationV8v0Group,
            tmnxOamTrV11v0Group,
            tmnxOamVccvTrV6v0Group,
            tmnxOamVccvTrV9v0Group,
            tmnxOamVccvTrV11v0Group,
            tmnxOamVprnTrV6v0Group
        }
    ::= { tmnxOamTrCompliances 13 }

tmnxOamTr7xx0V12v0Compliance     MODULE-COMPLIANCE
    STATUS      current
    DESCRIPTION
        "The incremental module compliance statement for management of OAM Trace
         Route tests on Nokia SROS series systems, release 12.0.  The
         corresponding base module compliance statement is
         tmnxOamTr7xx0V11v0Compliance."
    MODULE
        MANDATORY-GROUPS {
            tmnxOamTrV12v0Group
        }
    ::= { tmnxOamTrCompliances 14 }

tmnxOamTr7xx0V13v0Compliance     MODULE-COMPLIANCE
    STATUS      current
    DESCRIPTION
        "The incremental module compliance statement for management of OAM
         Trace Route tests on Nokia SROS series systems, release 13.0."
    MODULE
        MANDATORY-GROUPS {
            tmnxOamTrV13v0Group
        }
    ::= { tmnxOamTrCompliances 15 }

tmnxOamTr7xx0V15v0Compliance     MODULE-COMPLIANCE
    STATUS      current
    DESCRIPTION
        "The incremental module compliance statement for management of OAM
         Trace Route tests on Nokia SROS series systems, release 15.0."
    MODULE
        MANDATORY-GROUPS {
            tmnxOamTrV15v0Group
        }
    ::= { tmnxOamTrCompliances 17 }

tmnxOamTrGroups                  OBJECT IDENTIFIER ::= { tmnxOamTraceRouteConformance 2 }

tmnxOamMacTrV3v0Group            OBJECT-GROUP
    OBJECTS     {
        tmnxOamMacTrCtlTargetMacAddr,
        tmnxOamMacTrCtlSourceMacAddr,
        tmnxOamMacTrCtlSendControl,
        tmnxOamMacTrCtlReplyControl,
        tmnxOamMacTrL2MapRouterID,
        tmnxOamMacTrL2MapLabel,
        tmnxOamMacTrL2MapProtocol,
        tmnxOamMacTrL2MapVCType,
        tmnxOamMacTrL2MapVCID,
        tmnxOamMacTrL2MapDirection,
        tmnxOamMacTrL2MapSdpId,
        tmnxOamMacTrL2MapSapName
    }
    STATUS      current
    DESCRIPTION
        "The group of objects supporting management of OAM MAC Trace Route
         tests on Nokia SROS series systems."
    ::= { tmnxOamTrGroups 10 }

tmnxOamTrObsoleteV3v0Group       OBJECT-GROUP
    OBJECTS     {
        tmnxOamTrResultsTestAttempts,
        tmnxOamTrResultsTestSuccesses
    }
    STATUS      current
    DESCRIPTION
        "The group of objects supporting management of OAM Trace Route tests
         that became obsolete in the 3.0 release."
    ::= { tmnxOamTrGroups 11 }

tmnxOamTrGeneralV4v0Group        OBJECT-GROUP
    OBJECTS     {
        tmnxOamTrMaxConcurrentRequests,
        tmnxOamTrCtlRowStatus,
        tmnxOamTrCtlStorageType,
        tmnxOamTrCtlDescr,
        tmnxOamTrCtlTestMode,
        tmnxOamTrCtlAdminStatus,
        tmnxOamTrCtlFcName,
        tmnxOamTrCtlProfile,
        tmnxOamTrCtlServiceId,
        tmnxOamTrCtlDataSize,
        tmnxOamTrCtlTimeOut,
        tmnxOamTrCtlProbesPerHop,
        tmnxOamTrCtlMaxTtl,
        tmnxOamTrCtlInitialTtl,
        tmnxOamTrCtlDSField,
        tmnxOamTrCtlMaxFailures,
        tmnxOamTrCtlInterval,
        tmnxOamTrCtlMaxRows,
        tmnxOamTrCtlTrapGeneration,
        tmnxOamTrCtlCreateHopsEntries,
        tmnxOamTrCtlSAA,
        tmnxOamTrCtlRuns,
        tmnxOamTrCtlFailures,
        tmnxOamTrCtlLastRunResult,
        tmnxOamTrCtlLastChanged,
        tmnxOamTrCtlVRtrID,
        tmnxOamTrCtlTgtAddrType,
        tmnxOamTrCtlTgtAddress,
        tmnxOamTrCtlSrcAddrType,
        tmnxOamTrCtlSrcAddress,
        tmnxOamTrCtlWaitMilliSec,
        tmnxOamTrResultsOperStatus,
        tmnxOamTrResultsCurHopCount,
        tmnxOamTrResultsCurProbeCount,
        tmnxOamTrResultsLastGoodPath,
        tmnxOamTrResultsTgtAddrType,
        tmnxOamTrResultsTgtAddress,
        tmnxOamTrProbeHistoryResponse,
        tmnxOamTrProbeHistoryOneWayTime,
        tmnxOamTrProbeHistoryStatus,
        tmnxOamTrProbeHistoryLastRC,
        tmnxOamTrProbeHistoryTime,
        tmnxOamTrProbeHistoryResponsePlane,
        tmnxOamTrProbeHistoryAddressType,
        tmnxOamTrProbeHistorySapId,
        tmnxOamTrProbeHistoryVersion,
        tmnxOamTrProbeHistoryRouterID,
        tmnxOamTrProbeHistoryIfIndex,
        tmnxOamTrProbeHistoryDataLen,
        tmnxOamTrProbeHistorySize,
        tmnxOamTrProbeHistoryInOneWayTime,
        tmnxOamTrProbeHistoryAddrType,
        tmnxOamTrProbeHistoryAddress
    }
    STATUS      obsolete
    DESCRIPTION
        "The group of objects supporting management of OAM Trace Route test
         general capabilities on Nokia SROS series systems 4.0R1 release."
    ::= { tmnxOamTrGroups 12 }

tmnxOamTrHopsV4v0Group           OBJECT-GROUP
    OBJECTS     {
        tmnxOamTrHopsMinRtt,
        tmnxOamTrHopsMaxRtt,
        tmnxOamTrHopsAverageRtt,
        tmnxOamTrHopsRttSumOfSquares,
        tmnxOamTrHopsMinTt,
        tmnxOamTrHopsMaxTt,
        tmnxOamTrHopsAverageTt,
        tmnxOamTrHopsTtSumOfSquares,
        tmnxOamTrHopsSentProbes,
        tmnxOamTrHopsProbeResponses,
        tmnxOamTrHopsLastGoodProbe,
        tmnxOamTrHopsMinInTt,
        tmnxOamTrHopsMaxInTt,
        tmnxOamTrHopsAverageInTt,
        tmnxOamTrHopsInTtSumOfSqrs,
        tmnxOamTrHopsOutJitter,
        tmnxOamTrHopsInJitter,
        tmnxOamTrHopsRtJitter,
        tmnxOamTrHopsProbeTimeouts,
        tmnxOamTrHopsProbeFailures,
        tmnxOamTrHopsTgtAddrType,
        tmnxOamTrHopsTgtAddress
    }
    STATUS      current
    DESCRIPTION
        "The group of optional objects to report OAM Trace Route Hops returned
         in response to OAM Trace Route tests on Nokia 7x50 SR series systems
         4.0R1."
    ::= { tmnxOamTrGroups 13 }

tmnxOamLspTrV4v0Group            OBJECT-GROUP
    OBJECTS     {
        tmnxOamLspTrCtlVRtrID,
        tmnxOamLspTrCtlLspName,
        tmnxOamLspTrCtlPathName,
        tmnxOamLspTrCtlLdpPrefixType,
        tmnxOamLspTrCtlLdpPrefix,
        tmnxOamLspTrCtlLdpPrefixLen,
        tmnxOamLspTrMapAddrType,
        tmnxOamLspTrMapDSIPv4Addr,
        tmnxOamLspTrMapDSIfAddr,
        tmnxOamLspTrMapMTU,
        tmnxOamLspTrMapDSIndex,
        tmnxOamLspTrDSLabelLabel,
        tmnxOamLspTrDSLabelProtocol
    }
    STATUS      obsolete
    DESCRIPTION
        "The group of objects supporting management of OAM LSP Trace Route
         tests on Nokia SROS series systems 4.0 release."
    ::= { tmnxOamTrGroups 14 }

tmnxOamVprnTrV4v0Group           OBJECT-GROUP
    OBJECTS     {
        tmnxOamVprnTrCtlReplyControl,
        tmnxOamVprnTrCtlSrcAddrType,
        tmnxOamVprnTrCtlSrcAddress,
        tmnxOamVprnTrL3MapRouterID,
        tmnxOamVprnTrL3MapRteVprnLabel,
        tmnxOamVprnTrL3MapRteMetrics,
        tmnxOamVprnTrL3MapRteLastUp,
        tmnxOamVprnTrL3MapRteOwner,
        tmnxOamVprnTrL3MapRtePref,
        tmnxOamVprnTrL3MapRteDist,
        tmnxOamVprnTrL3MapNumNextHops,
        tmnxOamVprnTrL3MapNumRteTargets,
        tmnxOamVprnTrL3MapDestAddrType,
        tmnxOamVprnTrL3MapDestAddress,
        tmnxOamVprnTrL3MapDestMaskLen,
        tmnxOamVprnTrNextHopRtrID,
        tmnxOamVprnTrNextHopType,
        tmnxOamVprnTrNextHopTunnelID,
        tmnxOamVprnTrNextHopTunnelType,
        tmnxOamVprnTrNextHopIfIndex,
        tmnxOamVprnTrRouteTarget
    }
    STATUS      obsolete
    DESCRIPTION
        "The group of objects supporting management of OAM VPRN Trace Route
         tests on Nokia SROS series systems release 4.0."
    ::= { tmnxOamTrGroups 15 }

tmnxOamMcastTrV4v0Group          OBJECT-GROUP
    OBJECTS     {
        tmnxOamMcastTrCtlVRtrID,
        tmnxOamMcastTrCtlHops,
        tmnxOamMcastTrQueryId,
        tmnxOamMcastTrCtlSrcAddrType,
        tmnxOamMcastTrCtlSrcAddress,
        tmnxOamMcastTrCtlDestAddrType,
        tmnxOamMcastTrCtlDestAddress,
        tmnxOamMcastTrCtlRespAddrType,
        tmnxOamMcastTrCtlRespAddress,
        tmnxOamMcastTrCtlGrpAddrType,
        tmnxOamMcastTrCtlGrpAddress,
        tmnxOamMcastTrRespQueryArrivalTime,
        tmnxOamMcastTrRespInPktCount,
        tmnxOamMcastTrRespOutPktCount,
        tmnxOamMcastTrRespSGPktCount,
        tmnxOamMcastTrRespRtgProtocol,
        tmnxOamMcastTrRespFwdTtl,
        tmnxOamMcastTrRespMBZBit,
        tmnxOamMcastTrRespSrcBit,
        tmnxOamMcastTrRespSrcMask,
        tmnxOamMcastTrRespFwdCode,
        tmnxOamMcastTrRespInIfAddrType,
        tmnxOamMcastTrRespInIfAddress,
        tmnxOamMcastTrRespOutIfAddrType,
        tmnxOamMcastTrRespOutIfAddress,
        tmnxOamMcastTrRespPhRtrAddrType,
        tmnxOamMcastTrRespPhRtrAddress
    }
    STATUS      current
    DESCRIPTION
        "The group of objects supporting management of OAM Multicast Trace
         Route tests on Nokia SROS series systems release 4.0."
    ::= { tmnxOamTrGroups 16 }

tmnxOamTrObsoleteV4v0Group       OBJECT-GROUP
    OBJECTS     {
        tmnxOamTrCtlTargetIpAddress,
        tmnxOamTrResultsIpTgtAddr,
        tmnxOamTrProbeHistoryIpAddr,
        tmnxOamTrHopsIpTgtAddress,
        tmnxOamLspTrCtlLdpIpPrefix,
        tmnxOamLspTrCtlLdpIpPrefixLen,
        tmnxOamVprnTrCtlSourceIpAddr,
        tmnxOamVprnTrL3MapRteDestAddr,
        tmnxOamVprnTrL3MapRteDestMask,
        tmnxOamMcastTrCtlSrcIpAddr,
        tmnxOamMcastTrCtlDestIpAddr,
        tmnxOamMcastTrCtlRespIpAddr,
        tmnxOamMcastTrCtlGrpIpAddr,
        tmnxOamMcastTrRespPrevHopRtrAddr,
        tmnxOamMcastTrRespInIfAddr,
        tmnxOamMcastTrRespOutIfAddr
    }
    STATUS      current
    DESCRIPTION
        "The group of objects supporting management of OAM trace route tests on
         Nokia SROS series systems that were made obsolete in release 4.0."
    ::= { tmnxOamTrGroups 17 }

tmnxOamTrNotificationV4v0Group   NOTIFICATION-GROUP
    NOTIFICATIONS {
        tmnxOamTrPathChange,
        tmnxOamTrTestFailed,
        tmnxOamTrTestCompleted
    }
    STATUS      obsolete
    DESCRIPTION
        "The group of notifications supporting the OAM Trace Route test feature
         on Nokia SROS series systems release 4.0."
    ::= { tmnxOamTrGroups 18 }

tmnxOamLspTrV5v0Group            OBJECT-GROUP
    OBJECTS     {
        tmnxOamLspTrCtlVRtrID,
        tmnxOamLspTrCtlLspName,
        tmnxOamLspTrCtlPathName,
        tmnxOamLspTrCtlLdpPrefixType,
        tmnxOamLspTrCtlLdpPrefix,
        tmnxOamLspTrCtlLdpPrefixLen,
        tmnxOamLspTrCtlPathDestType,
        tmnxOamLspTrCtlPathDest,
        tmnxOamLspTrCtlNhIntfName,
        tmnxOamLspTrCtlNhAddressType,
        tmnxOamLspTrCtlNhAddress,
        tmnxOamLspTrMapAddrType,
        tmnxOamLspTrMapDSIPv4Addr,
        tmnxOamLspTrMapDSIfAddr,
        tmnxOamLspTrMapMTU,
        tmnxOamLspTrDSLabelLabel,
        tmnxOamLspTrDSLabelProtocol
    }
    STATUS      obsolete
    DESCRIPTION
        "The group of objects supporting management of OAM LSP Trace Route
         tests on Nokia SROS series systems 5.0 release."
    ::= { tmnxOamTrGroups 19 }

tmnxOamTrObsoleteV5v0Group       OBJECT-GROUP
    OBJECTS     {
        tmnxOamLspTrMapDSIndex
    }
    STATUS      current
    DESCRIPTION
        "The group of objects supporting management of OAM Trace tests on Nokia
         SROS series systems that were made obsolete in release 5.0."
    ::= { tmnxOamTrGroups 20 }

tmnxOamTrGeneralV5v0Group        OBJECT-GROUP
    OBJECTS     {
        tmnxOamTrMaxConcurrentRequests,
        tmnxOamTrCtlRowStatus,
        tmnxOamTrCtlStorageType,
        tmnxOamTrCtlDescr,
        tmnxOamTrCtlTestMode,
        tmnxOamTrCtlAdminStatus,
        tmnxOamTrCtlFcName,
        tmnxOamTrCtlProfile,
        tmnxOamTrCtlServiceId,
        tmnxOamTrCtlDataSize,
        tmnxOamTrCtlTimeOut,
        tmnxOamTrCtlProbesPerHop,
        tmnxOamTrCtlMaxTtl,
        tmnxOamTrCtlInitialTtl,
        tmnxOamTrCtlDSField,
        tmnxOamTrCtlMaxFailures,
        tmnxOamTrCtlInterval,
        tmnxOamTrCtlMaxRows,
        tmnxOamTrCtlTrapGeneration,
        tmnxOamTrCtlCreateHopsEntries,
        tmnxOamTrCtlSAA,
        tmnxOamTrCtlRuns,
        tmnxOamTrCtlFailures,
        tmnxOamTrCtlLastRunResult,
        tmnxOamTrCtlLastChanged,
        tmnxOamTrCtlVRtrID,
        tmnxOamTrCtlTgtAddrType,
        tmnxOamTrCtlTgtAddress,
        tmnxOamTrCtlSrcAddrType,
        tmnxOamTrCtlSrcAddress,
        tmnxOamTrCtlWaitMilliSec,
        tmnxOamTrResultsOperStatus,
        tmnxOamTrResultsCurHopCount,
        tmnxOamTrResultsCurProbeCount,
        tmnxOamTrResultsLastGoodPath,
        tmnxOamTrResultsTgtAddrType,
        tmnxOamTrResultsTgtAddress,
        tmnxOamTrProbeHistoryResponse,
        tmnxOamTrProbeHistoryOneWayTime,
        tmnxOamTrProbeHistoryStatus,
        tmnxOamTrProbeHistoryLastRC,
        tmnxOamTrProbeHistoryTime,
        tmnxOamTrProbeHistoryResponsePlane,
        tmnxOamTrProbeHistoryAddressType,
        tmnxOamTrProbeHistorySapId,
        tmnxOamTrProbeHistoryVersion,
        tmnxOamTrProbeHistoryRouterID,
        tmnxOamTrProbeHistoryIfIndex,
        tmnxOamTrProbeHistoryDataLen,
        tmnxOamTrProbeHistorySize,
        tmnxOamTrProbeHistoryInOneWayTime,
        tmnxOamTrProbeHistoryAddrType,
        tmnxOamTrProbeHistoryAddress,
        tmnxOamLTtraceFecDiscoveryState,
        tmnxOamLTtraceFecDisStatusBits,
        tmnxOamLTtraceFecDisPaths,
        tmnxOamLTtraceFecFailedHops,
        tmnxOamLTtraceFecLastDisEnd,
        tmnxOamLTtraceFecFailedProbes,
        tmnxOamLTtraceFecProbeState,
        tmnxOamLTtracePathRemAddrType,
        tmnxOamLTtracePathRemoteAddr,
        tmnxOamLTtracePathEgrNhAddrType,
        tmnxOamLTtracePathEgrNhAddr,
        tmnxOamLTtracePathDisTtl,
        tmnxOamLTtracePathLastDisTime,
        tmnxOamLTtracePathLastRc,
        tmnxOamLTtracePathProbeState,
        tmnxOamLTtraceCtlLdpPrefixType,
        tmnxOamLTtraceCtlLdpPrefix,
        tmnxOamLTtraceCtlLdpPrefixLen,
        tmnxOamLTtraceCtlMaxPath,
        tmnxOamLTtraceResultsDisPaths,
        tmnxOamLTtraceResultsFailedHops,
        tmnxOamLTtraceResultsDisState,
        tmnxOamLTtraceResultsDisStatus,
        tmnxOamLTtraceUpStreamHopIndex,
        tmnxOamLTtraceHopAddrType,
        tmnxOamLTtraceHopAddr,
        tmnxOamLTtraceHopDstAddrType,
        tmnxOamLTtraceHopDstAddr,
        tmnxOamLTtraceHopEgrNhAddrType,
        tmnxOamLTtraceHopEgrNhAddr,
        tmnxOamLTtraceHopDisTtl,
        tmnxOamLTtraceHopLastRc,
        tmnxOamLTtraceHopDiscoveryState,
        tmnxOamLTtraceHopDiscoveryTime,
        tmnxOamLTtraceAutoRowStatus,
        tmnxOamLTtraceAutoLastChanged,
        tmnxOamLTtraceAutoStorageType,
        tmnxOamLTtraceAutoAdminState,
        tmnxOamLTtraceAutoFcName,
        tmnxOamLTtraceAutoProfile,
        tmnxOamLTtraceAutoDiscIntvl,
        tmnxOamLTtraceAutoMaxPath,
        tmnxOamLTtraceAutoTrMaxTtl,
        tmnxOamLTtraceAutoTrTimeOut,
        tmnxOamLTtraceAutoTrMaxFailures,
        tmnxOamLTtraceAutoPolicy1,
        tmnxOamLTtraceAutoPolicy2,
        tmnxOamLTtraceAutoPolicy3,
        tmnxOamLTtraceAutoPolicy4,
        tmnxOamLTtraceAutoPolicy5,
        tmnxOamLTtraceAutoProbeIntvl,
        tmnxOamLTtraceAutoPrTimeOut,
        tmnxOamLTtraceAutoPrMaxFailures,
        tmnxOamLTtraceAutoDiscoveryState,
        tmnxOamLTtraceAutoTotalFecs,
        tmnxOamLTtraceAutoDisFecs,
        tmnxOamLTtraceAutoLastDisStart,
        tmnxOamLTtraceAutoLastDisEnd,
        tmnxOamLTtraceAutoLastDisDur,
        tmnxOamLTtracePathProbeState,
        tmnxOamLTtracePathProbeTmOutCnt,
        tmnxOamLTtraceMaxConRequests
    }
    STATUS      obsolete
    DESCRIPTION
        "The group of objects supporting management of OAM Trace Route test
         general capabilities on Nokia SROS series systems 5.0 release."
    ::= { tmnxOamTrGroups 21 }

tmnxOamTrNotificationV5v0Group   NOTIFICATION-GROUP
    NOTIFICATIONS {
        tmnxOamTrPathChange,
        tmnxOamTrTestFailed,
        tmnxOamTrTestCompleted,
        tmnxOamLdpTtraceAutoDiscState,
        tmnxOamLdpTtraceFecProbeState,
        tmnxOamLdpTtraceFecDisStatus
    }
    STATUS      current
    DESCRIPTION
        "The group of notifications supporting the OAM Trace Route test feature
         on Nokia SROS series systems release 5.0."
    ::= { tmnxOamTrGroups 22 }

tmnxOamVccvTrV6v0Group           OBJECT-GROUP
    OBJECTS     {
        tmnxOamVccvTrCtlSdpIdVcId,
        tmnxOamVccvTrCtlReplyMode,
        tmnxOamVccvTrNextPwID,
        tmnxOamVccvTrNextPwType,
        tmnxOamVccvTrNextSenderAddrType,
        tmnxOamVccvTrNextSenderAddr,
        tmnxOamVccvTrNextRemoteAddrType,
        tmnxOamVccvTrNextRemoteAddr
    }
    STATUS      current
    DESCRIPTION
        "The group of objects supporting management of OAM VCCV Trace Route
         test general capabilities on Nokia SROS series systems 6.0 release."
    ::= { tmnxOamTrGroups 23 }

tmnxOamVprnTrObsoleteV6v0Group   OBJECT-GROUP
    OBJECTS     {
        tmnxOamVprnTrNextHopRtrID
    }
    STATUS      current
    DESCRIPTION
        "The group of objects supporting management of OAM VPRN Trace Route
         tests on Nokia SROS series systems that were made obsolete in release
         6.0."
    ::= { tmnxOamTrGroups 24 }

tmnxOamVprnTrV6v0Group           OBJECT-GROUP
    OBJECTS     {
        tmnxOamVprnTrCtlReplyControl,
        tmnxOamVprnTrCtlSrcAddrType,
        tmnxOamVprnTrCtlSrcAddress,
        tmnxOamVprnTrL3MapRouterID,
        tmnxOamVprnTrL3MapRteVprnLabel,
        tmnxOamVprnTrL3MapRteMetrics,
        tmnxOamVprnTrL3MapRteLastUp,
        tmnxOamVprnTrL3MapRteOwner,
        tmnxOamVprnTrL3MapRtePref,
        tmnxOamVprnTrL3MapRteDist,
        tmnxOamVprnTrL3MapNumNextHops,
        tmnxOamVprnTrL3MapNumRteTargets,
        tmnxOamVprnTrL3MapDestAddrType,
        tmnxOamVprnTrL3MapDestAddress,
        tmnxOamVprnTrL3MapDestMaskLen,
        tmnxOamVprnTrNextHopType,
        tmnxOamVprnTrNextHopTunnelID,
        tmnxOamVprnTrNextHopTunnelType,
        tmnxOamVprnTrNextHopIfIndex,
        tmnxOamVprnTrNextHopAddrType,
        tmnxOamVprnTrNextHopAddress,
        tmnxOamVprnTrRouteTarget
    }
    STATUS      current
    DESCRIPTION
        "The group of objects supporting management of OAM VPRN Trace Route
         tests on Nokia SROS series systems release 6.0."
    ::= { tmnxOamTrGroups 25 }

tmnxOamP2mpLspTraceGroup         OBJECT-GROUP
    OBJECTS     {
        tmnxOamP2mpLspTrCtlInstName,
        tmnxOamP2mpLspTrCtlLeafIpAddr,
        tmnxOamP2mpLspTrCtlLeafIpAddrType,
        tmnxOamP2mpLspTrCtlLspName,
        tmnxOamP2mpLspTrMapAddrType,
        tmnxOamP2mpLspTrMapDSIPv4Addr,
        tmnxOamP2mpLspTrMapDSIfAddr,
        tmnxOamP2mpLspTrMapMTU,
        tmnxOamP2mpLspTrMapP2mpBranch,
        tmnxOamP2mpLspTrMapP2mpBud,
        tmnxOamP2mpLspTrDSLabelLabel,
        tmnxOamP2mpLspTrDSLabelProtocol
    }
    STATUS      current
    DESCRIPTION
        "The group of objects supporting management of OAM P2MP LSP Trace Route
         tests on Nokia SROS series systems release 7.0."
    ::= { tmnxOamTrGroups 26 }

tmnxOamTrGeneralV6v0Group        OBJECT-GROUP
    OBJECTS     {
        tmnxOamTrMaxConcurrentRequests,
        tmnxOamTrCtlRowStatus,
        tmnxOamTrCtlStorageType,
        tmnxOamTrCtlDescr,
        tmnxOamTrCtlTestMode,
        tmnxOamTrCtlAdminStatus,
        tmnxOamTrCtlFcName,
        tmnxOamTrCtlProfile,
        tmnxOamTrCtlServiceId,
        tmnxOamTrCtlDataSize,
        tmnxOamTrCtlTimeOut,
        tmnxOamTrCtlProbesPerHop,
        tmnxOamTrCtlMaxTtl,
        tmnxOamTrCtlInitialTtl,
        tmnxOamTrCtlDSField,
        tmnxOamTrCtlMaxFailures,
        tmnxOamTrCtlInterval,
        tmnxOamTrCtlTrapGeneration,
        tmnxOamTrCtlSAA,
        tmnxOamTrCtlRuns,
        tmnxOamTrCtlFailures,
        tmnxOamTrCtlLastRunResult,
        tmnxOamTrCtlLastChanged,
        tmnxOamTrCtlVRtrID,
        tmnxOamTrCtlTgtAddrType,
        tmnxOamTrCtlTgtAddress,
        tmnxOamTrCtlSrcAddrType,
        tmnxOamTrCtlSrcAddress,
        tmnxOamTrCtlWaitMilliSec,
        tmnxOamTrResultsOperStatus,
        tmnxOamTrResultsCurHopCount,
        tmnxOamTrResultsCurProbeCount,
        tmnxOamTrResultsLastGoodPath,
        tmnxOamTrResultsTgtAddrType,
        tmnxOamTrResultsTgtAddress,
        tmnxOamTrProbeHistoryResponse,
        tmnxOamTrProbeHistoryOneWayTime,
        tmnxOamTrProbeHistoryStatus,
        tmnxOamTrProbeHistoryLastRC,
        tmnxOamTrProbeHistoryTime,
        tmnxOamTrProbeHistoryResponsePlane,
        tmnxOamTrProbeHistoryAddressType,
        tmnxOamTrProbeHistorySapId,
        tmnxOamTrProbeHistoryVersion,
        tmnxOamTrProbeHistoryRouterID,
        tmnxOamTrProbeHistoryIfIndex,
        tmnxOamTrProbeHistoryDataLen,
        tmnxOamTrProbeHistorySize,
        tmnxOamTrProbeHistoryInOneWayTime,
        tmnxOamTrProbeHistoryAddrType,
        tmnxOamTrProbeHistoryAddress,
        tmnxOamLTtraceFecDiscoveryState,
        tmnxOamLTtraceFecDisStatusBits,
        tmnxOamLTtraceFecDisPaths,
        tmnxOamLTtraceFecFailedHops,
        tmnxOamLTtraceFecLastDisEnd,
        tmnxOamLTtraceFecFailedProbes,
        tmnxOamLTtraceFecProbeState,
        tmnxOamLTtracePathRemAddrType,
        tmnxOamLTtracePathRemoteAddr,
        tmnxOamLTtracePathEgrNhAddrType,
        tmnxOamLTtracePathEgrNhAddr,
        tmnxOamLTtracePathDisTtl,
        tmnxOamLTtracePathLastDisTime,
        tmnxOamLTtracePathLastRc,
        tmnxOamLTtracePathProbeState,
        tmnxOamLTtraceCtlLdpPrefixType,
        tmnxOamLTtraceCtlLdpPrefix,
        tmnxOamLTtraceCtlLdpPrefixLen,
        tmnxOamLTtraceCtlMaxPath,
        tmnxOamLTtraceResultsDisPaths,
        tmnxOamLTtraceResultsFailedHops,
        tmnxOamLTtraceResultsDisState,
        tmnxOamLTtraceResultsDisStatus,
        tmnxOamLTtraceUpStreamHopIndex,
        tmnxOamLTtraceHopAddrType,
        tmnxOamLTtraceHopAddr,
        tmnxOamLTtraceHopDstAddrType,
        tmnxOamLTtraceHopDstAddr,
        tmnxOamLTtraceHopEgrNhAddrType,
        tmnxOamLTtraceHopEgrNhAddr,
        tmnxOamLTtraceHopDisTtl,
        tmnxOamLTtraceHopLastRc,
        tmnxOamLTtraceHopDiscoveryState,
        tmnxOamLTtraceHopDiscoveryTime,
        tmnxOamLTtraceAutoRowStatus,
        tmnxOamLTtraceAutoLastChanged,
        tmnxOamLTtraceAutoStorageType,
        tmnxOamLTtraceAutoAdminState,
        tmnxOamLTtraceAutoFcName,
        tmnxOamLTtraceAutoProfile,
        tmnxOamLTtraceAutoDiscIntvl,
        tmnxOamLTtraceAutoMaxPath,
        tmnxOamLTtraceAutoTrMaxTtl,
        tmnxOamLTtraceAutoTrTimeOut,
        tmnxOamLTtraceAutoTrMaxFailures,
        tmnxOamLTtraceAutoPolicy1,
        tmnxOamLTtraceAutoPolicy2,
        tmnxOamLTtraceAutoPolicy3,
        tmnxOamLTtraceAutoPolicy4,
        tmnxOamLTtraceAutoPolicy5,
        tmnxOamLTtraceAutoProbeIntvl,
        tmnxOamLTtraceAutoPrTimeOut,
        tmnxOamLTtraceAutoPrMaxFailures,
        tmnxOamLTtraceAutoDiscoveryState,
        tmnxOamLTtraceAutoTotalFecs,
        tmnxOamLTtraceAutoDisFecs,
        tmnxOamLTtraceAutoLastDisStart,
        tmnxOamLTtraceAutoLastDisEnd,
        tmnxOamLTtraceAutoLastDisDur,
        tmnxOamLTtracePathProbeState,
        tmnxOamLTtracePathProbeTmOutCnt,
        tmnxOamLTtraceMaxConRequests
    }
    STATUS      obsolete
    DESCRIPTION
        "The group of objects supporting management of OAM Trace Route test
         general capabilities on Nokia SROS series systems 6.0 release."
    ::= { tmnxOamTrGroups 27 }

tmnxOamTrObsoleteV6v0Group       OBJECT-GROUP
    OBJECTS     {
        tmnxOamTrCtlCreateHopsEntries,
        tmnxOamLspTrCtlVRtrID,
        tmnxOamTrCtlMaxRows
    }
    STATUS      current
    DESCRIPTION
        "The group of objects supporting management of OAM trace route
         operations on Nokia SR series systems that were made obsolete in
         release 6.0.

         Please see tmnxOamVprnTrObsoleteV6v0Group for additional obsoleted
         objects."
    ::= { tmnxOamTrGroups 28 }

tmnxOamTrGeneralV7v0Group        OBJECT-GROUP
    OBJECTS     {
        tmnxOamTrMaxConcurrentRequests,
        tmnxOamTrCtlRowStatus,
        tmnxOamTrCtlTestMode,
        tmnxOamTrCtlAdminStatus,
        tmnxOamTrCtlFcName,
        tmnxOamTrCtlProfile,
        tmnxOamTrCtlServiceId,
        tmnxOamTrCtlDataSize,
        tmnxOamTrCtlTimeOut,
        tmnxOamTrCtlProbesPerHop,
        tmnxOamTrCtlMaxTtl,
        tmnxOamTrCtlInitialTtl,
        tmnxOamTrCtlDSField,
        tmnxOamTrCtlMaxFailures,
        tmnxOamTrCtlInterval,
        tmnxOamTrCtlTrapGeneration,
        tmnxOamTrCtlSAA,
        tmnxOamTrCtlRuns,
        tmnxOamTrCtlFailures,
        tmnxOamTrCtlLastRunResult,
        tmnxOamTrCtlLastChanged,
        tmnxOamTrCtlVRtrID,
        tmnxOamTrCtlTgtAddrType,
        tmnxOamTrCtlTgtAddress,
        tmnxOamTrCtlSrcAddrType,
        tmnxOamTrCtlSrcAddress,
        tmnxOamTrCtlWaitMilliSec,
        tmnxOamTrResultsOperStatus,
        tmnxOamTrResultsCurHopCount,
        tmnxOamTrResultsCurProbeCount,
        tmnxOamTrResultsLastGoodPath,
        tmnxOamTrResultsTgtAddrType,
        tmnxOamTrResultsTgtAddress,
        tmnxOamTrProbeHistoryResponse,
        tmnxOamTrProbeHistoryOneWayTime,
        tmnxOamTrProbeHistoryStatus,
        tmnxOamTrProbeHistoryLastRC,
        tmnxOamTrProbeHistoryTime,
        tmnxOamTrProbeHistoryResponsePlane,
        tmnxOamTrProbeHistoryAddressType,
        tmnxOamTrProbeHistorySapId,
        tmnxOamTrProbeHistoryVersion,
        tmnxOamTrProbeHistoryRouterID,
        tmnxOamTrProbeHistoryIfIndex,
        tmnxOamTrProbeHistoryDataLen,
        tmnxOamTrProbeHistorySize,
        tmnxOamTrProbeHistoryInOneWayTime,
        tmnxOamTrProbeHistoryAddrType,
        tmnxOamTrProbeHistoryAddress,
        tmnxOamLTtraceFecDiscoveryState,
        tmnxOamLTtraceFecDisStatusBits,
        tmnxOamLTtraceFecDisPaths,
        tmnxOamLTtraceFecFailedHops,
        tmnxOamLTtraceFecLastDisEnd,
        tmnxOamLTtraceFecFailedProbes,
        tmnxOamLTtraceFecProbeState,
        tmnxOamLTtracePathRemAddrType,
        tmnxOamLTtracePathRemoteAddr,
        tmnxOamLTtracePathEgrNhAddrType,
        tmnxOamLTtracePathEgrNhAddr,
        tmnxOamLTtracePathDisTtl,
        tmnxOamLTtracePathLastDisTime,
        tmnxOamLTtracePathLastRc,
        tmnxOamLTtracePathProbeState,
        tmnxOamLTtraceCtlLdpPrefixType,
        tmnxOamLTtraceCtlLdpPrefix,
        tmnxOamLTtraceCtlLdpPrefixLen,
        tmnxOamLTtraceCtlMaxPath,
        tmnxOamLTtraceResultsDisPaths,
        tmnxOamLTtraceResultsFailedHops,
        tmnxOamLTtraceResultsDisState,
        tmnxOamLTtraceResultsDisStatus,
        tmnxOamLTtraceUpStreamHopIndex,
        tmnxOamLTtraceHopAddrType,
        tmnxOamLTtraceHopAddr,
        tmnxOamLTtraceHopDstAddrType,
        tmnxOamLTtraceHopDstAddr,
        tmnxOamLTtraceHopEgrNhAddrType,
        tmnxOamLTtraceHopEgrNhAddr,
        tmnxOamLTtraceHopDisTtl,
        tmnxOamLTtraceHopLastRc,
        tmnxOamLTtraceHopDiscoveryState,
        tmnxOamLTtraceHopDiscoveryTime,
        tmnxOamLTtraceAutoRowStatus,
        tmnxOamLTtraceAutoLastChanged,
        tmnxOamLTtraceAutoAdminState,
        tmnxOamLTtraceAutoFcName,
        tmnxOamLTtraceAutoProfile,
        tmnxOamLTtraceAutoDiscIntvl,
        tmnxOamLTtraceAutoMaxPath,
        tmnxOamLTtraceAutoTrMaxTtl,
        tmnxOamLTtraceAutoTrTimeOut,
        tmnxOamLTtraceAutoTrMaxFailures,
        tmnxOamLTtraceAutoPolicy1,
        tmnxOamLTtraceAutoPolicy2,
        tmnxOamLTtraceAutoPolicy3,
        tmnxOamLTtraceAutoPolicy4,
        tmnxOamLTtraceAutoPolicy5,
        tmnxOamLTtraceAutoProbeIntvl,
        tmnxOamLTtraceAutoPrTimeOut,
        tmnxOamLTtraceAutoPrMaxFailures,
        tmnxOamLTtraceAutoDiscoveryState,
        tmnxOamLTtraceAutoTotalFecs,
        tmnxOamLTtraceAutoDisFecs,
        tmnxOamLTtraceAutoLastDisStart,
        tmnxOamLTtraceAutoLastDisEnd,
        tmnxOamLTtraceAutoLastDisDur,
        tmnxOamLTtracePathProbeState,
        tmnxOamLTtracePathProbeTmOutCnt,
        tmnxOamLTtraceMaxConRequests,
        tmnxOamTrHopsRttOFSumSquares,
        tmnxOamTrHopsRttHCSumSquares,
        tmnxOamTrHopsTtOFSumSquares,
        tmnxOamTrHopsTtHCSumSquares,
        tmnxOamTrHopsInTtOFSumSqrs,
        tmnxOamTrHopsInTtHCSumSqrs,
        tmnxOamTrResultsTestRunResult
    }
    STATUS      current
    DESCRIPTION
        "The group of objects supporting management of OAM Trace Route test
         general capabilities on Nokia SROS series systems 7.0 release, and
         still supported in the latest SROS release."
    ::= { tmnxOamTrGroups 29 }

tmnxOamEthCfmTrV8v0Group         OBJECT-GROUP
    OBJECTS     {
        tmnxOamEthCfmTrCtlTgtMacAddr,
        tmnxOamEthCfmTrCtlSrcMdIndex,
        tmnxOamEthCfmTrCtlSrcMaIndex,
        tmnxOamEthCfmTrCtlSrcMepId,
        tmnxOamEthCfmTrPrHistIngressMac,
        tmnxOamEthCfmTrPrHistEgressMac,
        tmnxOamEthCfmTrPrHistRelayAction,
        tmnxOamEthCfmTrPrHistForwarded,
        tmnxOamEthCfmTrPrHistTerminalMep
    }
    STATUS      current
    DESCRIPTION
        "The group of objects supporting management of OAM Ethernet CFM trace
         route tests on Nokia SROS series systems 8.0 release."
    ::= { tmnxOamTrGroups 30 }

tmnxOamLspTrV6v0Group            OBJECT-GROUP
    OBJECTS     {
        tmnxOamLspTrCtlLspName,
        tmnxOamLspTrCtlPathName,
        tmnxOamLspTrCtlLdpPrefixType,
        tmnxOamLspTrCtlLdpPrefix,
        tmnxOamLspTrCtlLdpPrefixLen,
        tmnxOamLspTrCtlPathDestType,
        tmnxOamLspTrCtlPathDest,
        tmnxOamLspTrCtlNhIntfName,
        tmnxOamLspTrCtlNhAddressType,
        tmnxOamLspTrCtlNhAddress,
        tmnxOamLspTrMapAddrType,
        tmnxOamLspTrMapDSIPv4Addr,
        tmnxOamLspTrMapDSIfAddr,
        tmnxOamLspTrMapMTU,
        tmnxOamLspTrDSLabelLabel,
        tmnxOamLspTrDSLabelProtocol
    }
    STATUS      current
    DESCRIPTION
        "The group of objects supporting management of OAM LSP Trace Route
         tests on Nokia SROS series systems 6.0 release."
    ::= { tmnxOamTrGroups 31 }

tmnxOamTrGeneralV8v0Group        OBJECT-GROUP
    OBJECTS     {
        tmnxOamLTtracePathProbeSendErr,
        tmnxOamLTtraceFecSendErrProbes
    }
    STATUS      current
    DESCRIPTION
        "The group of objects supporting management of OAM Trace Route test
         general capabilities on Nokia SROS series systems 8.0 release."
    ::= { tmnxOamTrGroups 32 }

tmnxOamTrNotificationV8v0Group   NOTIFICATION-GROUP
    NOTIFICATIONS {
        tmnxOamLdpTtraceFecPFailUpdate
    }
    STATUS      current
    DESCRIPTION
        "The group of notifications supporting the OAM Trace Route test feature
         on Nokia SROS series systems release 8.0."
    ::= { tmnxOamTrGroups 33 }

tmnxOamVccvTrV9v0Group           OBJECT-GROUP
    OBJECTS     {
        tmnxOamVccvTrCtlSpokeSdpId,
        tmnxOamVccvTrCtlSaiiGlobalId,
        tmnxOamVccvTrCtlSaiiPrefix,
        tmnxOamVccvTrCtlSaiiAcId,
        tmnxOamVccvTrCtlTaiiGlobalId,
        tmnxOamVccvTrCtlTaiiPrefix,
        tmnxOamVccvTrCtlTaiiAcId,
        tmnxOamVccvTrNextSaiiGlobalId,
        tmnxOamVccvTrNextSaiiPrefix,
        tmnxOamVccvTrNextSaiiAcId,
        tmnxOamVccvTrNextTaiiGlobalId,
        tmnxOamVccvTrNextTaiiPrefix,
        tmnxOamVccvTrNextTaiiAcId
    }
    STATUS      current
    DESCRIPTION
        "The group of additional objects supporting management of OAM VCCV
         Trace Route test general capabilities on Nokia SROS series 9.0
         release."
    ::= { tmnxOamTrGroups 34 }

tmnxOamLTtraceV9v0Group          OBJECT-GROUP
    OBJECTS     {
        tmnxOamLTtraceHopLabel1,
        tmnxOamLTtraceHopLabel2,
        tmnxOamLTtraceHopLabel3,
        tmnxOamLTtraceHopLabel4,
        tmnxOamLTtraceHopLabel5,
        tmnxOamLTtraceHopLabel6,
        tmnxOamLTtraceHopIfAddrType,
        tmnxOamLTtraceHopIfAddress,
        tmnxOamLTtraceHopRouterIdType,
        tmnxOamLTtraceHopRouterId
    }
    STATUS      current
    DESCRIPTION
        "The group of additional objects supporting management of OAM LDP Tree
         Discovery capabilities on Nokia SROS series 9.0 release."
    ::= { tmnxOamTrGroups 35 }

tmnxOamTrGeneralV11v0Group       OBJECT-GROUP
    OBJECTS     {
        tmnxOamLTtraceCtlDownstreamMpTlv,
        tmnxOamLspTrCtlAssocChannel,
        tmnxOamLspTrCtlDownstreamMapTlv,
        tmnxOamLspTrCtlForce,
        tmnxOamLspTrCtlMplsTpPathType,
        tmnxOamLspTrCtlTestSubMode,
        tmnxOamLspTrFecStackFecSubType,
        tmnxOamLspTrFecStackOperType,
        tmnxOamLspTrFecStackPrefix,
        tmnxOamLspTrFecStackPrefixLen,
        tmnxOamLspTrFecStackPrefixType,
        tmnxOamLspTrFecStackRemPeerAddr,
        tmnxOamLspTrFecStackRemPeerAddrT,
        tmnxOamTrProbeHistoryRtrnSubcode,
        tmnxOamTrProbeHistorySdpBindId
    }
    STATUS      current
    DESCRIPTION
        "The group of additional objects supporting management of OAM Trace
         Route tests on Nokia SROS series systems, release 11.0."
    ::= { tmnxOamTrGroups 36 }

tmnxOamVccvTrV11v0Group          OBJECT-GROUP
    OBJECTS     {
        tmnxOamVccvTrCtlAssocChannel,
        tmnxOamVccvTrCtlTestSubMode
    }
    STATUS      current
    DESCRIPTION
        "The group of additional objects supporting management of OAM VCCV
         trace route tests on Nokia SROS series systems running release 11.0."
    ::= { tmnxOamTrGroups 37 }

tmnxOamTrV11v0Group              OBJECT-GROUP
    OBJECTS     {
        tmnxOamTrProbeHistorySrcGlobalId,
        tmnxOamTrProbeHistorySrcNodeId,
        tmnxOamVccvTrNextTpAgi,
        tmnxOamVccvTrNextTpSaiiAcId,
        tmnxOamVccvTrNextTpSaiiGlobalId,
        tmnxOamVccvTrNextTpSaiiNodeId,
        tmnxOamVccvTrNextTpTaiiAcId,
        tmnxOamVccvTrNextTpTaiiGlobalId,
        tmnxOamVccvTrNextTpTaiiNodeId
    }
    STATUS      current
    DESCRIPTION
        "The group of additional objects supporting management of OAM trace
         route tests on Nokia SROS series systems running release 11.0."
    ::= { tmnxOamTrGroups 38 }

tmnxOamTrV12v0Group              OBJECT-GROUP
    OBJECTS     {
        tmnxOamIcmpTrLabelStackBottom,
        tmnxOamIcmpTrLabelStackExperimnt,
        tmnxOamIcmpTrLabelStackLabel,
        tmnxOamIcmpTrLabelStackTtl,
        tmnxOamVccvTrCtlSwitTgtFecType,
        tmnxOamVccvTrTgFec128CtlDstAddr,
        tmnxOamVccvTrTgFec128CtlDstAddrT,
        tmnxOamVccvTrTgFec128CtlPwId,
        tmnxOamVccvTrTgFec128CtlPwType,
        tmnxOamVccvTrTgFec128CtlSrcAddr,
        tmnxOamVccvTrTgFec128CtlSrcAddrT,
        tmnxOamVccvTrTgStaticCtlAgi,
        tmnxOamVccvTrTgStaticCtlSaiiAcId,
        tmnxOamVccvTrTgStaticCtlSaiiGlbl,
        tmnxOamVccvTrTgStaticCtlSaiiNode,
        tmnxOamVccvTrTgStaticCtlTaiiAcId,
        tmnxOamVccvTrTgStaticCtlTaiiGlbl,
        tmnxOamVccvTrTgStaticCtlTaiiNode
    }
    STATUS      current
    DESCRIPTION
        "The group of additional objects supporting management of OAM trace
         route tests on Nokia SROS series systems running release 12.0."
    ::= { tmnxOamTrGroups 39 }

tmnxOamTrObsoleteV13v0Group      OBJECT-GROUP
    OBJECTS     {
        tmnxOamLspTrMapDSIPv4Addr,
        tmnxOamLspTrMapDSIfAddr,
        tmnxOamTrProbeHistoryRouterID
    }
    STATUS      current
    DESCRIPTION
        "The group of objects supporting management of OAM trace route
         operations on Nokia SR series systems that were made obsolete in
         release 13.0."
    ::= { tmnxOamTrGroups 40 }

tmnxOamTrV13v0Group              OBJECT-GROUP
    OBJECTS     {
        tmnxOamLspTrMapDsEgrIfNum,
        tmnxOamLspTrMapDsIfAddress,
        tmnxOamLspTrMapDsIfAddressType,
        tmnxOamLspTrMapDsIngIfNum,
        tmnxOamLspTrMapDsIpAddress,
        tmnxOamLspTrMapDsIpAddressType,
        tmnxOamTrProbeHistoryNtwrkIfName
    }
    STATUS      current
    DESCRIPTION
        "The group of additional objects supporting management of OAM trace
         route tests on Nokia SROS series systems running release 13.0."
    ::= { tmnxOamTrGroups 41 }

tmnxOamTrObsoleteV14v0Group      OBJECT-GROUP
    OBJECTS     {
        tmnxOamLTtraceAutoStorageType,
        tmnxOamTrCtlDescr,
        tmnxOamTrCtlStorageType
    }
    STATUS      current
    DESCRIPTION
        "The group of objects supporting management of OAM trace route
         operations on Nokia SR series systems that were made obsolete in SROS
         release 14.0."
    ::= { tmnxOamTrGroups 42 }

tmnxOamTrV15v0Group              OBJECT-GROUP
    OBJECTS     {
        tmnxOamEthCfmTrCtlRemoteMepId,
        tmnxOamLspTrCtlIgpInstance
    }
    STATUS      current
    DESCRIPTION
        "The group of additional objects supporting management of OAM trace
         route tests on Nokia SROS series systems running release 15.0."
    ::= { tmnxOamTrGroups 44 }

tmnxOamSaaConformance            OBJECT IDENTIFIER ::= { tmnxOamTestConformance 3 }

tmnxOamSaaCompliances            OBJECT IDENTIFIER ::= { tmnxOamSaaConformance 1 }

tmnxOamSaaV3v0Compliance         MODULE-COMPLIANCE
    STATUS      obsolete
    DESCRIPTION
        "The compliance statement for management of OAM SAA tests on Nokia SROS
         series systems."
    MODULE
        MANDATORY-GROUPS {
            tmnxOamSaaGeneralV3v0Group,
            tmnxOamSaaThresholdV3v0Group,
            tmnxOamSaaNotificationV3v0Group
        }
    ::= { tmnxOamSaaCompliances 1 }

tmnxOamSaaV7v0Compliance         MODULE-COMPLIANCE
    STATUS      obsolete
    DESCRIPTION
        "The compliance statement for management of OAM SAA tests on Nokia SROS
         series systems."
    MODULE
        MANDATORY-GROUPS {
            tmnxOamSaaGeneralV7v0Group,
            tmnxOamSaaThresholdV3v0Group,
            tmnxOamSaaNotificationV3v0Group
        }
    ::= { tmnxOamSaaCompliances 2 }

tmnxOamSaaV8v0Compliance         MODULE-COMPLIANCE
    STATUS      obsolete
    DESCRIPTION
        "The compliance statement for management of OAM SAA tests on Nokia SROS
         series systems."
    MODULE
        MANDATORY-GROUPS {
            tmnxOamSaaGeneralV7v0Group,
            tmnxOamSaaGeneralV8v0Group,
            tmnxOamSaaThresholdV3v0Group,
            tmnxOamSaaNotificationV3v0Group
        }
    ::= { tmnxOamSaaCompliances 3 }

tmnxOamSaaV10v0Compliance        MODULE-COMPLIANCE
    STATUS      current
    DESCRIPTION
        "The compliance statement for management of OAM SAA tests on Nokia SROS
         series systems."
    MODULE
        MANDATORY-GROUPS {
            tmnxOamSaaGeneralV7v0Group,
            tmnxOamSaaGeneralV8v0Group,
            tmnxOamSaaThresholdV3v0Group,
            tmnxOamSaaNotificationV3v0Group,
            tmnxOamSaaGeneralV10v0Group
        }
    ::= { tmnxOamSaaCompliances 4 }

tmnxOamSaaGroups                 OBJECT IDENTIFIER ::= { tmnxOamSaaConformance 2 }

tmnxOamSaaGeneralV3v0Group       OBJECT-GROUP
    OBJECTS     {
        tmnxOamSaaCtlRowStatus,
        tmnxOamSaaCtlStorageType,
        tmnxOamSaaCtlLastChanged,
        tmnxOamSaaCtlAdminStatus,
        tmnxOamSaaCtlTestMode,
        tmnxOamSaaCtlDescr,
        tmnxOamSaaCtlRuns,
        tmnxOamSaaCtlFailures,
        tmnxOamSaaCtlLastRunResult
    }
    STATUS      obsolete
    DESCRIPTION
        "The group of objects supporting management of OAM SAA test general
         capabilities on Nokia SROS series systems."
    ::= { tmnxOamSaaGroups 1 }

tmnxOamSaaThresholdV3v0Group     OBJECT-GROUP
    OBJECTS     {
        tmnxOamSaaTRowStatus,
        tmnxOamSaaTLastChanged,
        tmnxOamSaaTThreshold,
        tmnxOamSaaTValue,
        tmnxOamSaaTLastSent,
        tmnxOamSaaTTestMode,
        tmnxOamSaaTTestRunIndex
    }
    STATUS      current
    DESCRIPTION
        "The group of objects supporting management of OAM Trace Route SAA test
         thresholds on Nokia SROS series systems 3.0R1."
    ::= { tmnxOamSaaGroups 2 }

tmnxOamSaaNotificationV3v0Group  NOTIFICATION-GROUP
    NOTIFICATIONS {
        tmnxOamSaaThreshold
    }
    STATUS      current
    DESCRIPTION
        "The group of notifications supporting the OAM Trace Route test feature
         on Nokia SROS series systems."
    ::= { tmnxOamSaaGroups 3 }

tmnxOamSaaGeneralV7v0Group       OBJECT-GROUP
    OBJECTS     {
        tmnxOamSaaCtlRowStatus,
        tmnxOamSaaCtlLastChanged,
        tmnxOamSaaCtlAdminStatus,
        tmnxOamSaaCtlTestMode,
        tmnxOamSaaCtlDescr,
        tmnxOamSaaCtlRuns,
        tmnxOamSaaCtlFailures,
        tmnxOamSaaCtlLastRunResult,
        tmnxOamSaaCtlAcctPolicyId,
        tmnxOamSaaCtlSuppressAccounting
    }
    STATUS      current
    DESCRIPTION
        "The group of objects supporting management of OAM SAA test general
         capabilities on Nokia SROS series systems 7.0 release, and still
         supported in the latest SROS release."
    ::= { tmnxOamSaaGroups 4 }

tmnxOamSaaGeneralV8v0Group       OBJECT-GROUP
    OBJECTS     {
        tmnxOamSaaCtlContinuous
    }
    STATUS      current
    DESCRIPTION
        "The group of additional objects supporting management of OAM SAA test
         general capabilities on Nokia SROS series systems 8.0 release."
    ::= { tmnxOamSaaGroups 5 }

tmnxOamSaaGeneralV10v0Group      OBJECT-GROUP
    OBJECTS     {
        tmnxOamSaaCtlKeepProbeHistoryAdm,
        tmnxOamSaaCtlKeepProbeHistoryOpr
    }
    STATUS      current
    DESCRIPTION
        "The group of additional objects supporting management of OAM SAA test
         general capabilities on Nokia SROS Release 10.0 systems."
    ::= { tmnxOamSaaGroups 6 }

tmnxOamSaaObsoleteV14v0Group     OBJECT-GROUP
    OBJECTS     {
        tmnxOamSaaCtlStorageType
    }
    STATUS      current
    DESCRIPTION
        "The group of objects supporting management of OAM SAA operations on
         Nokia SR series systems that were made obsolete in SROS release 14.0."
    ::= { tmnxOamSaaGroups 7 }

tmnxOamMobGatewayConformance     OBJECT IDENTIFIER ::= { tmnxOamTestConformance 4 }

tmnxOamGeneralConformance        OBJECT IDENTIFIER ::= { tmnxOamTestConformance 5 }

tmnxOamGeneralCompliances        OBJECT IDENTIFIER ::= { tmnxOamGeneralConformance 1 }

tmnxOamGeneralV8v0Compliance     MODULE-COMPLIANCE
    STATUS      obsolete
    DESCRIPTION
        "The compliance statement for management of OAM general capabilities on
         Nokia SROS series systems for Release 8.0."
    MODULE
        MANDATORY-GROUPS {
            tmnxOamGeneralV8v0Group
        }
    ::= { tmnxOamGeneralCompliances 1 }

tmnxOamGeneralV10v0Compliance    MODULE-COMPLIANCE
    STATUS      current
    DESCRIPTION
        "The compliance statement for management of OAM general capabilities on
         Nokia SROS series systems for Release 10.0."
    MODULE
        MANDATORY-GROUPS {
            tmnxOamGeneralV8v0Group,
            tmnxOamGeneralV10v0Group
        }
    ::= { tmnxOamGeneralCompliances 2 }

tmnxOamGeneralV11v0Compliance    MODULE-COMPLIANCE
    STATUS      current
    DESCRIPTION
        "The compliance statement for management of OAM general capabilities
         added in Nokia SROS series systems for Release 11.0."
    MODULE
        MANDATORY-GROUPS {
            tmnxOamGeneralV11v0Group
        }
    ::= { tmnxOamGeneralCompliances 3 }

tmnxOamGeneralV14v0Compliance    MODULE-COMPLIANCE
    STATUS      current
    DESCRIPTION
        "The compliance statement for management of OAM general capabilities
         added in Nokia SROS series systems for Release 14.0."
    MODULE
        MANDATORY-GROUPS {
            tmnxOamGeneralV14v0Group
        }
    ::= { tmnxOamGeneralCompliances 6 }

tmnxOamGeneralGroups             OBJECT IDENTIFIER ::= { tmnxOamGeneralConformance 2 }

tmnxOamGeneralV8v0Group          OBJECT-GROUP
    OBJECTS     {
        tmnxOamMplsPduTimeStampFormat
    }
    STATUS      current
    DESCRIPTION
        "The group of objects supporting management of OAM test general
         capabilities on Nokia SROS systems, release 8.0 R4."
    ::= { tmnxOamGeneralGroups 1 }

tmnxOamGeneralV10v0Group         OBJECT-GROUP
    OBJECTS     {
        tmnxOamSysPerfOprLimitTx,
        tmnxOamSysPerfCfgLimitTx,
        tmnxOamSysPerfCfgTotalTx,
        tmnxOamSysPerfLastClearedTime,
        tmnxOamSysPerfLocalTestTx,
        tmnxOamSysPerfRemoteTestRx,
        tmnxOamSysPerfReqTypeLocalTestTx,
        tmnxOamSysPerfReqTypeRemoteTstRx,
        tmnxOamSysSessionLimit,
        tmnxOamSysSessionCount
    }
    STATUS      current
    DESCRIPTION
        "The group of objects supporting management of OAM test general
         capabilities on Nokia SROS systems, release 10.0."
    ::= { tmnxOamGeneralGroups 2 }

tmnxOamGeneralV11v0Group         OBJECT-GROUP
    OBJECTS     {
        tmnxOamMplsEchoDownstreamMapTlv
    }
    STATUS      current
    DESCRIPTION
        "The group of additional objects supporting management of general OAM
         test capabilities on Nokia SROS systems, release 11.0."
    ::= { tmnxOamGeneralGroups 3 }

tmnxOamGeneralV14v0Group         OBJECT-GROUP
    OBJECTS     {
        tmnxOamSysBgIcmpBrgSessionCount,
        tmnxOamSysBgIcmpBrgSessionLimit
    }
    STATUS      current
    DESCRIPTION
        "The group of additional objects supporting management of general OAM
         test capabilities on Nokia SROS systems, release 14.0."
    ::= { tmnxOamGeneralGroups 6 }

tmnxOamTestNotifications         OBJECT IDENTIFIER ::= { tmnxSRNotifyPrefix 11 }

tmnxOamPingNotifyPrefix          OBJECT IDENTIFIER ::= { tmnxOamTestNotifications 1 }

tmnxOamPingNotifications         OBJECT IDENTIFIER ::= { tmnxOamPingNotifyPrefix 0 }

tmnxOamPingProbeFailed           NOTIFICATION-TYPE
    OBJECTS     {
        tmnxOamPingCtlTargetIpAddress,
        tmnxOamPingResultsOperStatus,
        tmnxOamPingResultsMinRtt,
        tmnxOamPingResultsMaxRtt,
        tmnxOamPingResultsAverageRtt,
        tmnxOamPingResultsRttSumOfSquares,
        tmnxOamPingResultsMtuResponseSize,
        tmnxOamPingResultsSvcPing,
        tmnxOamPingResultsProbeResponses,
        tmnxOamPingResultsSentProbes,
        tmnxOamPingResultsLastGoodProbe
    }
    STATUS      obsolete
    DESCRIPTION
        "Generated when a probe failure is detected when the
         corresponding tmnxOamPingCtlTrapGeneration object is set to
         probeFailure(0) subject to the value of
         tmnxOamPingCtlTrapProbeFailureFilter.  The object
         tmnxOamPingCtlTrapProbeFailureFilter can be used to specify the
         number of successive probe failures that are required
         before this notification can be generated."
    ::= { tmnxOamPingNotifications 1 }

tmnxOamPingTestFailed            NOTIFICATION-TYPE
    OBJECTS     {
        tmnxOamPingCtlTargetIpAddress,
        tmnxOamPingResultsOperStatus,
        tmnxOamPingResultsMinRtt,
        tmnxOamPingResultsMaxRtt,
        tmnxOamPingResultsAverageRtt,
        tmnxOamPingResultsRttSumOfSquares,
        tmnxOamPingResultsMtuResponseSize,
        tmnxOamPingResultsSvcPing,
        tmnxOamPingResultsProbeResponses,
        tmnxOamPingResultsSentProbes,
        tmnxOamPingResultsLastGoodProbe
    }
    STATUS      obsolete
    DESCRIPTION
        "Generated when a ping test is determined to have failed
         when the corresponding tmnxOamPingCtlTrapGeneration object is
         set to testFailure(1).  In this instance
         tmnxOamPingCtlTrapTestFailureFilter should specify the number of
         probes in a test required to have failed in order to
         consider the test as failed."
    ::= { tmnxOamPingNotifications 2 }

tmnxOamPingTestCompleted         NOTIFICATION-TYPE
    OBJECTS     {
        tmnxOamPingCtlTargetIpAddress,
        tmnxOamPingResultsOperStatus,
        tmnxOamPingResultsMinRtt,
        tmnxOamPingResultsMaxRtt,
        tmnxOamPingResultsAverageRtt,
        tmnxOamPingResultsRttSumOfSquares,
        tmnxOamPingResultsMtuResponseSize,
        tmnxOamPingResultsSvcPing,
        tmnxOamPingResultsProbeResponses,
        tmnxOamPingResultsSentProbes,
        tmnxOamPingResultsLastGoodProbe
    }
    STATUS      obsolete
    DESCRIPTION
        "Generated at the completion of a ping test when the corresponding
         tmnxOamPingCtlTrapGeneration object is set to testCompletion(2)."
    ::= { tmnxOamPingNotifications 3 }

tmnxOamPingProbeFailedV2         NOTIFICATION-TYPE
    OBJECTS     {
        tmnxOamPingCtlTgtAddrType,
        tmnxOamPingCtlTgtAddress,
        tmnxOamPingResultsOperStatus,
        tmnxOamPingResultsMinRtt,
        tmnxOamPingResultsMaxRtt,
        tmnxOamPingResultsAverageRtt,
        tmnxOamPingResultsRttSumOfSquares,
        tmnxOamPingResultsMtuResponseSize,
        tmnxOamPingResultsSvcPing,
        tmnxOamPingResultsProbeResponses,
        tmnxOamPingResultsSentProbes,
        tmnxOamPingResultsLastGoodProbe
    }
    STATUS      obsolete
    DESCRIPTION
        "Generated when a probe failure is detected when the
         corresponding tmnxOamPingCtlTrapGeneration object is set to
         probeFailure(0) subject to the value of
         tmnxOamPingCtlTrapProbeFailureFilter.  The object
         tmnxOamPingCtlTrapProbeFailureFilter can be used to specify the
         number of successive probe failures that are required
         before this notification can be generated."
    ::= { tmnxOamPingNotifications 4 }

tmnxOamPingTestFailedV2          NOTIFICATION-TYPE
    OBJECTS     {
        tmnxOamPingCtlTgtAddrType,
        tmnxOamPingCtlTgtAddress,
        tmnxOamPingResultsOperStatus,
        tmnxOamPingResultsMinRtt,
        tmnxOamPingResultsMaxRtt,
        tmnxOamPingResultsAverageRtt,
        tmnxOamPingResultsRttSumOfSquares,
        tmnxOamPingResultsMtuResponseSize,
        tmnxOamPingResultsSvcPing,
        tmnxOamPingResultsProbeResponses,
        tmnxOamPingResultsSentProbes,
        tmnxOamPingResultsLastGoodProbe
    }
    STATUS      obsolete
    DESCRIPTION
        "Generated when a ping test is determined to have failed
         when the corresponding tmnxOamPingCtlTrapGeneration object is
         set to testFailure(1).  In this instance
         tmnxOamPingCtlTrapTestFailureFilter should specify the number of
         probes in a test required to have failed in order to
         consider the test as failed."
    ::= { tmnxOamPingNotifications 5 }

tmnxOamPingTestCompletedV2       NOTIFICATION-TYPE
    OBJECTS     {
        tmnxOamPingCtlTgtAddrType,
        tmnxOamPingCtlTgtAddress,
        tmnxOamPingResultsOperStatus,
        tmnxOamPingResultsMinRtt,
        tmnxOamPingResultsMaxRtt,
        tmnxOamPingResultsAverageRtt,
        tmnxOamPingResultsRttSumOfSquares,
        tmnxOamPingResultsMtuResponseSize,
        tmnxOamPingResultsSvcPing,
        tmnxOamPingResultsProbeResponses,
        tmnxOamPingResultsSentProbes,
        tmnxOamPingResultsLastGoodProbe
    }
    STATUS      obsolete
    DESCRIPTION
        "Generated at the completion of a ping test when the corresponding
         tmnxOamPingCtlTrapGeneration object is set to testCompletion(2)."
    ::= { tmnxOamPingNotifications 6 }

tmnxAncpLoopbackTestCompleted    NOTIFICATION-TYPE
    OBJECTS     {
        tmnxOamAncpHistoryAncpString
    }
    STATUS      current
    DESCRIPTION
        "This Notification is sent whenever a ANCP loopback is finished for
         which a notification was explicitly requested."
    ::= { tmnxOamPingNotifications 7 }

tmnxOamPingProbeFailedV3         NOTIFICATION-TYPE
    OBJECTS     {
        tmnxOamPingCtlTgtAddrType,
        tmnxOamPingCtlTgtAddress,
        tmnxOamPingResultsOperStatus,
        tmnxOamPingResultsMinRtt,
        tmnxOamPingResultsMaxRtt,
        tmnxOamPingResultsAverageRtt,
        tmnxOamPingResultsRttSumOfSquares,
        tmnxOamPingResultsRttOFSumSquares,
        tmnxOamPingResultsMtuResponseSize,
        tmnxOamPingResultsSvcPing,
        tmnxOamPingResultsProbeResponses,
        tmnxOamPingResultsSentProbes,
        tmnxOamPingResultsLastGoodProbe
    }
    STATUS      current
    DESCRIPTION
        "[CAUSE] The tmnxOamPingProbeFailedV3 notification is sent at the end
         of an OAM or SAA test run, when a sufficient number of successive
         probes failed.

         The notification is sent if both of the following conditions are met:
         1.  The 'probeFailure(0)' bit of the tmnxOamPingCtlTrapGeneration BITS
             object is enabled, AND
         2.  The test run includes at least one occurrence of N successive probe
             failures, where N is configured using
             tmnxOamPingCtlTrapProbeFailureFilter.

         This notification is sent at most once per test run.

         [EFFECT] Informational.  The probe failures may indicate a problem with
         live traffic flow.

         [RECOVERY] Investigate the cause of the probe failures."
    ::= { tmnxOamPingNotifications 8 }

tmnxOamPingTestFailedV3          NOTIFICATION-TYPE
    OBJECTS     {
        tmnxOamPingCtlTgtAddrType,
        tmnxOamPingCtlTgtAddress,
        tmnxOamPingResultsOperStatus,
        tmnxOamPingResultsMinRtt,
        tmnxOamPingResultsMaxRtt,
        tmnxOamPingResultsAverageRtt,
        tmnxOamPingResultsRttSumOfSquares,
        tmnxOamPingResultsRttOFSumSquares,
        tmnxOamPingResultsMtuResponseSize,
        tmnxOamPingResultsSvcPing,
        tmnxOamPingResultsProbeResponses,
        tmnxOamPingResultsSentProbes,
        tmnxOamPingResultsLastGoodProbe
    }
    STATUS      current
    DESCRIPTION
        "[CAUSE] The tmnxOamPingTestFailedV3 notification is sent at the end of
         an OAM or SAA test run, when a sufficient number of probes failed.

         The notification is sent if both of the following conditions are met:
         1.  The 'testFailure(1)' bit of the tmnxOamPingCtlTrapGeneration BITS
             object is enabled, AND
         2.  The test run had at least N probe failures, where N is configured
             using tmnxOamPingCtlTrapTestFailureFilter.

         This notification is sent at most once per test run.

         [EFFECT] Informational.  The probe failures may indicate a problem with
         live traffic flow.

         [RECOVERY] Investigate the cause of the probe failures."
    ::= { tmnxOamPingNotifications 9 }

tmnxOamPingTestCompletedV3       NOTIFICATION-TYPE
    OBJECTS     {
        tmnxOamPingCtlTgtAddrType,
        tmnxOamPingCtlTgtAddress,
        tmnxOamPingResultsOperStatus,
        tmnxOamPingResultsMinRtt,
        tmnxOamPingResultsMaxRtt,
        tmnxOamPingResultsAverageRtt,
        tmnxOamPingResultsRttSumOfSquares,
        tmnxOamPingResultsRttOFSumSquares,
        tmnxOamPingResultsMtuResponseSize,
        tmnxOamPingResultsSvcPing,
        tmnxOamPingResultsProbeResponses,
        tmnxOamPingResultsSentProbes,
        tmnxOamPingResultsLastGoodProbe
    }
    STATUS      current
    DESCRIPTION
        "Generated at the completion of a ping test when the corresponding
         tmnxOamPingCtlTrapGeneration object is set to testCompletion(2)."
    ::= { tmnxOamPingNotifications 10 }

tmnxOamTraceRouteNotifyPrefix    OBJECT IDENTIFIER ::= { tmnxOamTestNotifications 2 }

tmnxOamTraceRouteNotifications   OBJECT IDENTIFIER ::= { tmnxOamTraceRouteNotifyPrefix 0 }

tmnxOamTrPathChange              NOTIFICATION-TYPE
    OBJECTS     {
        tmnxOamTrCtlTestMode,
        tmnxOamTrCtlLastRunResult,
        tmnxOamTrResultsOperStatus
    }
    STATUS      current
    DESCRIPTION
        "The path to a target has changed."
    ::= { tmnxOamTraceRouteNotifications 1 }

tmnxOamTrTestFailed              NOTIFICATION-TYPE
    OBJECTS     {
        tmnxOamTrCtlTestMode,
        tmnxOamTrCtlLastRunResult,
        tmnxOamTrResultsOperStatus
    }
    STATUS      current
    DESCRIPTION
        "The OAM trace route test failed to complete successfully."
    ::= { tmnxOamTraceRouteNotifications 2 }

tmnxOamTrTestCompleted           NOTIFICATION-TYPE
    OBJECTS     {
        tmnxOamTrCtlTestMode,
        tmnxOamTrCtlLastRunResult,
        tmnxOamTrResultsOperStatus
    }
    STATUS      current
    DESCRIPTION
        "The OAM trace route test has just been completed."
    ::= { tmnxOamTraceRouteNotifications 3 }

tmnxOamLdpTtraceAutoDiscState    NOTIFICATION-TYPE
    OBJECTS     {
        tmnxOamLTtraceAutoDiscoveryState
    }
    STATUS      current
    DESCRIPTION
        "The tmnxOamLdpTtraceAutoDiscState notification is generated when the
         discovery state of the 'Auto LDP Tree Trace entity' represented by
         tmnxOamLTtraceAutoDiscoveryState has been changed."
    ::= { tmnxOamTraceRouteNotifications 4 }

tmnxOamLdpTtraceFecProbeState    NOTIFICATION-TYPE
    OBJECTS     {
        tmnxOamLTtraceFecProbeState,
        tmnxOamLTtraceFecDisPaths,
        tmnxOamLTtraceFecFailedProbes,
        tmnxOamLTtraceFecSendErrProbes
    }
    STATUS      current
    DESCRIPTION
        "The tmnxOamLdpTtraceFecProbeState notification is generated when the
         probe state of the 'auto discovered FEC' has been changed."
    ::= { tmnxOamTraceRouteNotifications 5 }

tmnxOamLdpTtraceFecDisStatus     NOTIFICATION-TYPE
    OBJECTS     {
        tmnxOamLTtraceFecDisStatusBits,
        tmnxOamLTtraceFecDisPaths
    }
    STATUS      current
    DESCRIPTION
        "The tmnxOamLdpTtraceFecDisStatus notification is generated when
         the discovery status BITS or the number of discovered paths of the
         'auto discovered FEC' has been changed.  Note that the changes are
         evaluated at the end of a FEC discovery."
    ::= { tmnxOamTraceRouteNotifications 6 }

tmnxOamLdpTtraceFecPFailUpdate   NOTIFICATION-TYPE
    OBJECTS     {
        tmnxOamLTtraceFecProbeState,
        tmnxOamLTtraceFecDisPaths,
        tmnxOamLTtraceFecFailedProbes,
        tmnxOamLTtraceFecSendErrProbes
    }
    STATUS      current
    DESCRIPTION
        "The tmnxOamLdpTtraceFecPFailUpdate notification is generated when
         there is a probe state change in any of the relevant discovered paths
         while the overall FEC probe state, tmnxOamLTtraceFecProbeState is in
         'partially failed' state."
    ::= { tmnxOamTraceRouteNotifications 7 }

tmnxOamSaaNotifyPrefix           OBJECT IDENTIFIER ::= { tmnxOamTestNotifications 3 }

tmnxOamSaaNotifications          OBJECT IDENTIFIER ::= { tmnxOamSaaNotifyPrefix 0 }

tmnxOamSaaThreshold              NOTIFICATION-TYPE
    OBJECTS     {
        tmnxOamSaaTThreshold,
        tmnxOamSaaTValue,
        tmnxOamSaaCtlTestMode,
        tmnxOamSaaCtlLastRunResult,
        tmnxOamSaaTTestRunIndex
    }
    STATUS      current
    DESCRIPTION
        "Generated at the completion of an SAA OAM trace route test when a
         threshold has been crossed for a results statistic."
    ::= { tmnxOamSaaNotifications 1 }

END
