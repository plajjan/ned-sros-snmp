TIMETRA-IGMP-MIB DEFINITIONS ::= BEGIN

IMPORTS
    InterfaceIndex, InterfaceIndexOrZero
                                                         FROM IF-MIB
    InetAddress, InetAddressType
                                                         FROM INET-ADDRESS-MIB
    MODULE-COMPLIANCE, NOTIFICATION-GROUP,
    OBJECT-GROUP
                                                         FROM SNMPv2-CONF
    Counter32, Gauge32, Integer32,
    IpAddress, MODULE-IDENTITY,
    NOTIFICATION-TYPE, OBJECT-TYPE,
    Unsigned32
                                                         FROM SNMPv2-SMI
    DisplayString, MacAddress, RowStatus,
    TEXTUAL-CONVENTION, TimeInterval,
    TimeStamp, TruthValue
                                                         FROM SNMPv2-TC
    timetraSRMIBModules, tmnxSRConfs,
    tmnxSRNotifyPrefix, tmnxSRObjs
                                                         FROM TIMETRA-GLOBAL-MIB
    tmnxMcacLagPortsDown, tmnxMcacLevelId
                                                         FROM TIMETRA-MCAST-CAC-MIB
    sapEncapValue, sapPortId
                                                         FROM TIMETRA-SAP-MIB
    TNamedItem, TPolicyStatementNameOrEmpty,
    TmnxAdminState, TmnxIgmpGroupFilterMode,
    TmnxIgmpGroupType, TmnxOperState,
    TmnxPppoeSessionId, TmnxServId,
    TmnxSubIdentStringOrEmpty,
    TmnxVRtrIDOrZero,
    VRtrIgmpHostMcRDstStatType
                                                         FROM TIMETRA-TC-MIB
    vRtrID, vRtrIfIndex
                                                         FROM TIMETRA-VRTR-MIB
    ;

timetraIgmpMIBModule             MODULE-IDENTITY
    LAST-UPDATED "201701010000Z"
    ORGANIZATION "Nokia"
    CONTACT-INFO
        "Nokia SROS Support
         Web: http://www.nokia.com"
    DESCRIPTION
        "This document is the SNMP MIB module to manage and provision the
         extensions to the IGMP routing protocol for the Nokia SROS device.

         Copyright 2003-2017 Nokia.  All rights reserved.
         Reproduction of this document is authorized on the condition that
         the foregoing copyright notice is included.

         This SNMP MIB module (Specification) embodies Nokia's
         proprietary intellectual property.  Nokia retains
         all title and ownership in the Specification, including any
         revisions.

         Nokia grants all interested parties a non-exclusive license to use and
         distribute an unmodified copy of this Specification in connection with
         management of Nokia products, and without fee, provided this copyright
         notice and license appear on all copies.

         This Specification is supplied 'as is', and Nokia makes no warranty,
         either express or implied, as to the use, operation, condition, or
         performance of the Specification."

    REVISION    "201701010000Z"
    DESCRIPTION
        "Rev 15.0               1 Jan 2017 00:00
         15.0 release of the TIMETRA-IGMP-MIB."

    REVISION    "201601010000Z"
    DESCRIPTION
        "Rev 14.0               1 Jan 2016 00:00
         14.0 release of the TIMETRA-IGMP-MIB."

    REVISION    "201401010000Z"
    DESCRIPTION
        "Rev 12.0               1 Jan 2014 00:00
         12.0 release of the TIMETRA-IGMP-MIB."

    REVISION    "201102010000Z"
    DESCRIPTION
        "Rev 9.0                1 Feb 2011 00:00
         9.0 release of the TIMETRA-IGMP-MIB."

    REVISION    "200902280000Z"
    DESCRIPTION
        "Rev 7.0                28 Feb 2009 00:00
         7.0 release of the TIMETRA-IGMP-MIB."

    REVISION    "200807010000Z"
    DESCRIPTION
        "Rev 6.1                01 Jul 2008 00:00
         6.1 release of the TIMETRA-IGMP-MIB."

    REVISION    "200801010000Z"
    DESCRIPTION
        "Rev 6.0                01 Jan 2008 00:00
         6.0 release of the TIMETRA-IGMP-MIB."

    REVISION    "200701010000Z"
    DESCRIPTION
        "Rev 5.0                01 Jan 2007 00:00
         5.0 release of the TIMETRA-IGMP-MIB."

    REVISION    "200603230000Z"
    DESCRIPTION
        "Rev 4.0                23 Mar 2006 00:00
         4.0 release of the TIMETRA-IGMP-MIB."

    REVISION    "200508310000Z"
    DESCRIPTION
        "Rev 3.0                31 Aug 2005 00:00
         3.0 release of the TIMETRA-IGMP-MIB."

    REVISION    "200501240000Z"
    DESCRIPTION
        "Rev 2.1                24 Jan 2005 00:00
         2.1 release of the TIMETRA-IGMP-MIB."

    REVISION    "200401150000Z"
    DESCRIPTION
        "Rev 2.0                15 Jan 2004 00:00
         2.0 release of the TIMETRA-IGMP-MIB."

    REVISION    "200308150000Z"
    DESCRIPTION
        "Rev 1.2                15 Aug 2003 00:00
         1.2 release of the TIMETRA-IGMP-MIB."

    ::= { timetraSRMIBModules 23 }

IgmpGrpItfOperState              ::= TEXTUAL-CONVENTION
    STATUS      current
    DESCRIPTION
        "The IgmpGrpItfOperState data type is an enumerated integer that
         describes the values used to identify the current operational state of
         an IGMP Group Interface."
    SYNTAX      INTEGER {
        unknown        (1),
        noIgmpOnGrpItf (2),
        grpItfDown     (3),
        inService      (4),
        notFwding      (5)
    }

tmnxIgmpObjs                     OBJECT IDENTIFIER ::= { tmnxSRObjs 23 }

vRtrIgmpProtocolObjs             OBJECT IDENTIFIER ::= { tmnxIgmpObjs 1 }

vRtrIgmpGeneralTable             OBJECT-TYPE
    SYNTAX      SEQUENCE OF VRtrIgmpGeneralEntry
    MAX-ACCESS  not-accessible
    STATUS      current
    DESCRIPTION
        "The vRtrIgmpGeneralTable contains objects for general control and
         management of an IGMP protocol instance within a virtual router."
    ::= { vRtrIgmpProtocolObjs 1 }

vRtrIgmpGeneralEntry             OBJECT-TYPE
    SYNTAX      VRtrIgmpGeneralEntry
    MAX-ACCESS  not-accessible
    STATUS      current
    DESCRIPTION
        "Each row entry represents an instance of the IGMP protocol running
         within a virtual router.  Entries in this table cannot be
         created and deleted via SNMP SET operations.  An entry in this table
         is created by the agent when vRtrIgmpStatus in the vRtrConfTable is
         set to 'create'.  The entry is destroyed when vRtrIgmpStatus is set
         to 'delete'"
    INDEX       { vRtrID }
    ::= { vRtrIgmpGeneralTable 1 }

VRtrIgmpGeneralEntry             ::= SEQUENCE
{
    vRtrIgmpGenQueryInterval         Unsigned32,
    vRtrIgmpGenLastMembQueryIntvl    Unsigned32,
    vRtrIgmpGenQueryResponseIntvl    Unsigned32,
    vRtrIgmpGenRobustCount           Unsigned32,
    vRtrIgmpGenLastChange            TimeStamp,
    vRtrIgmpGenAdminState            TmnxAdminState,
    vRtrIgmpGenOperState             TmnxOperState,
    vRtrIgmpGenGrpIfQuerySrcIp       IpAddress
}

vRtrIgmpGenQueryInterval         OBJECT-TYPE
    SYNTAX      Unsigned32 (2..1024)
    UNITS       "seconds"
    MAX-ACCESS  read-create
    STATUS      current
    DESCRIPTION
        "vRtrIgmpGenQueryInterval is the frequency at which IGMP Host-Query
         packets are transmitted."
    DEFVAL      { 125 }
    ::= { vRtrIgmpGeneralEntry 1 }

vRtrIgmpGenLastMembQueryIntvl    OBJECT-TYPE
    SYNTAX      Unsigned32 (1..1023)
    UNITS       "seconds"
    MAX-ACCESS  read-create
    STATUS      current
    DESCRIPTION
        "vRtrIgmpGenLastMembQueryIntvl is the Max Response Time
         inserted into Group-Specific Queries sent in response to
         Leave Group messages, and is also the amount of time between
         Group-Specific Query messages.  This value may be tuned to
         modify the leave latency of the network.  A reduced value
         results in reduced time to detect the loss of the last
         member of a group."
    DEFVAL      { 1 }
    ::= { vRtrIgmpGeneralEntry 2 }

vRtrIgmpGenQueryResponseIntvl    OBJECT-TYPE
    SYNTAX      Unsigned32 (1..1023)
    UNITS       "seconds"
    MAX-ACCESS  read-create
    STATUS      current
    DESCRIPTION
        "The maximum query response time advertised in IGMPv2 queries."
    DEFVAL      { 10 }
    ::= { vRtrIgmpGeneralEntry 3 }

vRtrIgmpGenRobustCount           OBJECT-TYPE
    SYNTAX      Unsigned32 (2..10)
    MAX-ACCESS  read-create
    STATUS      current
    DESCRIPTION
        "The Robustness Variable allows tuning for the expected
         packet loss on a subnet.  If a subnet is expected to be
         lossy, the Robustness Variable may be increased.  IGMP is
         robust to (Robustness Variable-1) packet losses."
    DEFVAL      { 2 }
    ::= { vRtrIgmpGeneralEntry 4 }

vRtrIgmpGenLastChange            OBJECT-TYPE
    SYNTAX      TimeStamp
    MAX-ACCESS  read-only
    STATUS      current
    DESCRIPTION
        "The sysUpTime when this row was last modified."
    ::= { vRtrIgmpGeneralEntry 5 }

vRtrIgmpGenAdminState            OBJECT-TYPE
    SYNTAX      TmnxAdminState
    MAX-ACCESS  read-create
    STATUS      current
    DESCRIPTION
        "When vRtrIgmpGenAdminState is set to 'inService', the agent attempts
         to enable the IGMP protocol instance on this virtual router.

         When vRtrIgmpGenAdminState is set to 'outOfService', the agent
         attempts to disable the IGMP protocol instance on this router."
    DEFVAL      { inService }
    ::= { vRtrIgmpGeneralEntry 6 }

vRtrIgmpGenOperState             OBJECT-TYPE
    SYNTAX      TmnxOperState
    MAX-ACCESS  read-only
    STATUS      current
    DESCRIPTION
        "vRtrIgmpGenOperState indicates the current operating state of this
         IGMP protocol instance on this router."
    ::= { vRtrIgmpGeneralEntry 7 }

vRtrIgmpGenGrpIfQuerySrcIp       OBJECT-TYPE
    SYNTAX      IpAddress
    MAX-ACCESS  read-create
    STATUS      current
    DESCRIPTION
        "The value of vRtrIgmpGenGrpIfQuerySrcIp specifies the source IP
         address used when generating IGMP queries on group interfaces."
    DEFVAL      { 0 }
    ::= { vRtrIgmpGeneralEntry 8 }

vRtrIgmpGrpSrcTable              OBJECT-TYPE
    SYNTAX      SEQUENCE OF VRtrIgmpGrpSrcEntry
    MAX-ACCESS  not-accessible
    STATUS      current
    DESCRIPTION
        "The table listing the IP multicast sources corresponding to the IP
         multicast groups. This table represents the global IGMP source, group
         database."
    ::= { vRtrIgmpProtocolObjs 2 }

vRtrIgmpGrpSrcEntry              OBJECT-TYPE
    SYNTAX      VRtrIgmpGrpSrcEntry
    MAX-ACCESS  not-accessible
    STATUS      current
    DESCRIPTION
        "An entry in the vRtrIgmpGrpSrcTable. Each entry represents a source
         address from which receivers are interested/not interested in
         receiving multicast traffic. "
    INDEX       {
        vRtrID,
        vRtrIgmpGrpSrcGroupAddress,
        vRtrIgmpGrpSrcSourceAddress,
        vRtrIgmpGrpSrcFwdOrBlk,
        vRtrIfIndex
    }
    ::= { vRtrIgmpGrpSrcTable 1 }

VRtrIgmpGrpSrcEntry              ::= SEQUENCE
{
    vRtrIgmpGrpSrcGroupAddress       IpAddress,
    vRtrIgmpGrpSrcSourceAddress      IpAddress,
    vRtrIgmpGrpSrcFwdOrBlk           INTEGER,
    vRtrIgmpGrpSrcUpTime             Unsigned32
}

vRtrIgmpGrpSrcGroupAddress       OBJECT-TYPE
    SYNTAX      IpAddress
    MAX-ACCESS  not-accessible
    STATUS      current
    DESCRIPTION
        "The IP multicast group address for which this entry contains
         information."
    ::= { vRtrIgmpGrpSrcEntry 1 }

vRtrIgmpGrpSrcSourceAddress      OBJECT-TYPE
    SYNTAX      IpAddress
    MAX-ACCESS  not-accessible
    STATUS      current
    DESCRIPTION
        "The source address for which this entry contains information."
    ::= { vRtrIgmpGrpSrcEntry 2 }

vRtrIgmpGrpSrcFwdOrBlk           OBJECT-TYPE
    SYNTAX      INTEGER {
        forward (1),
        block   (2)
    }
    MAX-ACCESS  read-only
    STATUS      current
    DESCRIPTION
        "vRtrIgmpGrpSrcFwdOrBlk indicates whether this entry is on the forward
         list or block list."
    ::= { vRtrIgmpGrpSrcEntry 3 }

vRtrIgmpGrpSrcUpTime             OBJECT-TYPE
    SYNTAX      Unsigned32
    UNITS       "seconds"
    MAX-ACCESS  read-only
    STATUS      current
    DESCRIPTION
        "vRtrIgmpGrpSrcUpTime indicates the time since this source group entry
         got created."
    ::= { vRtrIgmpGrpSrcEntry 4 }

vRtrIgmpSSMTranslateTable        OBJECT-TYPE
    SYNTAX      SEQUENCE OF VRtrIgmpSSMTranslateEntry
    MAX-ACCESS  not-accessible
    STATUS      current
    DESCRIPTION
        "vRtrIgmpSSMTranslateTable is used to configure group ranges which are
         translated to SSM (S,G) entries."
    ::= { vRtrIgmpProtocolObjs 3 }

vRtrIgmpSSMTranslateEntry        OBJECT-TYPE
    SYNTAX      VRtrIgmpSSMTranslateEntry
    MAX-ACCESS  not-accessible
    STATUS      current
    DESCRIPTION
        "An entry in the vRtrIgmpSSMTranslateTable. Entries can be created or
         deleted by an SNMP SET request to vRtrIgmpSSMTranslateRowStatus."
    INDEX       {
        vRtrID,
        vRtrIgmpSSMTranslateGrpAddr1,
        vRtrIgmpSSMTranslateGrpAddr2,
        vRtrIgmpSSMTranslateSrcAddr
    }
    ::= { vRtrIgmpSSMTranslateTable 1 }

VRtrIgmpSSMTranslateEntry        ::= SEQUENCE
{
    vRtrIgmpSSMTranslateGrpAddr1     IpAddress,
    vRtrIgmpSSMTranslateGrpAddr2     IpAddress,
    vRtrIgmpSSMTranslateSrcAddr      IpAddress,
    vRtrIgmpSSMTranslateRowStatus    RowStatus
}

vRtrIgmpSSMTranslateGrpAddr1     OBJECT-TYPE
    SYNTAX      IpAddress
    MAX-ACCESS  not-accessible
    STATUS      current
    DESCRIPTION
        "vRtrIgmpSSMTranslateGrpAddr1 is an index into the table and it
         indicates the start of the group range."
    ::= { vRtrIgmpSSMTranslateEntry 1 }

vRtrIgmpSSMTranslateGrpAddr2     OBJECT-TYPE
    SYNTAX      IpAddress
    MAX-ACCESS  not-accessible
    STATUS      current
    DESCRIPTION
        "vRtrIgmpSSMTranslateGrpAddr2 is an index into the table and it
         indicates the end of the group range. The value of
         vRtrIgmpSSMTranslateGrpAddr2 should always be greater than or equal to
         the value of vRtrIgmpSSMTranslateGrpAddr1."
    ::= { vRtrIgmpSSMTranslateEntry 2 }

vRtrIgmpSSMTranslateSrcAddr      OBJECT-TYPE
    SYNTAX      IpAddress
    MAX-ACCESS  not-accessible
    STATUS      current
    DESCRIPTION
        "vRtrIgmpSSMTranslateSrcAddr is an index into the table. It indicates
         the source address for this group range. Whenever a (*,G) report is
         received in the range specified by vRtrIgmpSSMTranslateGrpAddr1 and
         vRtrIgmpSSMTranslateGrpAddr2, it is translated to an (S,G) report with
         the value of this object as the source address."
    ::= { vRtrIgmpSSMTranslateEntry 3 }

vRtrIgmpSSMTranslateRowStatus    OBJECT-TYPE
    SYNTAX      RowStatus
    MAX-ACCESS  read-create
    STATUS      current
    DESCRIPTION
        "vRtrIgmpSSMTranslateRowStatus is used to create/delete an entry in
         this table. 'createAndGo' and 'destroy' are the only operations
         supported."
    ::= { vRtrIgmpSSMTranslateEntry 4 }

vRtrIgmpGenStatsTable            OBJECT-TYPE
    SYNTAX      SEQUENCE OF VRtrIgmpGenStatsEntry
    MAX-ACCESS  not-accessible
    STATUS      current
    DESCRIPTION
        "The vRtrIgmpGenStatsTable contains objects for general statistics for
         an IGMP protocol instance within a virtual router."
    ::= { vRtrIgmpProtocolObjs 4 }

vRtrIgmpGenStatsEntry            OBJECT-TYPE
    SYNTAX      VRtrIgmpGenStatsEntry
    MAX-ACCESS  not-accessible
    STATUS      current
    DESCRIPTION
        "Each row entry represents statistics for an instance of the IGMP
         protocol running within a virtual router."
    AUGMENTS    { vRtrIgmpGeneralEntry }
    ::= { vRtrIgmpGenStatsTable 1 }

VRtrIgmpGenStatsEntry            ::= SEQUENCE
{
    vRtrIgmpGenStatsStarGTypes       Gauge32,
    vRtrIgmpGenStatsSGTypes          Gauge32
}

vRtrIgmpGenStatsStarGTypes       OBJECT-TYPE
    SYNTAX      Gauge32
    MAX-ACCESS  read-only
    STATUS      current
    DESCRIPTION
        "vRtrIgmpGenStatsStarGTypes indicates the number of entries in
         vRtrIgmpGrpSrcTable for which the source type is 'starG'."
    ::= { vRtrIgmpGenStatsEntry 1 }

vRtrIgmpGenStatsSGTypes          OBJECT-TYPE
    SYNTAX      Gauge32
    MAX-ACCESS  read-only
    STATUS      current
    DESCRIPTION
        "vRtrIgmpGenStatsSGTypes indicates the number of entries in
         vRtrIgmpGrpSrcTable for which the source type is 'sg'."
    ::= { vRtrIgmpGenStatsEntry 2 }

vRtrIgmpGrpSrcSummaryTable       OBJECT-TYPE
    SYNTAX      SEQUENCE OF VRtrIgmpGrpSrcSummaryEntry
    MAX-ACCESS  not-accessible
    STATUS      current
    DESCRIPTION
        "The table listing the IP multicast Group/Source summary counters."
    ::= { vRtrIgmpProtocolObjs 5 }

vRtrIgmpGrpSrcSummaryEntry       OBJECT-TYPE
    SYNTAX      VRtrIgmpGrpSrcSummaryEntry
    MAX-ACCESS  not-accessible
    STATUS      current
    DESCRIPTION
        "An entry in the vRtrIgmpGrpSrcSummaryTable.

         Each entry represents the summary counters for each Group/Source
         combination."
    INDEX       {
        vRtrID,
        vRtrIgmpGrpSrcGroupAddress,
        vRtrIgmpGrpSrcSourceAddress
    }
    ::= { vRtrIgmpGrpSrcSummaryTable 1 }

VRtrIgmpGrpSrcSummaryEntry       ::= SEQUENCE
{
    vRtrIgmpGrpSrcSummFwdInterfaces  Gauge32,
    vRtrIgmpGrpSrcSummBlkInterfaces  Gauge32,
    vRtrIgmpGrpSrcSummFwdHosts       Gauge32,
    vRtrIgmpGrpSrcSummBlkHosts       Gauge32,
    vRtrIgmpGrpSrcSummFwdGrpIfSaps   Gauge32,
    vRtrIgmpGrpSrcSummBlkGrpIfSaps   Gauge32
}

vRtrIgmpGrpSrcSummFwdInterfaces  OBJECT-TYPE
    SYNTAX      Gauge32
    MAX-ACCESS  read-only
    STATUS      current
    DESCRIPTION
        "vRtrIgmpGrpSrcSummFwdInterfaces indicates the number of interfaces
         having this Group/Source combination in the forwarding list."
    ::= { vRtrIgmpGrpSrcSummaryEntry 1 }

vRtrIgmpGrpSrcSummBlkInterfaces  OBJECT-TYPE
    SYNTAX      Gauge32
    MAX-ACCESS  read-only
    STATUS      current
    DESCRIPTION
        "vRtrIgmpGrpSrcSummBlkInterfaces indicates the number of interfaces
         having this Group/Source combination in the blocking list."
    ::= { vRtrIgmpGrpSrcSummaryEntry 2 }

vRtrIgmpGrpSrcSummFwdHosts       OBJECT-TYPE
    SYNTAX      Gauge32
    MAX-ACCESS  read-only
    STATUS      current
    DESCRIPTION
        "vRtrIgmpGrpSrcSummFwdHosts indicates the number of hosts having this
         Group/Source combination in the forwarding list."
    ::= { vRtrIgmpGrpSrcSummaryEntry 3 }

vRtrIgmpGrpSrcSummBlkHosts       OBJECT-TYPE
    SYNTAX      Gauge32
    MAX-ACCESS  read-only
    STATUS      current
    DESCRIPTION
        "vRtrIgmpGrpSrcSummBlkHosts indicates the number of hosts having this
         Group/Source combination in the blocking list."
    ::= { vRtrIgmpGrpSrcSummaryEntry 4 }

vRtrIgmpGrpSrcSummFwdGrpIfSaps   OBJECT-TYPE
    SYNTAX      Gauge32
    MAX-ACCESS  read-only
    STATUS      current
    DESCRIPTION
        "vRtrIgmpGrpSrcSummFwdGrpIfSaps indicates the number of Grp If SAP's
         having this Group/Source combination in the forwarding list."
    ::= { vRtrIgmpGrpSrcSummaryEntry 5 }

vRtrIgmpGrpSrcSummBlkGrpIfSaps   OBJECT-TYPE
    SYNTAX      Gauge32
    MAX-ACCESS  read-only
    STATUS      current
    DESCRIPTION
        "vRtrIgmpGrpSrcSummBlkGrpIfSaps indicates the number of Grp If SAP's
         having this Group/Source combination in the blocking list."
    ::= { vRtrIgmpGrpSrcSummaryEntry 6 }

vRtrIgmpIfObjs                   OBJECT IDENTIFIER ::= { tmnxIgmpObjs 2 }

vRtrIgmpIfTable                  OBJECT-TYPE
    SYNTAX      SEQUENCE OF VRtrIgmpIfEntry
    MAX-ACCESS  not-accessible
    STATUS      current
    DESCRIPTION
        "The table listing the interfaces on which IGMP protocol operation is
         enabled."
    ::= { vRtrIgmpIfObjs 1 }

vRtrIgmpIfEntry                  OBJECT-TYPE
    SYNTAX      VRtrIgmpIfEntry
    MAX-ACCESS  not-accessible
    STATUS      current
    DESCRIPTION
        "Each row entry in the vRtrIgmpIfTable represents an interface on
         this router that participates in the IGMP protocol.  An entry in
         this table can be created or destroyed by an SNMP SET request to
         vRtrIgmpIfRowStatus.  An attempt to destroy a row will fail if
         vRtrIgmpIfAdminState has not first been set to 'outOfService'."
    INDEX       {
        vRtrID,
        vRtrIfIndex
    }
    ::= { vRtrIgmpIfTable 1 }

VRtrIgmpIfEntry                  ::= SEQUENCE
{
    vRtrIgmpIfRowStatus              RowStatus,
    vRtrIgmpIfLastChangeTime         TimeStamp,
    vRtrIgmpIfAdminState             TmnxAdminState,
    vRtrIgmpIfOperState              TmnxOperState,
    vRtrIgmpIfAdminVersion           Unsigned32,
    vRtrIgmpIfOperVersion            Unsigned32,
    vRtrIgmpIfQuerier                IpAddress,
    vRtrIgmpIfImportPolicy           TPolicyStatementNameOrEmpty,
    vRtrIgmpIfGroupCount             Unsigned32,
    vRtrIgmpIfQuerierUpTime          Unsigned32,
    vRtrIgmpIfQuerierExpiryTime      Unsigned32,
    vRtrIgmpIfNextGenQueryTime       Unsigned32,
    vRtrIgmpIfSubnetCheck            TruthValue,
    vRtrIgmpIfMaxGroups              Unsigned32,
    vRtrIgmpIfMaxGroupsTillNow       Counter32,
    vRtrIgmpIfMcacPolicyName         TPolicyStatementNameOrEmpty,
    vRtrIgmpIfMcacUnconstrainedBW    Integer32,
    vRtrIgmpIfMcacConstAdminState    TmnxAdminState,
    vRtrIgmpIfMcacPreRsvdMandBW      Integer32,
    vRtrIgmpIfMcacinUseMandBw        Unsigned32,
    vRtrIgmpIfMcacinUseOpnlBw        Unsigned32,
    vRtrIgmpIfMcacAvailMandBw        Unsigned32,
    vRtrIgmpIfMcacAvailOpnlBw        Unsigned32,
    vRtrIgmpIfMcacValuesInTransit    TruthValue,
    vRtrIgmpIfDisRtrAlertChk         TruthValue,
    vRtrIgmpIfMaxSources             Unsigned32,
    vRtrIgmpIfMaxGrpSources          Unsigned32,
    vRtrIgmpIfQueryInterval          Unsigned32,
    vRtrIgmpIfLastMembQueryIntvl     Unsigned32,
    vRtrIgmpIfQueryResponseIntvl     Unsigned32,
    vRtrIgmpIfMcacUseLagPortWeight   TruthValue,
    vRtrIgmpIfRedundantMcast         TruthValue,
    vRtrIgmpIfRedundantMcastFwding   TruthValue,
    vRtrIgmpIfMcacIfPolicyName       TPolicyStatementNameOrEmpty
}

vRtrIgmpIfRowStatus              OBJECT-TYPE
    SYNTAX      RowStatus
    MAX-ACCESS  read-create
    STATUS      current
    DESCRIPTION
        "The activation of a row enables IGMP on the interface. The destruction
         of a row disables IGMP on the interface. Before this row can be
         destroyed, vRtrIgmpIfAdminState must have been set to 'outOfService'."
    ::= { vRtrIgmpIfEntry 1 }

vRtrIgmpIfLastChangeTime         OBJECT-TYPE
    SYNTAX      TimeStamp
    MAX-ACCESS  read-only
    STATUS      current
    DESCRIPTION
        "The sysUpTime when this row was last modified."
    ::= { vRtrIgmpIfEntry 2 }

vRtrIgmpIfAdminState             OBJECT-TYPE
    SYNTAX      TmnxAdminState
    MAX-ACCESS  read-create
    STATUS      current
    DESCRIPTION
        "vRtrIgmpIfAdminState specifies the desired administrative state for
         IGMP protocol on this interface."
    DEFVAL      { inService }
    ::= { vRtrIgmpIfEntry 3 }

vRtrIgmpIfOperState              OBJECT-TYPE
    SYNTAX      TmnxOperState
    MAX-ACCESS  read-only
    STATUS      current
    DESCRIPTION
        "The current operational state of IGMP protocol on this interface."
    ::= { vRtrIgmpIfEntry 4 }

vRtrIgmpIfAdminVersion           OBJECT-TYPE
    SYNTAX      Unsigned32
    MAX-ACCESS  read-create
    STATUS      current
    DESCRIPTION
        "The configured version of IGMP which is running on this interface.
         This object can be used to configure a router capable of
         running either value.  For IGMP to function correctly, all
         routers on a LAN must be configured to run the same version
         of IGMP on that LAN."
    DEFVAL      { 3 }
    ::= { vRtrIgmpIfEntry 5 }

vRtrIgmpIfOperVersion            OBJECT-TYPE
    SYNTAX      Unsigned32
    MAX-ACCESS  read-only
    STATUS      current
    DESCRIPTION
        "The operational version of IGMP which is running on this interface. If
         the value of vRtrIgmpIfAdminVersion is configured as '3' but all of
         the routers in the local subnet of this interface use IGMP version v1
         or v2, the operational version will be v1 or v2."
    ::= { vRtrIgmpIfEntry 6 }

vRtrIgmpIfQuerier                OBJECT-TYPE
    SYNTAX      IpAddress
    MAX-ACCESS  read-only
    STATUS      current
    DESCRIPTION
        "The address of the IGMP Querier on the IP subnet to which this
         interface is attached."
    ::= { vRtrIgmpIfEntry 7 }

vRtrIgmpIfImportPolicy           OBJECT-TYPE
    SYNTAX      TPolicyStatementNameOrEmpty
    MAX-ACCESS  read-create
    STATUS      current
    DESCRIPTION
        "vRtrIgmpIfImportPolicy specifies the policy that is to be applied on
         this interface."
    DEFVAL      { ''H }
    ::= { vRtrIgmpIfEntry 8 }

vRtrIgmpIfGroupCount             OBJECT-TYPE
    SYNTAX      Unsigned32
    MAX-ACCESS  read-only
    STATUS      current
    DESCRIPTION
        "vRtrIgmpIfGroupCount is the number of multicast groups which have been
         learned by the router on this interface."
    ::= { vRtrIgmpIfEntry 9 }

vRtrIgmpIfQuerierUpTime          OBJECT-TYPE
    SYNTAX      Unsigned32
    UNITS       "seconds"
    MAX-ACCESS  read-only
    STATUS      current
    DESCRIPTION
        "vRtrIgmpIfQuerierUpTime is the time since vRtrIgmpIfQuerier was last
         elected as querier."
    ::= { vRtrIgmpIfEntry 10 }

vRtrIgmpIfQuerierExpiryTime      OBJECT-TYPE
    SYNTAX      Unsigned32
    UNITS       "seconds"
    MAX-ACCESS  read-only
    STATUS      current
    DESCRIPTION
        "vRtrIgmpIfQuerierExpiryTime is the time remaining before
         vRtrIgmpIfQuerier is aged out. If vRtrIgmpIfQuerier is the local
         interface address, the value of vRtrIgmpIfQuerierExpiryTime will be
         zero."
    ::= { vRtrIgmpIfEntry 11 }

vRtrIgmpIfNextGenQueryTime       OBJECT-TYPE
    SYNTAX      Unsigned32
    UNITS       "seconds"
    MAX-ACCESS  read-only
    STATUS      current
    DESCRIPTION
        "If this router is the querier(vRtrIgmpIfQuerier is a local address),
         vRtrIgmpIfNextGenQueryTime is the time remaining before the general
         query is sent on this interface. If this router is not the querier on
         the interface, the value of this object will be zero."
    ::= { vRtrIgmpIfEntry 12 }

vRtrIgmpIfSubnetCheck            OBJECT-TYPE
    SYNTAX      TruthValue
    MAX-ACCESS  read-create
    STATUS      current
    DESCRIPTION
        "vRtrIgmpIfSubnetCheck is used to enable/disable subnet checking for
         IGMP messages received on this interface.

         If this flag is set to 'true', subnet checking is enabled. All IGMP
         packets with a source address that is not in the local subnet are
         dropped."
    DEFVAL      { true }
    ::= { vRtrIgmpIfEntry 13 }

vRtrIgmpIfMaxGroups              OBJECT-TYPE
    SYNTAX      Unsigned32 (0 | 1..16000)
    MAX-ACCESS  read-create
    STATUS      current
    DESCRIPTION
        "The value of vRtrIgmpIfMaxGroups specifies the maximum number of groups
         for which IGMP can have local receiver information based on received
         IGMP reports on this interface.  When this configuration is changed
         dynamically to a value lower than currently accepted number of groups,
         the groups that are already accepted are not deleted.  Only new groups
         will not be allowed.  When this object has a value of 0, there is no
         limit to the number of groups."
    DEFVAL      { 0 }
    ::= { vRtrIgmpIfEntry 14 }

vRtrIgmpIfMaxGroupsTillNow       OBJECT-TYPE
    SYNTAX      Counter32
    MAX-ACCESS  read-only
    STATUS      current
    DESCRIPTION
        "The value of vRtrIgmpIfMaxGroupsTillNow indicates the highest value
         that vRtrIgmpIfMaxGroups had till now."
    ::= { vRtrIgmpIfEntry 15 }

vRtrIgmpIfMcacPolicyName         OBJECT-TYPE
    SYNTAX      TPolicyStatementNameOrEmpty
    MAX-ACCESS  read-create
    STATUS      current
    DESCRIPTION
        "The value of vRtrIgmpIfMcacPolicyName specifies the name of the
         multicast CAC policy.

         The multicast cac policy applies the interface cac algorithm if the
         channel(group) on this interface is part of the policy as specified in
         vRtrIgmpIfMcacPolicyName."
    DEFVAL      { "" }
    ::= { vRtrIgmpIfEntry 16 }

vRtrIgmpIfMcacUnconstrainedBW    OBJECT-TYPE
    SYNTAX      Integer32 (-1 | 0..2147483647)
    UNITS       "kbps"
    MAX-ACCESS  read-create
    STATUS      current
    DESCRIPTION
        "The value of vRtrIgmpIfMcacUnconstrainedBW specifies the bandwidth
         assigned for interface's multicast cac policy traffic in kilo-bits per
         second(kbps).

         If the default value of '-1' is set, there is no constraint on
         bandwidth allocated at the interface.

         If the value of vRtrIgmpIfMcacUnconstrainedBW is set to '0' and if a
         multicast cac policy is assigned on the interface, then no group
         (channel) from that policy is allowed on that interface."
    DEFVAL      { -1 }
    ::= { vRtrIgmpIfEntry 17 }

vRtrIgmpIfMcacConstAdminState    OBJECT-TYPE
    SYNTAX      TmnxAdminState
    MAX-ACCESS  read-create
    STATUS      current
    DESCRIPTION
        "The value of vRtrIgmpIfMcacConstAdminState specifies the
         administrative state of the multicast CAC policy's constraints."
    DEFVAL      { inService }
    ::= { vRtrIgmpIfEntry 18 }

vRtrIgmpIfMcacPreRsvdMandBW      OBJECT-TYPE
    SYNTAX      Integer32 (-1 | 0..2147483647)
    UNITS       "kbps"
    MAX-ACCESS  read-create
    STATUS      current
    DESCRIPTION
        "The value of vRtrIgmpIfMcacPreRsvdMandBW specifies the bandwidth
         pre-reserved for all the mandatory channels on a given interface in
         kilo-bits per second(kbps).

         If the value of vRtrIgmpIfMcacUnconstrainedBW is '0', no mandatory
         channels are allowed. If the value of vRtrIgmpIfMcacUnconstrainedBW is
         '-1', then all mandatory and optional channels are allowed.

         If the value of vRtrIgmpIfMcacPreRsvdMandBW is equal to the value of
         vRtrIgmpIfMcacUnconstrainedBW, then all the unconstrained bandwidth on
         a given interface is allocated to mandatory channels configured
         through multicast cac policy on that interface and no optional groups
         (channels) are allowed.

         The value of vRtrIgmpIfMcacPreRsvdMandBW should always be less than or
         equal to that of vRtrIgmpIfMcacUnconstrainedBW. An attempt to set the
         value of vRtrIgmpIfMcacPreRsvdMandBW greater than that of
         vRtrIgmpIfMcacUnconstrainedBW will result in inconsistent value error."
    DEFVAL      { -1 }
    ::= { vRtrIgmpIfEntry 19 }

vRtrIgmpIfMcacinUseMandBw        OBJECT-TYPE
    SYNTAX      Unsigned32
    UNITS       "kbps"
    MAX-ACCESS  read-only
    STATUS      current
    DESCRIPTION
        "The value of vRtrIgmpIfMcacinUseMandBw indicates the in-use bandwidth
         in kilo-bits per second(kbps) for the mandatory channels for this
         protocol interface instance."
    ::= { vRtrIgmpIfEntry 20 }

vRtrIgmpIfMcacinUseOpnlBw        OBJECT-TYPE
    SYNTAX      Unsigned32
    UNITS       "kbps"
    MAX-ACCESS  read-only
    STATUS      current
    DESCRIPTION
        "The value of vRtrIgmpIfMcacinUseOpnlBw indicates the in-use bandwidth
         in kilo-bits per second(kbps) for the optional channels for this
         protocol interface instance."
    ::= { vRtrIgmpIfEntry 21 }

vRtrIgmpIfMcacAvailMandBw        OBJECT-TYPE
    SYNTAX      Unsigned32
    UNITS       "kbps"
    MAX-ACCESS  read-only
    STATUS      current
    DESCRIPTION
        "The value of vRtrIgmpIfMcacAvailMandBw indicates the pre-reserved
         bandwidth in kilo-bits per second(kbps) for the mandatory channels for
         this interface instance."
    ::= { vRtrIgmpIfEntry 22 }

vRtrIgmpIfMcacAvailOpnlBw        OBJECT-TYPE
    SYNTAX      Unsigned32
    UNITS       "kbps"
    MAX-ACCESS  read-only
    STATUS      current
    DESCRIPTION
        "The value of vRtrIgmpIfMcacAvailOpnlBw indicates the available
         bandwidth in kilo-bits per second(kbps) for this interface instance."
    ::= { vRtrIgmpIfEntry 23 }

vRtrIgmpIfMcacValuesInTransit    OBJECT-TYPE
    SYNTAX      TruthValue
    MAX-ACCESS  read-only
    STATUS      current
    DESCRIPTION
        "The value of vRtrIgmpIfMcacValuesInTransit indicates that the
         operational (available and in-use mandatory/optional) value for the
         following objects are in transition due to configuration change:

         vRtrIgmpIfMcacAvailMandBw vRtrIgmpIfMcacAvailOpnlBw
         vRtrIgmpIfMcacinUseMandBw vRtrIgmpIfMcacinUseOpnlBw

         When Multicast CAC Policy is applied on the interface for the join of
         the next channel, the operational values will be recalculated and
         applied to the above objects and the value for
         vRtrIgmpIfMcacValuesInTransit will be set to 'false'.

         If the value of vRtrIgmpIfMcacValuesInTransit is 'true' then the
         values are in transition."
    ::= { vRtrIgmpIfEntry 24 }

vRtrIgmpIfDisRtrAlertChk         OBJECT-TYPE
    SYNTAX      TruthValue
    MAX-ACCESS  read-create
    STATUS      current
    DESCRIPTION
        "vRtrIgmpIfDisRtrAlertChk is used to enable/disable router alert
         checking for IGMP messages received on this interface.

         If this flag is set to 'true', checking is disabled."
    DEFVAL      { false }
    ::= { vRtrIgmpIfEntry 25 }

vRtrIgmpIfMaxSources             OBJECT-TYPE
    SYNTAX      Unsigned32 (0 | 1..1000)
    MAX-ACCESS  read-create
    STATUS      current
    DESCRIPTION
        "The value of vRtrIgmpIfMaxSources specifies the maximum number of sources
         for which IGMP can have local receiver information based on received
         IGMP reports on this interface.  When this configuration is changed
         dynamically to a value lower than currently accepted number of sources,
         the sources that are already accepted are not deleted. Only new sources
         will not be allowed. When this object has a value of 0, there is no
         limit to the number of sources."
    DEFVAL      { 0 }
    ::= { vRtrIgmpIfEntry 26 }

vRtrIgmpIfMaxGrpSources          OBJECT-TYPE
    SYNTAX      Unsigned32 (0 | 1..32000)
    MAX-ACCESS  read-create
    STATUS      current
    DESCRIPTION
        "The value of vRtrIgmpIfMaxGrpSources specifies the maximum number of
         group sources for which IGMP can have local receiver information based
         on received IGMP reports on this interface.  When this configuration is
         changed dynamically to a value lower than currently accepted number of
         group sources, the group sources that are already accepted are not
         deleted. Only new group sources will not be allowed. When this object
         has a value of 0, there is no limit to the number of group sources."
    DEFVAL      { 0 }
    ::= { vRtrIgmpIfEntry 27 }

vRtrIgmpIfQueryInterval          OBJECT-TYPE
    SYNTAX      Unsigned32 (0 | 2..1024)
    UNITS       "seconds"
    MAX-ACCESS  read-create
    STATUS      current
    DESCRIPTION
        "The value of vRtrIgmpIfQueryInterval specifies the frequency at which
         the IGMP Host-Query packets are transmitted on this interface."
    DEFVAL      { 0 }
    ::= { vRtrIgmpIfEntry 28 }

vRtrIgmpIfLastMembQueryIntvl     OBJECT-TYPE
    SYNTAX      Unsigned32 (0 | 1..1023)
    UNITS       "seconds"
    MAX-ACCESS  read-create
    STATUS      current
    DESCRIPTION
        "The value of vRtrIgmpIfLastMembQueryIntvl specifies the Max Response
         Time inserted into Group-Specific Queries sent in response to
         Leave Group messages, and is also the amount of time between
         Group-Specific Query messages.  This value may be tuned to
         modify the leave latency of the network.  A reduced value
         results in reduced time to detect the loss of the last
         member of a group."
    DEFVAL      { 0 }
    ::= { vRtrIgmpIfEntry 29 }

vRtrIgmpIfQueryResponseIntvl     OBJECT-TYPE
    SYNTAX      Unsigned32 (0 | 1..1023)
    UNITS       "seconds"
    MAX-ACCESS  read-create
    STATUS      current
    DESCRIPTION
        "The value of vRtrIgmpIfQueryResponseIntvl specifies maximum query
         response time advertised in Igmpv2 queries on this interface."
    DEFVAL      { 0 }
    ::= { vRtrIgmpIfEntry 30 }

vRtrIgmpIfMcacUseLagPortWeight   OBJECT-TYPE
    SYNTAX      TruthValue
    MAX-ACCESS  read-create
    STATUS      current
    DESCRIPTION
        "The value of vRtrIgmpIfMcacUseLagPortWeight specifies if this system
         must use the LAG port weight while calculating Multicast CAC
         constraints.

         The LAG port weight is configured with the object
         TIMETRA-LAG-MIB::tLagPortWeightSpeed."
    DEFVAL      { false }
    ::= { vRtrIgmpIfEntry 31 }

vRtrIgmpIfRedundantMcast         OBJECT-TYPE
    SYNTAX      TruthValue
    MAX-ACCESS  read-create
    STATUS      current
    DESCRIPTION
        "The value of vRtrIgmpIfRedundantMcast specifies if this system
         includes state information about this interface with the
         Multi-Chassis-Redundancy Synchronization (MCS) peer associated with
         its port, for the purpose of forwarding Multicast traffic."
    DEFVAL      { false }
    ::= { vRtrIgmpIfEntry 32 }

vRtrIgmpIfRedundantMcastFwding   OBJECT-TYPE
    SYNTAX      TruthValue
    MAX-ACCESS  read-only
    STATUS      current
    DESCRIPTION
        "The value of vRtrIgmpIfRedundantMcastFwding indicates if this
         interface is the forwarding interface of a pair of redundant multicast
         interfaces.

         The value of this object is only relevant while the value of the
         object vRtrIgmpIfRedundantMcast is equal to 'true'."
    DEFVAL      { false }
    ::= { vRtrIgmpIfEntry 33 }

vRtrIgmpIfMcacIfPolicyName       OBJECT-TYPE
    SYNTAX      TPolicyStatementNameOrEmpty
    MAX-ACCESS  read-create
    STATUS      current
    DESCRIPTION
        "The value of vRtrIgmpIfMcacIfPolicyName specifies the name of the
         multicast CAC interface-policy.

         The multicast cac policy applies the interface cac algorithm if the
         channel(group) on this interface is part of the policy as specified in
         vRtrIgmpIfMcacIfPolicyName."
    DEFVAL      { "" }
    ::= { vRtrIgmpIfEntry 34 }

vRtrIgmpIfGroupTable             OBJECT-TYPE
    SYNTAX      SEQUENCE OF VRtrIgmpIfGroupEntry
    MAX-ACCESS  not-accessible
    STATUS      current
    DESCRIPTION
        "The table listing the IP multicast groups for which there are members
         on a particular interface. This table represents the IGMP group
         database."
    ::= { vRtrIgmpIfObjs 2 }

vRtrIgmpIfGroupEntry             OBJECT-TYPE
    SYNTAX      VRtrIgmpIfGroupEntry
    MAX-ACCESS  not-accessible
    STATUS      current
    DESCRIPTION
        "An entry in the vRtrIgmpIfGroupTable. Each entry represents a group
         address for which receivers are interested/not interested in receiving
         multicast traffic."
    INDEX       {
        vRtrID,
        vRtrIfIndex,
        vRtrIgmpIfGroupAddress
    }
    ::= { vRtrIgmpIfGroupTable 1 }

VRtrIgmpIfGroupEntry             ::= SEQUENCE
{
    vRtrIgmpIfGroupAddress           IpAddress,
    vRtrIgmpIfGroupType              TmnxIgmpGroupType,
    vRtrIgmpIfGroupUpTime            TimeInterval,
    vRtrIgmpIfGroupExpiryTime        TimeInterval,
    vRtrIgmpIfGroupVersion1HostTimer TimeInterval,
    vRtrIgmpIfGroupMode              TmnxIgmpGroupFilterMode,
    vRtrIgmpIfGroupCompatMode        Unsigned32,
    vRtrIgmpIfGroupVersion2HostTimer TimeInterval,
    vRtrIgmpIfGroupLastReporter      IpAddress
}

vRtrIgmpIfGroupAddress           OBJECT-TYPE
    SYNTAX      IpAddress
    MAX-ACCESS  not-accessible
    STATUS      current
    DESCRIPTION
        "The IP multicast group address for which this entry contains
         information."
    ::= { vRtrIgmpIfGroupEntry 1 }

vRtrIgmpIfGroupType              OBJECT-TYPE
    SYNTAX      TmnxIgmpGroupType
    MAX-ACCESS  read-only
    STATUS      current
    DESCRIPTION
        "vRtrIgmpIfGroupType indicates how this group entry was learned. If
         this group entry was learned by IGMP, it will be set to 'dynamic'. For
         statically configured groups, the value will be set to 'static'."
    ::= { vRtrIgmpIfGroupEntry 2 }

vRtrIgmpIfGroupUpTime            OBJECT-TYPE
    SYNTAX      TimeInterval
    MAX-ACCESS  read-only
    STATUS      current
    DESCRIPTION
        "The time elapsed since this entry was created."
    ::= { vRtrIgmpIfGroupEntry 3 }

vRtrIgmpIfGroupExpiryTime        OBJECT-TYPE
    SYNTAX      TimeInterval
    MAX-ACCESS  read-only
    STATUS      current
    DESCRIPTION
        "The minimum amount of time remaining before this entry will
         be aged out.  A value of 0 indicates that the entry is only
         present because igmpCacheSelf is true and that if the router
         left the group, this entry would be aged out immediately.
         Note that some implementations may process membership
         reports from the local system in the same way as reports
         from other hosts, so a value of 0 is not required."
    ::= { vRtrIgmpIfGroupEntry 4 }

vRtrIgmpIfGroupVersion1HostTimer OBJECT-TYPE
    SYNTAX      TimeInterval
    MAX-ACCESS  read-only
    STATUS      current
    DESCRIPTION
        "The time remaining until the local router will assume that
         there are no longer any IGMP version 1 members on the IP
         subnet attached to this interface.  Upon hearing any IGMPv1
         Membership Report, this value is reset to the group
         membership timer.  While this time remaining is non-zero,
         the local router ignores any IGMPv2 Leave messages for this
         group that it receives on this interface."
    ::= { vRtrIgmpIfGroupEntry 5 }

vRtrIgmpIfGroupMode              OBJECT-TYPE
    SYNTAX      TmnxIgmpGroupFilterMode
    MAX-ACCESS  read-only
    STATUS      current
    DESCRIPTION
        "vRtrIgmpIfGroupMode is based on the type of membership report(s)
         received on the interface for the group. In the 'include' mode,
         reception of packets sent to the specified multicast address is
         requested only from those IP source addresses listed in the
         source-list parameter of the IGMP membership report. In 'exclude'
         mode, reception of packets sent to the given multicast address is
         requested from all IP source addresses except those listed in the
         source-list parameter. vRtrIgmpIfGrpSrcTable lists the sources
         corresponding to this group, if any."
    ::= { vRtrIgmpIfGroupEntry 6 }

vRtrIgmpIfGroupCompatMode        OBJECT-TYPE
    SYNTAX      Unsigned32
    MAX-ACCESS  read-only
    STATUS      current
    DESCRIPTION
        "vRtrIgmpIfGroupCompatMode is used in order for routers to be
         compatible with older version routers. IGMPv3 hosts MUST operate
         in version 1 and version 2 compatibility modes.  IGMPv3 hosts MUST
         keep state per local interface regarding the compatibility mode of
         each attached network.  A host's compatibility mode is determined
         from the Host Compatibility Mode variable which can be in
         one of three states:  IGMPv1, IGMPv2 or IGMPv3.  This variable is
         kept per interface and is dependent on the version of General Queries
         heard on that interface as well as the Older Version Querier Present
         timers for the interface."
    ::= { vRtrIgmpIfGroupEntry 7 }

vRtrIgmpIfGroupVersion2HostTimer OBJECT-TYPE
    SYNTAX      TimeInterval
    MAX-ACCESS  read-only
    STATUS      current
    DESCRIPTION
        "The time remaining until the local router will assume that
         there are no longer any IGMP version 2 members on the IP
         subnet attached to this interface.  Upon hearing any IGMPv2
         Membership Report, this value is reset to the group
         membership timer.  While this time remaining is non-zero,
         the local router ignores any IGMPv3 Leave messages for this
         group that it receives on this interface."
    ::= { vRtrIgmpIfGroupEntry 8 }

vRtrIgmpIfGroupLastReporter      OBJECT-TYPE
    SYNTAX      IpAddress
    MAX-ACCESS  read-only
    STATUS      current
    DESCRIPTION
        "The IP address of the source of the last membership report
         received for this IP Multicast group address on this
         interface.  If no membership report has been received, this
         object has the value 0.0.0.0."
    ::= { vRtrIgmpIfGroupEntry 9 }

vRtrIgmpIfGrpSrcTable            OBJECT-TYPE
    SYNTAX      SEQUENCE OF VRtrIgmpIfGrpSrcEntry
    MAX-ACCESS  not-accessible
    STATUS      current
    DESCRIPTION
        "The table listing the IP multicast sources corresponding to the IP
         multicast groups for which there are members on a particular
         interface. This table represents IGMP source, group database."
    ::= { vRtrIgmpIfObjs 3 }

vRtrIgmpIfGrpSrcEntry            OBJECT-TYPE
    SYNTAX      VRtrIgmpIfGrpSrcEntry
    MAX-ACCESS  not-accessible
    STATUS      current
    DESCRIPTION
        "An entry in the vRtrIgmpIfGrpSrcTable. Each entry represents a source
         address from which receivers are interested/not interested in
         receiving multicast traffic from. "
    INDEX       {
        vRtrID,
        vRtrIfIndex,
        vRtrIgmpIfGroupAddress,
        vRtrIgmpIfGrpSrcAddress
    }
    ::= { vRtrIgmpIfGrpSrcTable 1 }

VRtrIgmpIfGrpSrcEntry            ::= SEQUENCE
{
    vRtrIgmpIfGrpSrcAddress          IpAddress,
    vRtrIgmpIfGrpSrcExpiryTime       TimeInterval,
    vRtrIgmpIfGrpSrcType             TmnxIgmpGroupType
}

vRtrIgmpIfGrpSrcAddress          OBJECT-TYPE
    SYNTAX      IpAddress
    MAX-ACCESS  not-accessible
    STATUS      current
    DESCRIPTION
        "The address of the source sending multicast traffic to the group
         identified by vRtrIgmpIfGroupAddress. If the value of
         vRtrIgmpIfGroupMode corresponding to this entry is 'include', the
         receivers are interested in receiving traffic from this source. If the
         value of vRtrIgmpIfGroupMode corresponding to this entry is 'exclude'
         and if the value of vRtrIgmpIfGrpSrcExpiryTime is '0', the receivers
         are not interested in receiving traffic from this source."
    ::= { vRtrIgmpIfGrpSrcEntry 1 }

vRtrIgmpIfGrpSrcExpiryTime       OBJECT-TYPE
    SYNTAX      TimeInterval
    MAX-ACCESS  read-only
    STATUS      current
    DESCRIPTION
        "The minimum amount of time remaining before this entry will be aged
         out. If the value of vRtrIgmpIfGrpSrcExpiryTime is non-zero and the
         value of vRtrIgmpIfGroupMode corresponding to this entry is 'include',
         it means that there are currently one or more systems which desire to
         receive multicast traffic for this source. If this timer expires and
         the value of vRtrIgmpIfGroupMode is 'include', the router concludes
         that traffic from this particular source is no longer desired on the
         attached network, and deletes this entry. This timer is treated
         differently when the value of vRtrIgmpIfGroupMode is 'exclude'. If the
         value of vRtrIgmpIfGrpSrcExpiryTime is non-zero and router filter-mode
         for the group is 'exclude', it means that at least one system desires
         to receive multicast traffic from this source. It should therefore be
         forwarded by a router on the network."
    ::= { vRtrIgmpIfGrpSrcEntry 2 }

vRtrIgmpIfGrpSrcType             OBJECT-TYPE
    SYNTAX      TmnxIgmpGroupType
    MAX-ACCESS  read-only
    STATUS      current
    DESCRIPTION
        "vRtrIgmpIfGrpSrcType indicates how this source entry was learned. If
         this source entry was learned by IGMP, it will be set to 'dynamic'.
         For statically configured sources, the value will be set to 'static'."
    ::= { vRtrIgmpIfGrpSrcEntry 3 }

vRtrIgmpIfStaticGrpSrcTable      OBJECT-TYPE
    SYNTAX      SEQUENCE OF VRtrIgmpIfStaticGrpSrcEntry
    MAX-ACCESS  not-accessible
    STATUS      current
    DESCRIPTION
        "The table listing the IP multicast sources corresponding to the IP
         multicast groups which are statically configured."
    ::= { vRtrIgmpIfObjs 4 }

vRtrIgmpIfStaticGrpSrcEntry      OBJECT-TYPE
    SYNTAX      VRtrIgmpIfStaticGrpSrcEntry
    MAX-ACCESS  not-accessible
    STATUS      current
    DESCRIPTION
        "An entry in the vRtrIgmpIfStaticGrpSrcTable. Entries can be created or
         deleted by an SNMP SET request to vRtrIgmpIfStaticGrpSrcRowStatus."
    INDEX       {
        vRtrID,
        vRtrIfIndex,
        vRtrIgmpIfGroupAddress,
        vRtrIgmpIfGrpSrcAddress
    }
    ::= { vRtrIgmpIfStaticGrpSrcTable 1 }

VRtrIgmpIfStaticGrpSrcEntry      ::= SEQUENCE
{ vRtrIgmpIfStaticGrpSrcRowStatus  RowStatus }

vRtrIgmpIfStaticGrpSrcRowStatus  OBJECT-TYPE
    SYNTAX      RowStatus
    MAX-ACCESS  read-create
    STATUS      current
    DESCRIPTION
        "The row status used for creation or deletion of
         vRtrIgmpIfStaticGrpSrcTable entries."
    ::= { vRtrIgmpIfStaticGrpSrcEntry 1 }

vRtrIgmpIfStatsTable             OBJECT-TYPE
    SYNTAX      SEQUENCE OF VRtrIgmpIfStatsEntry
    MAX-ACCESS  not-accessible
    STATUS      current
    DESCRIPTION
        "The table listing the IGMP statistics for a particular interface."
    ::= { vRtrIgmpIfObjs 5 }

vRtrIgmpIfStatsEntry             OBJECT-TYPE
    SYNTAX      VRtrIgmpIfStatsEntry
    MAX-ACCESS  not-accessible
    STATUS      current
    DESCRIPTION
        "An entry in the vRtrIgmpIfStatsTable."
    AUGMENTS    { vRtrIgmpIfEntry }
    ::= { vRtrIgmpIfStatsTable 1 }

VRtrIgmpIfStatsEntry             ::= SEQUENCE
{
    vRtrIgmpIfTxGenQueries           Counter32,
    vRtrIgmpIfTxGrpQueries           Counter32,
    vRtrIgmpIfTxGrpSrcQueries        Counter32,
    vRtrIgmpIfTxV1Reports            Counter32,
    vRtrIgmpIfTxV2Reports            Counter32,
    vRtrIgmpIfTxV3Reports            Counter32,
    vRtrIgmpIfTxLeaves               Counter32,
    vRtrIgmpIfTxErrors               Counter32,
    vRtrIgmpIfRxGenQueries           Counter32,
    vRtrIgmpIfRxGrpQueries           Counter32,
    vRtrIgmpIfRxGrpSrcQueries        Counter32,
    vRtrIgmpIfRxV1Reports            Counter32,
    vRtrIgmpIfRxV2Reports            Counter32,
    vRtrIgmpIfRxV3Reports            Counter32,
    vRtrIgmpIfRxLeaves               Counter32,
    vRtrIgmpIfRxBadLenPkts           Counter32,
    vRtrIgmpIfRxBadChecksumPkts      Counter32,
    vRtrIgmpIfRxUnknownTypePkts      Counter32,
    vRtrIgmpIfRxBadReceiveIfPkts     Counter32,
    vRtrIgmpIfRxNonLocal             Counter32,
    vRtrIgmpIfRxWrongVersions        Counter32,
    vRtrIgmpIfImportPolicyDrops      Counter32,
    vRtrIgmpIfRxNoRtrAlertPkts       Counter32,
    vRtrIgmpIfRxBadEncodings         Counter32,
    vRtrIgmpIfRxPktDrops             Counter32,
    vRtrIgmpIfStatsStarGTypes        Gauge32,
    vRtrIgmpIfStatsSGTypes           Gauge32,
    vRtrIgmpIfStatsMcacPolicyDrops   Counter32,
    vRtrIgmpIfRxLocalScopePkts       Counter32,
    vRtrIgmpIfRxRsvdScopePkts        Counter32
}

vRtrIgmpIfTxGenQueries           OBJECT-TYPE
    SYNTAX      Counter32
    MAX-ACCESS  read-only
    STATUS      current
    DESCRIPTION
        "The value of vRtrIgmpIfTxGenQueries indicates the number of IGMP
         General Queries transmitted on this interface."
    ::= { vRtrIgmpIfStatsEntry 1 }

vRtrIgmpIfTxGrpQueries           OBJECT-TYPE
    SYNTAX      Counter32
    MAX-ACCESS  read-only
    STATUS      current
    DESCRIPTION
        "The value of vRtrIgmpIfTxGrpQueries indicates the number of IGMP Group
         Specific Queries transmitted on this interface."
    ::= { vRtrIgmpIfStatsEntry 2 }

vRtrIgmpIfTxGrpSrcQueries        OBJECT-TYPE
    SYNTAX      Counter32
    MAX-ACCESS  read-only
    STATUS      current
    DESCRIPTION
        "The value of vRtrIgmpIfTxGrpSrcQueries indicates the number of IGMP
         Group and Source Specific Queries transmitted on this interface."
    ::= { vRtrIgmpIfStatsEntry 3 }

vRtrIgmpIfTxV1Reports            OBJECT-TYPE
    SYNTAX      Counter32
    MAX-ACCESS  read-only
    STATUS      current
    DESCRIPTION
        "The value of vRtrIgmpIfTxV1Reports indicates the total number of IGMP
         V1 Reports transmitted on this interface."
    ::= { vRtrIgmpIfStatsEntry 4 }

vRtrIgmpIfTxV2Reports            OBJECT-TYPE
    SYNTAX      Counter32
    MAX-ACCESS  read-only
    STATUS      current
    DESCRIPTION
        "The value of vRtrIgmpIfTxV2Reports indicates the total number of IGMP
         V2 Reports transmitted on this interface."
    ::= { vRtrIgmpIfStatsEntry 5 }

vRtrIgmpIfTxV3Reports            OBJECT-TYPE
    SYNTAX      Counter32
    MAX-ACCESS  read-only
    STATUS      current
    DESCRIPTION
        "The value of vRtrIgmpIfTxV3Reports indicates the total number of IGMP
         V3 Reports transmitted on this interface."
    ::= { vRtrIgmpIfStatsEntry 6 }

vRtrIgmpIfTxLeaves               OBJECT-TYPE
    SYNTAX      Counter32
    MAX-ACCESS  read-only
    STATUS      current
    DESCRIPTION
        "The value of vRtrIgmpIfTxLeaves indicates the total number of IGMP
         Leaves transmitted on this interface."
    ::= { vRtrIgmpIfStatsEntry 7 }

vRtrIgmpIfTxErrors               OBJECT-TYPE
    SYNTAX      Counter32
    MAX-ACCESS  read-only
    STATUS      current
    DESCRIPTION
        "The value of vRtrIgmpIfTxErrors indicates the total number of times
         there was an error transmitting IGMP packets on this interface.."
    ::= { vRtrIgmpIfStatsEntry 8 }

vRtrIgmpIfRxGenQueries           OBJECT-TYPE
    SYNTAX      Counter32
    MAX-ACCESS  read-only
    STATUS      current
    DESCRIPTION
        "The value of vRtrIgmpIfRxGenQueries indicates the total number of IGMP
         General Queries received on this interface."
    ::= { vRtrIgmpIfStatsEntry 9 }

vRtrIgmpIfRxGrpQueries           OBJECT-TYPE
    SYNTAX      Counter32
    MAX-ACCESS  read-only
    STATUS      current
    DESCRIPTION
        "The value of vRtrIgmpIfRxGrpQueries indicates the number of IGMP Group
         Specific Queries received on this interface."
    ::= { vRtrIgmpIfStatsEntry 10 }

vRtrIgmpIfRxGrpSrcQueries        OBJECT-TYPE
    SYNTAX      Counter32
    MAX-ACCESS  read-only
    STATUS      current
    DESCRIPTION
        "The value of vRtrIgmpIfRxGrpSrcQueries indicates the number of IGMP
         Group and Source Specific Queries received on this interface."
    ::= { vRtrIgmpIfStatsEntry 11 }

vRtrIgmpIfRxV1Reports            OBJECT-TYPE
    SYNTAX      Counter32
    MAX-ACCESS  read-only
    STATUS      current
    DESCRIPTION
        "The value of vRtrIgmpIfRxV1Reports indicates the total number of IGMP
         V1 Reports received on this interface."
    ::= { vRtrIgmpIfStatsEntry 12 }

vRtrIgmpIfRxV2Reports            OBJECT-TYPE
    SYNTAX      Counter32
    MAX-ACCESS  read-only
    STATUS      current
    DESCRIPTION
        "The value of vRtrIgmpIfRxV2Reports indicates the total number of IGMP
         V2 Reports received on this interface."
    ::= { vRtrIgmpIfStatsEntry 13 }

vRtrIgmpIfRxV3Reports            OBJECT-TYPE
    SYNTAX      Counter32
    MAX-ACCESS  read-only
    STATUS      current
    DESCRIPTION
        "The value of vRtrIgmpIfRxV3Reports indicates the total number of IGMP
         V3 Reports received on this interface."
    ::= { vRtrIgmpIfStatsEntry 14 }

vRtrIgmpIfRxLeaves               OBJECT-TYPE
    SYNTAX      Counter32
    MAX-ACCESS  read-only
    STATUS      current
    DESCRIPTION
        "The value of vRtrIgmpIfRxLeaves indicates the total number of IGMP V2
         Leaves received on this interface."
    ::= { vRtrIgmpIfStatsEntry 15 }

vRtrIgmpIfRxBadLenPkts           OBJECT-TYPE
    SYNTAX      Counter32
    MAX-ACCESS  read-only
    STATUS      current
    DESCRIPTION
        "The value of vRtrIgmpIfRxBadLenPkts indicates the total number of IGMP
         packets with bad length received on this interface."
    ::= { vRtrIgmpIfStatsEntry 16 }

vRtrIgmpIfRxBadChecksumPkts      OBJECT-TYPE
    SYNTAX      Counter32
    MAX-ACCESS  read-only
    STATUS      current
    DESCRIPTION
        "The value of vRtrIgmpIfRxBadChecksumPkts indicates the total number of
         IGMP packets with bad checksum received on this interface."
    ::= { vRtrIgmpIfStatsEntry 17 }

vRtrIgmpIfRxUnknownTypePkts      OBJECT-TYPE
    SYNTAX      Counter32
    MAX-ACCESS  read-only
    STATUS      current
    DESCRIPTION
        "The value of vRtrIgmpIfRxUnknownTypePkts indicates the total number of
         IGMP packets with unknown type received on this interface."
    ::= { vRtrIgmpIfStatsEntry 18 }

vRtrIgmpIfRxBadReceiveIfPkts     OBJECT-TYPE
    SYNTAX      Counter32
    MAX-ACCESS  read-only
    STATUS      current
    DESCRIPTION
        "The value of vRtrIgmpIfRxBadReceiveIfPkts indicates the total number
         of IGMP packets incorrectly received on this interface."
    ::= { vRtrIgmpIfStatsEntry 19 }

vRtrIgmpIfRxNonLocal             OBJECT-TYPE
    SYNTAX      Counter32
    MAX-ACCESS  read-only
    STATUS      current
    DESCRIPTION
        "The value of vRtrIgmpIfRxNonLocal indicates the total number of IGMP
         packets received from a non-local sender."
    ::= { vRtrIgmpIfStatsEntry 20 }

vRtrIgmpIfRxWrongVersions        OBJECT-TYPE
    SYNTAX      Counter32
    MAX-ACCESS  read-only
    STATUS      current
    DESCRIPTION
        "The value of vRtrIgmpIfRxWrongVersions indicates the total number of
         IGMP packets with wrong versions received on this interface."
    ::= { vRtrIgmpIfStatsEntry 21 }

vRtrIgmpIfImportPolicyDrops      OBJECT-TYPE
    SYNTAX      Counter32
    MAX-ACCESS  read-only
    STATUS      current
    DESCRIPTION
        "The value of vRtrIgmpIfImportPolicyDrops indicates the total number of
         times IGMP protocol instance matched the host IP address or
         group/source addresses specified in the import policy
         vRtrIgmpIfImportPolicy."
    ::= { vRtrIgmpIfStatsEntry 22 }

vRtrIgmpIfRxNoRtrAlertPkts       OBJECT-TYPE
    SYNTAX      Counter32
    MAX-ACCESS  read-only
    STATUS      current
    DESCRIPTION
        "The value of vRtrIgmpIfRxNoRtrAlertPkts indicates the total number of
         IGMPv3 packets received on this interface which did not have the
         router alert flag set."
    ::= { vRtrIgmpIfStatsEntry 23 }

vRtrIgmpIfRxBadEncodings         OBJECT-TYPE
    SYNTAX      Counter32
    MAX-ACCESS  read-only
    STATUS      current
    DESCRIPTION
        "The value of vRtrIgmpIfRxBadEncodings indicates the total number of
         IGMP packets received on this interface which were not encoded
         correctly."
    ::= { vRtrIgmpIfStatsEntry 24 }

vRtrIgmpIfRxPktDrops             OBJECT-TYPE
    SYNTAX      Counter32
    MAX-ACCESS  read-only
    STATUS      current
    DESCRIPTION
        "The value of vRtrIgmpIfRxPktDrops indicates the total number of IGMP
         packets that were received on this interface but were dropped."
    ::= { vRtrIgmpIfStatsEntry 25 }

vRtrIgmpIfStatsStarGTypes        OBJECT-TYPE
    SYNTAX      Gauge32
    MAX-ACCESS  read-only
    STATUS      current
    DESCRIPTION
        "vRtrIgmpIfStatsStarGTypes indicates the number of entries on this
         interface for which the source type is 'starG'."
    ::= { vRtrIgmpIfStatsEntry 26 }

vRtrIgmpIfStatsSGTypes           OBJECT-TYPE
    SYNTAX      Gauge32
    MAX-ACCESS  read-only
    STATUS      current
    DESCRIPTION
        "The value of vRtrIgmpIfStatsSGTypes indicates the number of entries on
         this interface for which the source type is 'sg'."
    ::= { vRtrIgmpIfStatsEntry 27 }

vRtrIgmpIfStatsMcacPolicyDrops   OBJECT-TYPE
    SYNTAX      Counter32
    MAX-ACCESS  read-only
    STATUS      current
    DESCRIPTION
        "The value of the object vRtrIgmpIfStatsMcacPolicyDrops indicates the
         number times an IGMP Group is dropped because of applying a multicast
         CAC policy on this interface."
    ::= { vRtrIgmpIfStatsEntry 28 }

vRtrIgmpIfRxLocalScopePkts       OBJECT-TYPE
    SYNTAX      Counter32
    MAX-ACCESS  read-only
    STATUS      current
    DESCRIPTION
        "The value of the object vRtrIgmpIfRxLocalScopePkts indicates the
         number of IGMP packets received on the link-local scope IPv4 multicast
         address."
    ::= { vRtrIgmpIfStatsEntry 29 }

vRtrIgmpIfRxRsvdScopePkts        OBJECT-TYPE
    SYNTAX      Counter32
    MAX-ACCESS  read-only
    STATUS      current
    DESCRIPTION
        "The value of the object vRtrIgmpIfRxRsvdScopePkts indicates the number
         of IGMP packets received on the reserved scope IPv4 multicast address."
    ::= { vRtrIgmpIfStatsEntry 30 }

vRtrIgmpIfMcacLevelTable         OBJECT-TYPE
    SYNTAX      SEQUENCE OF VRtrIgmpIfMcacLevelEntry
    MAX-ACCESS  not-accessible
    STATUS      current
    DESCRIPTION
        "The vRtrIgmpIfMcacLevelTable has an entry for each multicast CAC
         policy constraint level configured on this system."
    ::= { vRtrIgmpIfObjs 6 }

vRtrIgmpIfMcacLevelEntry         OBJECT-TYPE
    SYNTAX      VRtrIgmpIfMcacLevelEntry
    MAX-ACCESS  not-accessible
    STATUS      current
    DESCRIPTION
        "Each row entry represents a particular multicast CAC policy level
         constraints. Entries are created/deleted by the user."
    INDEX       {
        vRtrID,
        vRtrIfIndex,
        tmnxMcacLevelId
    }
    ::= { vRtrIgmpIfMcacLevelTable 1 }

VRtrIgmpIfMcacLevelEntry         ::= SEQUENCE
{
    vRtrIgmpIfMcacLevelRowStatus     RowStatus,
    vRtrIgmpIfMcacLevelBW            Unsigned32
}

vRtrIgmpIfMcacLevelRowStatus     OBJECT-TYPE
    SYNTAX      RowStatus
    MAX-ACCESS  read-create
    STATUS      current
    DESCRIPTION
        "The value of vRtrIgmpIfMcacLevelRowStatus is used for
         creation/deletion of level constraint in a CAC policy."
    ::= { vRtrIgmpIfMcacLevelEntry 1 }

vRtrIgmpIfMcacLevelBW            OBJECT-TYPE
    SYNTAX      Unsigned32 (0..2147483647)
    UNITS       "kbps"
    MAX-ACCESS  read-create
    STATUS      current
    DESCRIPTION
        "The value of vRtrIgmpIfMcacLevelBW specifies the bandwidth in
         kilo-bits per second(kbps) for the level."
    DEFVAL      { 1 }
    ::= { vRtrIgmpIfMcacLevelEntry 2 }

vRtrIgmpIfMcacLagTable           OBJECT-TYPE
    SYNTAX      SEQUENCE OF VRtrIgmpIfMcacLagEntry
    MAX-ACCESS  not-accessible
    STATUS      current
    DESCRIPTION
        "The vRtrIgmpIfMcacLagTable has an entry for each lag port configured
         for a multicast CAC policy bundle on this system."
    ::= { vRtrIgmpIfObjs 7 }

vRtrIgmpIfMcacLagEntry           OBJECT-TYPE
    SYNTAX      VRtrIgmpIfMcacLagEntry
    MAX-ACCESS  not-accessible
    STATUS      current
    DESCRIPTION
        "Each row entry represents a particular multicast CAC lag port
         constraints. Entries are created/deleted by the user."
    INDEX       {
        vRtrID,
        vRtrIfIndex,
        tmnxMcacLagPortsDown
    }
    ::= { vRtrIgmpIfMcacLagTable 1 }

VRtrIgmpIfMcacLagEntry           ::= SEQUENCE
{
    vRtrIgmpIfMcacLagRowStatus       RowStatus,
    vRtrIgmpIfMcacLagLevel           Unsigned32
}

vRtrIgmpIfMcacLagRowStatus       OBJECT-TYPE
    SYNTAX      RowStatus
    MAX-ACCESS  read-create
    STATUS      current
    DESCRIPTION
        "The value of vRtrIgmpIfMcacLagRowStatus is used for creation/deletion
         of lag constraint in a CAC policy."
    ::= { vRtrIgmpIfMcacLagEntry 1 }

vRtrIgmpIfMcacLagLevel           OBJECT-TYPE
    SYNTAX      Unsigned32 (1..8)
    MAX-ACCESS  read-create
    STATUS      current
    DESCRIPTION
        "The value of vRtrIgmpIfMcacLagLevel specifies the level id to use when
         the value of tmnxMcacLagPortsDown matches the actual number of ports
         down in a lag.

         Using the value of vRtrIgmpIfMcacLagLevel as an index, the operational
         interface unconstrained bandwidth will be set to
         vRtrIgmpIfMcacLevelBW.

         By default for all lag constraints the interface level will be set to
         1 at row creation."
    DEFVAL      { 1 }
    ::= { vRtrIgmpIfMcacLagEntry 2 }

vRtrIgmpIfSSMTltTableLastChanged OBJECT-TYPE
    SYNTAX      TimeStamp
    MAX-ACCESS  read-only
    STATUS      current
    DESCRIPTION
        "The value of vRtrIgmpIfSSMTltTableLastChanged indicates the sysUpTime
         value at the time of the last modification of an entry in the
         vRtrIgmpIfSSMTransTable.

         If no changes were made to the table since the last re-initialization
         of the local network management subsystem, then this object contains a
         zero value."
    ::= { vRtrIgmpIfObjs 8 }

vRtrIgmpIfSSMTransTable          OBJECT-TYPE
    SYNTAX      SEQUENCE OF VRtrIgmpIfSSMTransEntry
    MAX-ACCESS  not-accessible
    STATUS      current
    DESCRIPTION
        "vRtrIgmpIfSSMTransTable is used to configure group ranges which are
         translated to SSM (S,G) entries per interface."
    ::= { vRtrIgmpIfObjs 9 }

vRtrIgmpIfSSMTransEntry          OBJECT-TYPE
    SYNTAX      VRtrIgmpIfSSMTransEntry
    MAX-ACCESS  not-accessible
    STATUS      current
    DESCRIPTION
        "An entry in the vRtrIgmpIfSSMTransTable. Entries can be created or
         deleted by an SNMP SET request to vRtrIgmpIfSSMTransRowStatus."
    INDEX       {
        vRtrID,
        vRtrIfIndex,
        vRtrIgmpIfSSMTransGrpAddrType1,
        vRtrIgmpIfSSMTransGrpAddr1,
        vRtrIgmpIfSSMTransGrpAddrType2,
        vRtrIgmpIfSSMTransGrpAddr2,
        vRtrIgmpIfSSMTransSrcAddrType,
        vRtrIgmpIfSSMTransSrcAddr
    }
    ::= { vRtrIgmpIfSSMTransTable 1 }

VRtrIgmpIfSSMTransEntry          ::= SEQUENCE
{
    vRtrIgmpIfSSMTransGrpAddrType1   InetAddressType,
    vRtrIgmpIfSSMTransGrpAddr1       InetAddress,
    vRtrIgmpIfSSMTransGrpAddrType2   InetAddressType,
    vRtrIgmpIfSSMTransGrpAddr2       InetAddress,
    vRtrIgmpIfSSMTransSrcAddrType    InetAddressType,
    vRtrIgmpIfSSMTransSrcAddr        InetAddress,
    vRtrIgmpIfSSMTransRowStatus      RowStatus
}

vRtrIgmpIfSSMTransGrpAddrType1   OBJECT-TYPE
    SYNTAX      InetAddressType
    MAX-ACCESS  not-accessible
    STATUS      current
    DESCRIPTION
        "vRtrIgmpIfSSMTransGrpAddrType1 indicates the starting address type of
         the group range."
    ::= { vRtrIgmpIfSSMTransEntry 1 }

vRtrIgmpIfSSMTransGrpAddr1       OBJECT-TYPE
    SYNTAX      InetAddress (SIZE (4))
    MAX-ACCESS  not-accessible
    STATUS      current
    DESCRIPTION
        "vRtrIgmpIfSSMTransGrpAddr1 is an index into the table and it indicates
         the start of the group range."
    ::= { vRtrIgmpIfSSMTransEntry 2 }

vRtrIgmpIfSSMTransGrpAddrType2   OBJECT-TYPE
    SYNTAX      InetAddressType
    MAX-ACCESS  not-accessible
    STATUS      current
    DESCRIPTION
        "vRtrIgmpIfSSMTransGrpAddrType2 indicates the ending address type of
         the group range."
    ::= { vRtrIgmpIfSSMTransEntry 3 }

vRtrIgmpIfSSMTransGrpAddr2       OBJECT-TYPE
    SYNTAX      InetAddress (SIZE (4))
    MAX-ACCESS  not-accessible
    STATUS      current
    DESCRIPTION
        "vRtrIgmpIfSSMTransGrpAddr2 is an index into the table and it indicates
         the end of the group range. The value of vRtrIgmpIfSSMTransGrpAddr2
         should always be greater than or equal to the value of
         vRtrIgmpIfSSMTransGrpAddr1."
    ::= { vRtrIgmpIfSSMTransEntry 4 }

vRtrIgmpIfSSMTransSrcAddrType    OBJECT-TYPE
    SYNTAX      InetAddressType
    MAX-ACCESS  not-accessible
    STATUS      current
    DESCRIPTION
        "vRtrIgmpIfSSMTransSrcAddrType indicates the type of the source address
         for this group range."
    ::= { vRtrIgmpIfSSMTransEntry 5 }

vRtrIgmpIfSSMTransSrcAddr        OBJECT-TYPE
    SYNTAX      InetAddress (SIZE (4))
    MAX-ACCESS  not-accessible
    STATUS      current
    DESCRIPTION
        "vRtrIgmpIfSSMTransSrcAddr is an index into the table. It indicates the
         source address for this group range. Whenever a (*,G) report is
         received in the range specified by vRtrIgmpIfSSMTransGrpAddr1 and
         vRtrIgmpIfSSMTransGrpAddr2, it is translated to an (S,G) report with
         the value of this object as the source address."
    ::= { vRtrIgmpIfSSMTransEntry 6 }

vRtrIgmpIfSSMTransRowStatus      OBJECT-TYPE
    SYNTAX      RowStatus
    MAX-ACCESS  read-create
    STATUS      current
    DESCRIPTION
        "vRtrIgmpIfSSMTransRowStatus is used to create/delete an entry in this
         table. 'createAndGo' and 'destroy' are the only operations supported."
    ::= { vRtrIgmpIfSSMTransEntry 7 }

vRtrIgmpRsvpIfTable              OBJECT-TYPE
    SYNTAX      SEQUENCE OF VRtrIgmpRsvpIfEntry
    MAX-ACCESS  not-accessible
    STATUS      current
    DESCRIPTION
        "The table listing the interfaces on which IGMP protocol operation is
         enabled."
    ::= { vRtrIgmpIfObjs 10 }

vRtrIgmpRsvpIfEntry              OBJECT-TYPE
    SYNTAX      VRtrIgmpRsvpIfEntry
    MAX-ACCESS  not-accessible
    STATUS      current
    DESCRIPTION
        "Each row entry in the vRtrIgmpRsvpIfTable represents a tunnel interface on
         this router that participates in the PIM protocol.  Entries can be created and
         deleted via SNMP SET operations."
    INDEX       {
        vRtrID,
        vRtrIgmpRsvpIfLspName,
        vRtrIgmpRsvpIfSenderAddrType,
        vRtrIgmpRsvpIfSenderAddr
    }
    ::= { vRtrIgmpRsvpIfTable 1 }

VRtrIgmpRsvpIfEntry              ::= SEQUENCE
{
    vRtrIgmpRsvpIfLspName            TNamedItem,
    vRtrIgmpRsvpIfSenderAddrType     InetAddressType,
    vRtrIgmpRsvpIfSenderAddr         InetAddress,
    vRtrIgmpRsvpIfRowStatus          RowStatus,
    vRtrIgmpRsvpIfIndex              InterfaceIndex,
    vRtrIgmpRsvpIfBfdEnable          TruthValue,
    vRtrIgmpRsvpIfAdminState         TmnxAdminState,
    vRtrIgmpRsvpIfOperState          TmnxOperState
}

vRtrIgmpRsvpIfLspName            OBJECT-TYPE
    SYNTAX      TNamedItem
    MAX-ACCESS  not-accessible
    STATUS      current
    DESCRIPTION
        "The value of vRtrIgmpRsvpIfLspName indicates the name of the RSVP
         point to multipoint (P2MP) lsp name associated with this tunnel
         interface."
    ::= { vRtrIgmpRsvpIfEntry 1 }

vRtrIgmpRsvpIfSenderAddrType     OBJECT-TYPE
    SYNTAX      InetAddressType
    MAX-ACCESS  not-accessible
    STATUS      current
    DESCRIPTION
        "The value of vRtrIgmpRsvpIfSenderAddrType indicates the type for
         vRtrIgmpRsvpIfSenderAddr."
    ::= { vRtrIgmpRsvpIfEntry 2 }

vRtrIgmpRsvpIfSenderAddr         OBJECT-TYPE
    SYNTAX      InetAddress (SIZE (0|4))
    MAX-ACCESS  not-accessible
    STATUS      current
    DESCRIPTION
        "The value of vRtrIgmpRsvpIfSenderAddr indicates the sender address."
    ::= { vRtrIgmpRsvpIfEntry 3 }

vRtrIgmpRsvpIfRowStatus          OBJECT-TYPE
    SYNTAX      RowStatus
    MAX-ACCESS  read-create
    STATUS      current
    DESCRIPTION
        "The value of vRtrIgmpRsvpIfRowStatus is used to create or delete an
         entry."
    ::= { vRtrIgmpRsvpIfEntry 4 }

vRtrIgmpRsvpIfIndex              OBJECT-TYPE
    SYNTAX      InterfaceIndex
    MAX-ACCESS  read-only
    STATUS      current
    DESCRIPTION
        "The unique value of vRtrIgmpRsvpIfIndex indicates the tunnel interface  for this
         virtual router in the Nokia SROS system.  It is a unique value among entries with the
         same value of vRtrID."
    ::= { vRtrIgmpRsvpIfEntry 5 }

vRtrIgmpRsvpIfBfdEnable          OBJECT-TYPE
    SYNTAX      TruthValue
    MAX-ACCESS  read-create
    STATUS      current
    DESCRIPTION
        "The value of vRtrIgmpRsvpIfBfdEnable specifies if the BFD session on
         P2MP-LSPs for the failure detection of the ingress node of an LSP is
         enabled or not."
    DEFVAL      { false }
    ::= { vRtrIgmpRsvpIfEntry 6 }

vRtrIgmpRsvpIfAdminState         OBJECT-TYPE
    SYNTAX      TmnxAdminState
    MAX-ACCESS  read-create
    STATUS      current
    DESCRIPTION
        "vRtrIgmpRsvpIfAdminState specifies the desired administrative state
         for IGMP protocol on this tunnel-interface."
    DEFVAL      { inService }
    ::= { vRtrIgmpRsvpIfEntry 7 }

vRtrIgmpRsvpIfOperState          OBJECT-TYPE
    SYNTAX      TmnxOperState
    MAX-ACCESS  read-only
    STATUS      current
    DESCRIPTION
        "vRtrIgmpRsvpIfOperState indicates the current operational state of
         IGMP protocol on this tunnel-interface."
    ::= { vRtrIgmpRsvpIfEntry 8 }

vRtrIgmpLdpIfTableLastChanged    OBJECT-TYPE
    SYNTAX      TimeStamp
    MAX-ACCESS  read-only
    STATUS      current
    DESCRIPTION
        "The value of vRtrIgmpLdpIfTableLastChanged indicates the sysUpTime at
         the time of the last modification to vRtrIgmpLdpIfTable by adding,
         deleting an entry or change to a writable object in the table."
    ::= { vRtrIgmpIfObjs 11 }

vRtrIgmpLdpIfTable               OBJECT-TYPE
    SYNTAX      SEQUENCE OF VRtrIgmpLdpIfEntry
    MAX-ACCESS  not-accessible
    STATUS      current
    DESCRIPTION
        "The table listing the LDP interfaces on which IGMP protocol operation
         is enabled."
    ::= { vRtrIgmpIfObjs 12 }

vRtrIgmpLdpIfEntry               OBJECT-TYPE
    SYNTAX      VRtrIgmpLdpIfEntry
    MAX-ACCESS  not-accessible
    STATUS      current
    DESCRIPTION
        "Each row entry in the vRtrIgmpLdpIfTable represents a tunnel interface
         on this router that participates in the IGMP protocol.  Entries can be
         created and deleted via SNMP SET operations."
    INDEX       {
        vRtrID,
        vRtrIgmpLdpP2mpId,
        vRtrIgmpLdpIfSenderAddrType,
        vRtrIgmpLdpIfSenderAddr
    }
    ::= { vRtrIgmpLdpIfTable 1 }

VRtrIgmpLdpIfEntry               ::= SEQUENCE
{
    vRtrIgmpLdpP2mpId                Unsigned32,
    vRtrIgmpLdpIfSenderAddrType      InetAddressType,
    vRtrIgmpLdpIfSenderAddr          InetAddress,
    vRtrIgmpLdpIfRowStatus           RowStatus,
    vRtrIgmpLdpIfLastChanged         TimeStamp,
    vRtrIgmpLdpIfIndex               InterfaceIndex,
    vRtrIgmpLdpIfAdminState          TmnxAdminState,
    vRtrIgmpLdpIfOperState           TmnxOperState
}

vRtrIgmpLdpP2mpId                OBJECT-TYPE
    SYNTAX      Unsigned32
    MAX-ACCESS  not-accessible
    STATUS      current
    DESCRIPTION
        "The value of vRtrIgmpLdpP2mpId indicates the LDP P2MP Id."
    ::= { vRtrIgmpLdpIfEntry 1 }

vRtrIgmpLdpIfSenderAddrType      OBJECT-TYPE
    SYNTAX      InetAddressType
    MAX-ACCESS  not-accessible
    STATUS      current
    DESCRIPTION
        "The value of vRtrIgmpLdpIfSenderAddrType indicates the type for
         vRtrIgmpLdpIfSenderAddr."
    ::= { vRtrIgmpLdpIfEntry 2 }

vRtrIgmpLdpIfSenderAddr          OBJECT-TYPE
    SYNTAX      InetAddress (SIZE (0|4))
    MAX-ACCESS  not-accessible
    STATUS      current
    DESCRIPTION
        "The value of vRtrIgmpLdpIfSenderAddr indicates the sender address of
         the root node."
    ::= { vRtrIgmpLdpIfEntry 3 }

vRtrIgmpLdpIfRowStatus           OBJECT-TYPE
    SYNTAX      RowStatus
    MAX-ACCESS  read-create
    STATUS      current
    DESCRIPTION
        "The value of vRtrIgmpLdpIfRowStatus is used to create or delete an
         entry."
    ::= { vRtrIgmpLdpIfEntry 4 }

vRtrIgmpLdpIfLastChanged         OBJECT-TYPE
    SYNTAX      TimeStamp
    MAX-ACCESS  read-only
    STATUS      current
    DESCRIPTION
        "The value of vRtrIgmpLdpIfLastChanged indicates the timestamp of the
         last change to this row in vRtrIgmpLdpIfTable."
    ::= { vRtrIgmpLdpIfEntry 5 }

vRtrIgmpLdpIfIndex               OBJECT-TYPE
    SYNTAX      InterfaceIndex
    MAX-ACCESS  read-only
    STATUS      current
    DESCRIPTION
        "The value of vRtrIgmpLdpIfIndex indicates the LDP interface index for
         this virtual router which participates in the IGMP protocol. It is a
         unique value among entries with the same value of vRtrID."
    ::= { vRtrIgmpLdpIfEntry 6 }

vRtrIgmpLdpIfAdminState          OBJECT-TYPE
    SYNTAX      TmnxAdminState
    MAX-ACCESS  read-create
    STATUS      current
    DESCRIPTION
        "vRtrIgmpLdpIfAdminState specifies the desired administrative state for
         IGMP protocol on this tunnel-interface."
    DEFVAL      { inService }
    ::= { vRtrIgmpLdpIfEntry 7 }

vRtrIgmpLdpIfOperState           OBJECT-TYPE
    SYNTAX      TmnxOperState
    MAX-ACCESS  read-only
    STATUS      current
    DESCRIPTION
        "vRtrIgmpLdpIfOperState indicates the current operational state of IGMP
         protocol on this tunnel-interface."
    ::= { vRtrIgmpLdpIfEntry 8 }

vRtrIgmpIfSGrpRangeSrcTblLstChgd OBJECT-TYPE
    SYNTAX      TimeStamp
    MAX-ACCESS  read-only
    STATUS      current
    DESCRIPTION
        "The value of vRtrIgmpIfSGrpRangeSrcTblLstChgd indicates the sysUpTime
         at the time of the last modification of an entry in the
         vRtrIgmpIfSGrpRangeSrcTable.

         If no changes were made to the table since the last re-initialization
         of the local network management subsystem, then this object contains a
         zero value."
    ::= { vRtrIgmpIfObjs 13 }

vRtrIgmpIfSGrpRangeSrcTable      OBJECT-TYPE
    SYNTAX      SEQUENCE OF VRtrIgmpIfSGrpRangeSrcEntry
    MAX-ACCESS  not-accessible
    STATUS      current
    DESCRIPTION
        "The vRtrIgmpIfSGrpRangeSrcTable contains the IP multicast sources
         corresponding to the IP multicast group ranges which are statically
         configured."
    ::= { vRtrIgmpIfObjs 14 }

vRtrIgmpIfSGrpRangeSrcEntry      OBJECT-TYPE
    SYNTAX      VRtrIgmpIfSGrpRangeSrcEntry
    MAX-ACCESS  not-accessible
    STATUS      current
    DESCRIPTION
        "An entry in the vRtrIgmpIfSGrpRangeSrcTable. Entries can be created or
         deleted by an SNMP SET request to vRtrIgmpIfSGrpRangeSrcRowStatus."
    INDEX       {
        vRtrID,
        vRtrIfIndex,
        vRtrIgmpIfSGrpRangeStartAddrType,
        vRtrIgmpIfSGrpRangeStartAddr,
        vRtrIgmpIfSGrpRangeEndAddrType,
        vRtrIgmpIfSGrpRangeEndAddr,
        vRtrIgmpIfSGrpRangeStepAddrType,
        vRtrIgmpIfSGrpRangeStepAddr,
        vRtrIgmpIfSGrpRangeSrcAddrType,
        vRtrIgmpIfSGrpRangeSrcAddr
    }
    ::= { vRtrIgmpIfSGrpRangeSrcTable 1 }

VRtrIgmpIfSGrpRangeSrcEntry      ::= SEQUENCE
{
    vRtrIgmpIfSGrpRangeStartAddrType InetAddressType,
    vRtrIgmpIfSGrpRangeStartAddr     InetAddress,
    vRtrIgmpIfSGrpRangeEndAddrType   InetAddressType,
    vRtrIgmpIfSGrpRangeEndAddr       InetAddress,
    vRtrIgmpIfSGrpRangeStepAddrType  InetAddressType,
    vRtrIgmpIfSGrpRangeStepAddr      InetAddress,
    vRtrIgmpIfSGrpRangeSrcAddrType   InetAddressType,
    vRtrIgmpIfSGrpRangeSrcAddr       InetAddress,
    vRtrIgmpIfSGrpRangeSrcRowStatus  RowStatus,
    vRtrIgmpIfSGrpRangeLastChanged   TimeStamp,
    vRtrIgmpIfSGrpRangeGrpCount      Unsigned32
}

vRtrIgmpIfSGrpRangeStartAddrType OBJECT-TYPE
    SYNTAX      InetAddressType
    MAX-ACCESS  not-accessible
    STATUS      current
    DESCRIPTION
        "The value of vRtrIgmpIfSGrpRangeStartAddrType indicates the address
         type of vRtrIgmpIfSGrpRangeStartAddr."
    ::= { vRtrIgmpIfSGrpRangeSrcEntry 1 }

vRtrIgmpIfSGrpRangeStartAddr     OBJECT-TYPE
    SYNTAX      InetAddress (SIZE (4))
    MAX-ACCESS  not-accessible
    STATUS      current
    DESCRIPTION
        "The value of vRtrIgmpIfSGrpRangeStartAddr indicates the IP multicast
         group-range start-address for which this entry contains information."
    ::= { vRtrIgmpIfSGrpRangeSrcEntry 2 }

vRtrIgmpIfSGrpRangeEndAddrType   OBJECT-TYPE
    SYNTAX      InetAddressType
    MAX-ACCESS  not-accessible
    STATUS      current
    DESCRIPTION
        "The value of vRtrIgmpIfSGrpRangeEndAddrType indicates the address type
         of vRtrIgmpIfSGrpRangeEndAddr."
    ::= { vRtrIgmpIfSGrpRangeSrcEntry 3 }

vRtrIgmpIfSGrpRangeEndAddr       OBJECT-TYPE
    SYNTAX      InetAddress (SIZE (4))
    MAX-ACCESS  not-accessible
    STATUS      current
    DESCRIPTION
        "The value of vRtrIgmpIfSGrpRangeEndAddr indicates the IP multicast
         group-range end-address for which this entry contains information.

         The value of vRtrIgmpIfSGrpRangeEndAddr should always be greater than
         the value of vRtrIgmpIfSGrpRangeStartAddr."
    ::= { vRtrIgmpIfSGrpRangeSrcEntry 4 }

vRtrIgmpIfSGrpRangeStepAddrType  OBJECT-TYPE
    SYNTAX      InetAddressType
    MAX-ACCESS  not-accessible
    STATUS      current
    DESCRIPTION
        "The value of vRtrIgmpIfSGrpRangeStepAddrType indicates the address
         type of vRtrIgmpIfSGrpRangeStepAddr."
    ::= { vRtrIgmpIfSGrpRangeSrcEntry 5 }

vRtrIgmpIfSGrpRangeStepAddr      OBJECT-TYPE
    SYNTAX      InetAddress (SIZE (4))
    MAX-ACCESS  not-accessible
    STATUS      current
    DESCRIPTION
        "The value of vRtrIgmpIfSGrpRangeStepAddr indicates the step interval
         size within the group-range address."
    ::= { vRtrIgmpIfSGrpRangeSrcEntry 6 }

vRtrIgmpIfSGrpRangeSrcAddrType   OBJECT-TYPE
    SYNTAX      InetAddressType
    MAX-ACCESS  not-accessible
    STATUS      current
    DESCRIPTION
        "The value of vRtrIgmpIfSGrpRangeSrcAddrType indicates the address type
         of vRtrIgmpIfSGrpRangeSrcAddr."
    ::= { vRtrIgmpIfSGrpRangeSrcEntry 7 }

vRtrIgmpIfSGrpRangeSrcAddr       OBJECT-TYPE
    SYNTAX      InetAddress (SIZE (4))
    MAX-ACCESS  not-accessible
    STATUS      current
    DESCRIPTION
        "The value of vRtrIgmpIfSGrpRangeSrcAddr indicates the address of the
         source that is joined for every IP multicast group in the range
         vRtrIgmpIfSGrpRangeStartAddr-vRtrIgmpIfSGrpRangeEndAddr.

         A zero address value corresponds to a (*,G) join for every group in
         the range."
    ::= { vRtrIgmpIfSGrpRangeSrcEntry 8 }

vRtrIgmpIfSGrpRangeSrcRowStatus  OBJECT-TYPE
    SYNTAX      RowStatus
    MAX-ACCESS  read-create
    STATUS      current
    DESCRIPTION
        "The row status used for creation or deletion of
         vRtrIgmpIfSGrpRangeSrcTable entries."
    ::= { vRtrIgmpIfSGrpRangeSrcEntry 9 }

vRtrIgmpIfSGrpRangeLastChanged   OBJECT-TYPE
    SYNTAX      TimeStamp
    MAX-ACCESS  read-only
    STATUS      current
    DESCRIPTION
        "The sysUpTime when this row was last modified."
    ::= { vRtrIgmpIfSGrpRangeSrcEntry 10 }

vRtrIgmpIfSGrpRangeGrpCount      OBJECT-TYPE
    SYNTAX      Unsigned32
    MAX-ACCESS  read-only
    STATUS      current
    DESCRIPTION
        "The value of vRtrIgmpIfSGrpRangeGrpCount indicates the number of
         groups in the group-range."
    ::= { vRtrIgmpIfSGrpRangeSrcEntry 11 }

vRtrIgmpNotificationObjs         OBJECT IDENTIFIER ::= { tmnxIgmpObjs 3 }

vRtrIgmpNotifyQueryVersion       OBJECT-TYPE
    SYNTAX      Unsigned32
    MAX-ACCESS  accessible-for-notify
    STATUS      current
    DESCRIPTION
        "vRtrIgmpNotifyQueryVersion is used by vRtrIgmpIfRxQueryVerMismatch to
         notify the version of the query received by the router."
    ::= { vRtrIgmpNotificationObjs 1 }

vRtrIgmpNotifyGrpAddrType        OBJECT-TYPE
    SYNTAX      InetAddressType
    MAX-ACCESS  accessible-for-notify
    STATUS      current
    DESCRIPTION
        "The value of the object vRtrIgmpNotifyGrpAddrType indicates the type
         of vRtrIgmpNotifyGrpAddr."
    ::= { vRtrIgmpNotificationObjs 2 }

vRtrIgmpNotifyGrpAddr            OBJECT-TYPE
    SYNTAX      InetAddress
    MAX-ACCESS  accessible-for-notify
    STATUS      current
    DESCRIPTION
        "The value of the object vRtrIgmpNotifyGrpAddr indicates the multicast
         group address."
    ::= { vRtrIgmpNotificationObjs 3 }

vRtrIgmpNotifyDescription        OBJECT-TYPE
    SYNTAX      DisplayString
    MAX-ACCESS  accessible-for-notify
    STATUS      current
    DESCRIPTION
        "The object vRtrIgmpNotifyDescription is a printable character string."
    ::= { vRtrIgmpNotificationObjs 4 }

vRtrIgmpNotifyMcacPolicyName     OBJECT-TYPE
    SYNTAX      TPolicyStatementNameOrEmpty
    MAX-ACCESS  accessible-for-notify
    STATUS      current
    DESCRIPTION
        "The value of vRtrIgmpNotifyMcacPolicyName specifies the name of the
         multicast CAC policy."
    ::= { vRtrIgmpNotificationObjs 5 }

vRtrIgmpNotifySrcAddrType        OBJECT-TYPE
    SYNTAX      InetAddressType
    MAX-ACCESS  accessible-for-notify
    STATUS      current
    DESCRIPTION
        "The value of the object vRtrIgmpNotifySrcAddrType indicates the type
         of vRtrIgmpNotifySrcAddr."
    ::= { vRtrIgmpNotificationObjs 6 }

vRtrIgmpNotifySrcAddr            OBJECT-TYPE
    SYNTAX      InetAddress
    MAX-ACCESS  accessible-for-notify
    STATUS      current
    DESCRIPTION
        "The value of the object vRtrIgmpNotifySrcAddr indicates the multicast
         source address."
    ::= { vRtrIgmpNotificationObjs 7 }

vRtrIgmpHostObjs                 OBJECT IDENTIFIER ::= { tmnxIgmpObjs 4 }

vRtrIgmpHostTable                OBJECT-TYPE
    SYNTAX      SEQUENCE OF VRtrIgmpHostEntry
    MAX-ACCESS  not-accessible
    STATUS      current
    DESCRIPTION
        "The table listing the hosts for which IGMP protocol operation is
         enabled."
    ::= { vRtrIgmpHostObjs 1 }

vRtrIgmpHostEntry                OBJECT-TYPE
    SYNTAX      VRtrIgmpHostEntry
    MAX-ACCESS  not-accessible
    STATUS      current
    DESCRIPTION
        "Each row entry in the vRtrIgmpHostTable represents a host on this
         router that participates in the IGMP protocol."
    INDEX       {
        vRtrID,
        vRtrIgmpHostAddress
    }
    ::= { vRtrIgmpHostTable 1 }

VRtrIgmpHostEntry                ::= SEQUENCE
{
    vRtrIgmpHostAddress              IpAddress,
    vRtrIgmpHostLastChangeTime       TimeStamp,
    vRtrIgmpHostOperState            IgmpGrpItfOperState,
    vRtrIgmpHostOperVersion          Unsigned32,
    vRtrIgmpHostGroupCount           Unsigned32,
    vRtrIgmpHostNextGenQueryTime     Unsigned32,
    vRtrIgmpHostMaxGroupsTillNow     Counter32,
    vRtrIgmpHostFwdSvcId             TmnxServId,
    vRtrIgmpHostGrpIfId              InterfaceIndex,
    vRtrIgmpHostPppoeSessionId       TmnxPppoeSessionId,
    vRtrIgmpHostSubscriberId         TmnxSubIdentStringOrEmpty,
    vRtrIgmpHostMacAddress           MacAddress,
    vRtrIgmpHostIgmpPolicy           TPolicyStatementNameOrEmpty,
    vRtrIgmpHostMaxGroups            Unsigned32,
    vRtrIgmpHostAdminVersion         Unsigned32,
    vRtrIgmpHostMaxSources           Unsigned32,
    vRtrIgmpHostMaxGrpSources        Unsigned32,
    vRtrIgmpHostQueryInterval        Unsigned32,
    vRtrIgmpHostLastMembQueryIntvl   Unsigned32,
    vRtrIgmpHostQueryResponseIntvl   Unsigned32,
    vRtrIgmpHostDisRtrAlertChk       TruthValue,
    vRtrIgmpHostBondingConnIndex     Unsigned32,
    vRtrIgmpHostBondingId            TmnxSubIdentStringOrEmpty
}

vRtrIgmpHostAddress              OBJECT-TYPE
    SYNTAX      IpAddress
    MAX-ACCESS  not-accessible
    STATUS      current
    DESCRIPTION
        "The IP host address for which this entry contains information."
    ::= { vRtrIgmpHostEntry 1 }

vRtrIgmpHostLastChangeTime       OBJECT-TYPE
    SYNTAX      TimeStamp
    MAX-ACCESS  read-only
    STATUS      current
    DESCRIPTION
        "The sysUpTime when this row was last modified."
    ::= { vRtrIgmpHostEntry 2 }

vRtrIgmpHostOperState            OBJECT-TYPE
    SYNTAX      IgmpGrpItfOperState
    MAX-ACCESS  read-only
    STATUS      current
    DESCRIPTION
        "The current operational state of IGMP protocol for this host."
    ::= { vRtrIgmpHostEntry 3 }

vRtrIgmpHostOperVersion          OBJECT-TYPE
    SYNTAX      Unsigned32
    MAX-ACCESS  read-only
    STATUS      current
    DESCRIPTION
        "The operational version of IGMP which is running for this host. If the
         value of vRtrIgmpIfAdminVersion is configured as '3' but all of the
         routers in the local subnet of this interface use IGMP version v1 or
         v2, the operational version will be v1 or v2."
    ::= { vRtrIgmpHostEntry 4 }

vRtrIgmpHostGroupCount           OBJECT-TYPE
    SYNTAX      Unsigned32
    MAX-ACCESS  read-only
    STATUS      current
    DESCRIPTION
        "vRtrIgmpHostGroupCount is the number of multicast groups which have
         been learned by the router for this host."
    ::= { vRtrIgmpHostEntry 5 }

vRtrIgmpHostNextGenQueryTime     OBJECT-TYPE
    SYNTAX      Unsigned32
    UNITS       "seconds"
    MAX-ACCESS  read-only
    STATUS      current
    DESCRIPTION
        "If this router is the querier (vRtrIgmpIfQuerier is a local address),
         vRtrIgmpHostNextGenQueryTime is the time remaining before the general
         query is sent for this host. If this router is not the querier for the
         host, the value of this object will be zero."
    ::= { vRtrIgmpHostEntry 6 }

vRtrIgmpHostMaxGroupsTillNow     OBJECT-TYPE
    SYNTAX      Counter32
    MAX-ACCESS  read-only
    STATUS      current
    DESCRIPTION
        "The value of vRtrIgmpHostMaxGroupsTillNow indicates the highest value
         that vRtrIgmpHostMaxGroups had till now."
    ::= { vRtrIgmpHostEntry 7 }

vRtrIgmpHostFwdSvcId             OBJECT-TYPE
    SYNTAX      TmnxServId
    MAX-ACCESS  read-only
    STATUS      current
    DESCRIPTION
        "The value of vRtrIgmpHostFwdSvcId specifies the forwarding service ID
         for a subscriber interface in a retailer context."
    DEFVAL      { 0 }
    ::= { vRtrIgmpHostEntry 8 }

vRtrIgmpHostGrpIfId              OBJECT-TYPE
    SYNTAX      InterfaceIndex
    MAX-ACCESS  read-only
    STATUS      current
    DESCRIPTION
        "The value of vRtrIgmpHostGrpIfId specifies the forwarding group
         interface."
    ::= { vRtrIgmpHostEntry 9 }

vRtrIgmpHostPppoeSessionId       OBJECT-TYPE
    SYNTAX      TmnxPppoeSessionId
    MAX-ACCESS  read-only
    STATUS      current
    DESCRIPTION
        "The value of vRtrIgmpHostPppoeSessionId specifies the PPPoE session id
         of this subscriber host."
    ::= { vRtrIgmpHostEntry 10 }

vRtrIgmpHostSubscriberId         OBJECT-TYPE
    SYNTAX      TmnxSubIdentStringOrEmpty
    MAX-ACCESS  read-only
    STATUS      current
    DESCRIPTION
        "The value of vRtrIgmpHostSubscriberId indicates the subscriber
         identification of this subscriber host.

         This must be an existing subscriber."
    ::= { vRtrIgmpHostEntry 11 }

vRtrIgmpHostMacAddress           OBJECT-TYPE
    SYNTAX      MacAddress
    MAX-ACCESS  read-only
    STATUS      current
    DESCRIPTION
        "The value of vRtrIgmpHostMacAddress specifies the MAC address of this
         subscriber host."
    ::= { vRtrIgmpHostEntry 12 }

vRtrIgmpHostIgmpPolicy           OBJECT-TYPE
    SYNTAX      TPolicyStatementNameOrEmpty
    MAX-ACCESS  read-only
    STATUS      current
    DESCRIPTION
        "The value of vRtrIgmpHostIgmpPolicy specifies the name of the IGMP
         policy."
    DEFVAL      { "" }
    ::= { vRtrIgmpHostEntry 13 }

vRtrIgmpHostMaxGroups            OBJECT-TYPE
    SYNTAX      Unsigned32 (0 | 1..16000)
    MAX-ACCESS  read-only
    STATUS      current
    DESCRIPTION
        "The value of vRtrIgmpHostMaxGroups specifies the maximum number of groups
         for which IGMP can have local receiver information based on received
         IGMP reports on this subscriber host.  When this configuration is changed
         dynamically to a value lower than currently accepted number of groups,
         the groups that are already accepted are not deleted.  Only new groups
         will not be allowed.  When this object has a value of 0, there is no
         limit to the number of groups."
    DEFVAL      { 0 }
    ::= { vRtrIgmpHostEntry 14 }

vRtrIgmpHostAdminVersion         OBJECT-TYPE
    SYNTAX      Unsigned32
    MAX-ACCESS  read-only
    STATUS      current
    DESCRIPTION
        "The configured version of IGMP which is running for this Host. For
         IGMP to function correctly, all routers on a LAN must be configured to
         run the same version of IGMP on that LAN."
    DEFVAL      { 3 }
    ::= { vRtrIgmpHostEntry 15 }

vRtrIgmpHostMaxSources           OBJECT-TYPE
    SYNTAX      Unsigned32 (0 | 1..1000)
    MAX-ACCESS  read-only
    STATUS      current
    DESCRIPTION
        "The value of vRtrIgmpHostMaxSources specifies the maximum number of
         sources per group for which IGMP can have local receiver information
         based on received IGMP reports on this subscriber host. When this
         configuration is changed dynamically to a value lower than currently
         accepted number of sources, the sources that are already accepted are
         not deleted. Only new sources will not be allowed. When this object
         has a value of 0, there is no limit to the number of sources."
    DEFVAL      { 0 }
    ::= { vRtrIgmpHostEntry 16 }

vRtrIgmpHostMaxGrpSources        OBJECT-TYPE
    SYNTAX      Unsigned32 (0 | 1..32000)
    MAX-ACCESS  read-only
    STATUS      current
    DESCRIPTION
        "The value of vRtrIgmpHostMaxGrpSources specifies the maximum number of
         group sources per group for which IGMP can have local receiver
         information based on received IGMP reports on this subscriber host.
         When this configuration is changed dynamically to a value lower than
         currently accepted number of sources, the sources that are already
         accepted are not deleted. Only new sources will not be allowed. When
         this object has a value of 0, there is no limit to the number of
         sources."
    DEFVAL      { 0 }
    ::= { vRtrIgmpHostEntry 17 }

vRtrIgmpHostQueryInterval        OBJECT-TYPE
    SYNTAX      Unsigned32 (0 | 2..1024)
    UNITS       "seconds"
    MAX-ACCESS  read-only
    STATUS      current
    DESCRIPTION
        "The value of vRtrIgmpHostQueryInterval indicates the frequency at
         which the IGMP Host-Query packets are transmitted on this subscriber
         host."
    ::= { vRtrIgmpHostEntry 18 }

vRtrIgmpHostLastMembQueryIntvl   OBJECT-TYPE
    SYNTAX      Unsigned32 (0 | 1..1023)
    UNITS       "seconds"
    MAX-ACCESS  read-only
    STATUS      current
    DESCRIPTION
        "The value of vRtrIgmpHostLastMembQueryIntvl indicates the Max Response
         Time inserted into Group-Specific Queries sent in response to
         Leave Group messages, and is also the amount of time between
         Group-Specific Query messages.  This value may be tuned to
         modify the leave latency of the network.  A reduced value
         results in reduced time to detect the loss of the last
         member of a group."
    ::= { vRtrIgmpHostEntry 19 }

vRtrIgmpHostQueryResponseIntvl   OBJECT-TYPE
    SYNTAX      Unsigned32 (0 | 1..1023)
    UNITS       "seconds"
    MAX-ACCESS  read-only
    STATUS      current
    DESCRIPTION
        "The value of vRtrIgmpHostQueryResponseIntvl indicates maximum query
         response time advertised in Igmpv2 queries on this subscriber host."
    ::= { vRtrIgmpHostEntry 20 }

vRtrIgmpHostDisRtrAlertChk       OBJECT-TYPE
    SYNTAX      TruthValue
    MAX-ACCESS  read-only
    STATUS      current
    DESCRIPTION
        "vRtrIgmpHostDisRtrAlertChk indicates whether router alert checking for
         IGMP messages is enabled or disabled.

         If this flag is set to 'true', checking is disabled."
    ::= { vRtrIgmpHostEntry 21 }

vRtrIgmpHostBondingConnIndex     OBJECT-TYPE
    SYNTAX      Unsigned32
    MAX-ACCESS  read-only
    STATUS      current
    DESCRIPTION
        "vRtrIgmpHostBondingConnIndex indicates the bonding connection index of
         the session of this host. A value of 0 indicates this session is not
         part of a bonding context."
    ::= { vRtrIgmpHostEntry 22 }

vRtrIgmpHostBondingId            OBJECT-TYPE
    SYNTAX      TmnxSubIdentStringOrEmpty
    MAX-ACCESS  read-only
    STATUS      current
    DESCRIPTION
        "vRtrIgmpHostBondingId indicates the bonding identifier of the session
         of this host."
    ::= { vRtrIgmpHostEntry 23 }

vRtrIgmpHostStatsTable           OBJECT-TYPE
    SYNTAX      SEQUENCE OF VRtrIgmpHostStatsEntry
    MAX-ACCESS  not-accessible
    STATUS      current
    DESCRIPTION
        "The table listing the IGMP statistics for a particular host."
    ::= { vRtrIgmpHostObjs 2 }

vRtrIgmpHostStatsEntry           OBJECT-TYPE
    SYNTAX      VRtrIgmpHostStatsEntry
    MAX-ACCESS  not-accessible
    STATUS      current
    DESCRIPTION
        "An entry in the vRtrIgmpHostStatsTable."
    AUGMENTS    { vRtrIgmpHostEntry }
    ::= { vRtrIgmpHostStatsTable 1 }

VRtrIgmpHostStatsEntry           ::= SEQUENCE
{
    vRtrIgmpHostTxGenQueries         Counter32,
    vRtrIgmpHostTxGrpQueries         Counter32,
    vRtrIgmpHostTxGrpSrcQueries      Counter32,
    vRtrIgmpHostTxV1Reports          Counter32,
    vRtrIgmpHostTxV2Reports          Counter32,
    vRtrIgmpHostTxV3Reports          Counter32,
    vRtrIgmpHostTxLeaves             Counter32,
    vRtrIgmpHostTxErrors             Counter32,
    vRtrIgmpHostRxGenQueries         Counter32,
    vRtrIgmpHostRxGrpQueries         Counter32,
    vRtrIgmpHostRxGrpSrcQueries      Counter32,
    vRtrIgmpHostRxV1Reports          Counter32,
    vRtrIgmpHostRxV2Reports          Counter32,
    vRtrIgmpHostRxV3Reports          Counter32,
    vRtrIgmpHostRxLeaves             Counter32,
    vRtrIgmpHostRxBadLenPkts         Counter32,
    vRtrIgmpHostRxBadChecksumPkts    Counter32,
    vRtrIgmpHostRxUnknownTypePkts    Counter32,
    vRtrIgmpHostRxBadReceiveIfPkts   Counter32,
    vRtrIgmpHostRxNonLocal           Counter32,
    vRtrIgmpHostRxWrongVersions      Counter32,
    vRtrIgmpHostImportPolicyDrops    Counter32,
    vRtrIgmpHostRxNoRtrAlertPkts     Counter32,
    vRtrIgmpHostRxBadEncodings       Counter32,
    vRtrIgmpHostRxPktDrops           Counter32,
    vRtrIgmpHostStatsStarGTypes      Gauge32,
    vRtrIgmpHostStatsSGTypes         Gauge32,
    vRtrIgmpHostStatsMcacPolicyDrops Counter32,
    vRtrIgmpHostRxLocalScopePkts     Counter32,
    vRtrIgmpHostRxRsvdScopePkts      Counter32,
    vRtrIgmpHostRedirectionDrops     Counter32
}

vRtrIgmpHostTxGenQueries         OBJECT-TYPE
    SYNTAX      Counter32
    MAX-ACCESS  read-only
    STATUS      current
    DESCRIPTION
        "The value of vRtrIgmpHostTxGenQueries indicates the number of IGMP
         General Queries transmitted for this host."
    ::= { vRtrIgmpHostStatsEntry 1 }

vRtrIgmpHostTxGrpQueries         OBJECT-TYPE
    SYNTAX      Counter32
    MAX-ACCESS  read-only
    STATUS      current
    DESCRIPTION
        "The value of vRtrIgmpHostTxGrpQueries indicates the number of IGMP
         Group Specific Queries transmitted for this host."
    ::= { vRtrIgmpHostStatsEntry 2 }

vRtrIgmpHostTxGrpSrcQueries      OBJECT-TYPE
    SYNTAX      Counter32
    MAX-ACCESS  read-only
    STATUS      current
    DESCRIPTION
        "The value of vRtrIgmpHostTxGrpSrcQueries indicates the number of IGMP
         Group and Source Specific Queries transmitted for this host."
    ::= { vRtrIgmpHostStatsEntry 3 }

vRtrIgmpHostTxV1Reports          OBJECT-TYPE
    SYNTAX      Counter32
    MAX-ACCESS  read-only
    STATUS      current
    DESCRIPTION
        "The value of vRtrIgmpHostTxV1Reports indicates the total number of
         IGMP V1 Reports transmitted for this host."
    ::= { vRtrIgmpHostStatsEntry 4 }

vRtrIgmpHostTxV2Reports          OBJECT-TYPE
    SYNTAX      Counter32
    MAX-ACCESS  read-only
    STATUS      current
    DESCRIPTION
        "The value of vRtrIgmpHostTxV2Reports indicates the total number of
         IGMP V2 Reports transmitted for this host."
    ::= { vRtrIgmpHostStatsEntry 5 }

vRtrIgmpHostTxV3Reports          OBJECT-TYPE
    SYNTAX      Counter32
    MAX-ACCESS  read-only
    STATUS      current
    DESCRIPTION
        "The value of vRtrIgmpHostTxV3Reports indicates the total number of
         IGMP V3 Reports transmitted for this host."
    ::= { vRtrIgmpHostStatsEntry 6 }

vRtrIgmpHostTxLeaves             OBJECT-TYPE
    SYNTAX      Counter32
    MAX-ACCESS  read-only
    STATUS      current
    DESCRIPTION
        "The value of vRtrIgmpHostTxLeaves indicates the total number of IGMP
         Leaves transmitted for this host."
    ::= { vRtrIgmpHostStatsEntry 7 }

vRtrIgmpHostTxErrors             OBJECT-TYPE
    SYNTAX      Counter32
    MAX-ACCESS  read-only
    STATUS      current
    DESCRIPTION
        "The value of vRtrIgmpHostTxErrors indicates the total number of times
         there was an error transmitting IGMP packets for this host."
    ::= { vRtrIgmpHostStatsEntry 8 }

vRtrIgmpHostRxGenQueries         OBJECT-TYPE
    SYNTAX      Counter32
    MAX-ACCESS  read-only
    STATUS      current
    DESCRIPTION
        "The value of vRtrIgmpHostRxGenQueries indicates the total number of
         IGMP General Queries received for this host."
    ::= { vRtrIgmpHostStatsEntry 9 }

vRtrIgmpHostRxGrpQueries         OBJECT-TYPE
    SYNTAX      Counter32
    MAX-ACCESS  read-only
    STATUS      current
    DESCRIPTION
        "The value of vRtrIgmpHostRxGrpQueries indicates the number of IGMP
         Group Specific Queries received for this host."
    ::= { vRtrIgmpHostStatsEntry 10 }

vRtrIgmpHostRxGrpSrcQueries      OBJECT-TYPE
    SYNTAX      Counter32
    MAX-ACCESS  read-only
    STATUS      current
    DESCRIPTION
        "The value of vRtrIgmpHostRxGrpSrcQueries indicates the number of IGMP
         Group and Source Specific Queries received for this host."
    ::= { vRtrIgmpHostStatsEntry 11 }

vRtrIgmpHostRxV1Reports          OBJECT-TYPE
    SYNTAX      Counter32
    MAX-ACCESS  read-only
    STATUS      current
    DESCRIPTION
        "The value of vRtrIgmpHostRxV1Reports indicates the total number of
         IGMP V1 Reports received for this host."
    ::= { vRtrIgmpHostStatsEntry 12 }

vRtrIgmpHostRxV2Reports          OBJECT-TYPE
    SYNTAX      Counter32
    MAX-ACCESS  read-only
    STATUS      current
    DESCRIPTION
        "The value of vRtrIgmpHostRxV2Reports indicates the total number of
         IGMP V2 Reports received for this host."
    ::= { vRtrIgmpHostStatsEntry 13 }

vRtrIgmpHostRxV3Reports          OBJECT-TYPE
    SYNTAX      Counter32
    MAX-ACCESS  read-only
    STATUS      current
    DESCRIPTION
        "The value of vRtrIgmpHostRxV3Reports indicates the total number of
         IGMP V3 Reports received for this host."
    ::= { vRtrIgmpHostStatsEntry 14 }

vRtrIgmpHostRxLeaves             OBJECT-TYPE
    SYNTAX      Counter32
    MAX-ACCESS  read-only
    STATUS      current
    DESCRIPTION
        "The value of vRtrIgmpHostRxLeaves indicates the total number of IGMP
         V2 Leaves received for this host."
    ::= { vRtrIgmpHostStatsEntry 15 }

vRtrIgmpHostRxBadLenPkts         OBJECT-TYPE
    SYNTAX      Counter32
    MAX-ACCESS  read-only
    STATUS      current
    DESCRIPTION
        "The value of vRtrIgmpHostRxBadLenPkts indicates the total number of
         IGMP packets with bad length received for this host."
    ::= { vRtrIgmpHostStatsEntry 16 }

vRtrIgmpHostRxBadChecksumPkts    OBJECT-TYPE
    SYNTAX      Counter32
    MAX-ACCESS  read-only
    STATUS      current
    DESCRIPTION
        "The value of vRtrIgmpHostRxBadChecksumPkts indicates the total number
         of IGMP packets with bad checksum received for this host."
    ::= { vRtrIgmpHostStatsEntry 17 }

vRtrIgmpHostRxUnknownTypePkts    OBJECT-TYPE
    SYNTAX      Counter32
    MAX-ACCESS  read-only
    STATUS      current
    DESCRIPTION
        "The value of vRtrIgmpHostRxUnknownTypePkts indicates the total number
         of IGMP packets with unknown type received for this host."
    ::= { vRtrIgmpHostStatsEntry 18 }

vRtrIgmpHostRxBadReceiveIfPkts   OBJECT-TYPE
    SYNTAX      Counter32
    MAX-ACCESS  read-only
    STATUS      current
    DESCRIPTION
        "The value of vRtrIgmpHostRxBadReceiveIfPkts indicates the total number
         of IGMP packets incorrectly received for this host."
    ::= { vRtrIgmpHostStatsEntry 19 }

vRtrIgmpHostRxNonLocal           OBJECT-TYPE
    SYNTAX      Counter32
    MAX-ACCESS  read-only
    STATUS      current
    DESCRIPTION
        "The value of vRtrIgmpHostRxNonLocal indicates the total number of IGMP
         packets received from a non-local sender."
    ::= { vRtrIgmpHostStatsEntry 20 }

vRtrIgmpHostRxWrongVersions      OBJECT-TYPE
    SYNTAX      Counter32
    MAX-ACCESS  read-only
    STATUS      current
    DESCRIPTION
        "The value of vRtrIgmpHostRxWrongVersions indicates the total number of
         IGMP packets with wrong versions received for this host."
    ::= { vRtrIgmpHostStatsEntry 21 }

vRtrIgmpHostImportPolicyDrops    OBJECT-TYPE
    SYNTAX      Counter32
    MAX-ACCESS  read-only
    STATUS      current
    DESCRIPTION
        "The value of vRtrIgmpHostImportPolicyDrops indicates the total number
         of times IGMP protocol instance matched the host IP address or
         group/source addresses specified in the import policy
         tmnxSubIgmpPlcyImportPolicy."
    ::= { vRtrIgmpHostStatsEntry 22 }

vRtrIgmpHostRxNoRtrAlertPkts     OBJECT-TYPE
    SYNTAX      Counter32
    MAX-ACCESS  read-only
    STATUS      current
    DESCRIPTION
        "The value of vRtrIgmpHostRxNoRtrAlertPkts indicates the total number
         of IGMPv3 packets received for this host which did not have the router
         alert flag set."
    ::= { vRtrIgmpHostStatsEntry 23 }

vRtrIgmpHostRxBadEncodings       OBJECT-TYPE
    SYNTAX      Counter32
    MAX-ACCESS  read-only
    STATUS      current
    DESCRIPTION
        "The value of vRtrIgmpHostRxBadEncodings indicates the total number of
         IGMP packets received for this host which were not encoded correctly."
    ::= { vRtrIgmpHostStatsEntry 24 }

vRtrIgmpHostRxPktDrops           OBJECT-TYPE
    SYNTAX      Counter32
    MAX-ACCESS  read-only
    STATUS      current
    DESCRIPTION
        "The value of vRtrIgmpHostRxPktDrops indicates the total number of IGMP
         packets that were received for this host but were dropped."
    ::= { vRtrIgmpHostStatsEntry 25 }

vRtrIgmpHostStatsStarGTypes      OBJECT-TYPE
    SYNTAX      Gauge32
    MAX-ACCESS  read-only
    STATUS      current
    DESCRIPTION
        "The value of vRtrIgmpHostStatsStarGTypes indicates the number of
         entries for this host for which the source type is 'starG'."
    ::= { vRtrIgmpHostStatsEntry 26 }

vRtrIgmpHostStatsSGTypes         OBJECT-TYPE
    SYNTAX      Gauge32
    MAX-ACCESS  read-only
    STATUS      current
    DESCRIPTION
        "The value of vRtrIgmpHostStatsSGTypes indicates the number of entries
         for this host for which the source type is 'sg'."
    ::= { vRtrIgmpHostStatsEntry 27 }

vRtrIgmpHostStatsMcacPolicyDrops OBJECT-TYPE
    SYNTAX      Counter32
    MAX-ACCESS  read-only
    STATUS      current
    DESCRIPTION
        "The value of the object vRtrIgmpHostStatsMcacPolicyDrops indicates the
         number times an IGMP Group is dropped because of applying a multicast
         CAC policy for this host."
    ::= { vRtrIgmpHostStatsEntry 28 }

vRtrIgmpHostRxLocalScopePkts     OBJECT-TYPE
    SYNTAX      Counter32
    MAX-ACCESS  read-only
    STATUS      current
    DESCRIPTION
        "The value of the object vRtrIgmpHostRxLocalScopePkts indicates the
         number of IGMP packets received on the link-local scope IPv4 multicast
         address."
    ::= { vRtrIgmpHostStatsEntry 29 }

vRtrIgmpHostRxRsvdScopePkts      OBJECT-TYPE
    SYNTAX      Counter32
    MAX-ACCESS  read-only
    STATUS      current
    DESCRIPTION
        "The value of the object vRtrIgmpHostRxRsvdScopePkts indicates the
         number of IGMP packets received on the reserved scope IPv4 multicast
         address."
    ::= { vRtrIgmpHostStatsEntry 30 }

vRtrIgmpHostRedirectionDrops     OBJECT-TYPE
    SYNTAX      Counter32
    MAX-ACCESS  read-only
    STATUS      current
    DESCRIPTION
        "The value of the object vRtrIgmpHostRedirectionDrops indicates the
         number times an IGMP Group is dropped because of a failure while
         applying a redirection policy for this host."
    ::= { vRtrIgmpHostStatsEntry 31 }

vRtrIgmpGrpIfTable               OBJECT-TYPE
    SYNTAX      SEQUENCE OF VRtrIgmpGrpIfEntry
    MAX-ACCESS  not-accessible
    STATUS      current
    DESCRIPTION
        "The table listing the group interfaces on which IGMP protocol
         operation is enabled."
    ::= { vRtrIgmpHostObjs 3 }

vRtrIgmpGrpIfEntry               OBJECT-TYPE
    SYNTAX      VRtrIgmpGrpIfEntry
    MAX-ACCESS  not-accessible
    STATUS      current
    DESCRIPTION
        "Each row entry in the vRtrIgmpGrpIfTable represents a group interface on
         this router that participates in the IGMP protocol.  An entry in
         this table can be created or destroyed by an SNMP SET request to
         vRtrIgmpGrpIfRowStatus. An attempt to destroy a row will fail if
         vRtrIgmpGrpIfAdminState has not first been set to 'outOfService'."
    INDEX       {
        vRtrID,
        vRtrIfFwdSvcId,
        vRtrIfIndex
    }
    ::= { vRtrIgmpGrpIfTable 1 }

VRtrIgmpGrpIfEntry               ::= SEQUENCE
{
    vRtrIfFwdSvcId                   TmnxServId,
    vRtrIgmpGrpIfRowStatus           RowStatus,
    vRtrIgmpGrpIfLastChangeTime      TimeStamp,
    vRtrIgmpGrpIfAdminState          TmnxAdminState,
    vRtrIgmpGrpIfOperState           TmnxOperState,
    vRtrIgmpGrpIfSubHostsOnly        TruthValue,
    vRtrIgmpGrpIfAdminVersion        Unsigned32,
    vRtrIgmpGrpIfImportPolicy        TPolicyStatementNameOrEmpty,
    vRtrIgmpGrpIfSubnetCheck         TruthValue,
    vRtrIgmpGrpIfMcacPolicyName      TPolicyStatementNameOrEmpty,
    vRtrIgmpGrpIfMcacUnconstrainedBW Integer32,
    vRtrIgmpGrpIfMcacConstAdminState TmnxAdminState,
    vRtrIgmpGrpIfMcacPreRsvdMandBW   Integer32,
    vRtrIgmpGrpIfMcacinUseMandBw     Unsigned32,
    vRtrIgmpGrpIfMcacinUseOpnlBw     Unsigned32,
    vRtrIgmpGrpIfMcacAvailMandBw     Unsigned32,
    vRtrIgmpGrpIfMcacAvailOpnlBw     Unsigned32,
    vRtrIgmpGrpIfMcacValuesInTransit TruthValue,
    vRtrIgmpGrpIfDisRtrAlertChk      TruthValue,
    vRtrIgmpGrpIfMaxGroups           Unsigned32,
    vRtrIgmpGrpIfMaxSources          Unsigned32,
    vRtrIgmpGrpIfMaxGrpSources       Unsigned32,
    vRtrIgmpGrpIfQuerySrcIp          IpAddress,
    vRtrIgmpGrpIfMcacIfPolicyName    TPolicyStatementNameOrEmpty,
    vRtrIgmpGrpIfQueryInterval       Unsigned32,
    vRtrIgmpGrpIfLastMembQueryIntvl  Unsigned32,
    vRtrIgmpGrpIfQueryResponseIntvl  Unsigned32
}

vRtrIfFwdSvcId                   OBJECT-TYPE
    SYNTAX      TmnxServId
    MAX-ACCESS  not-accessible
    STATUS      current
    DESCRIPTION
        "The value of vRtrIfFwdSvcId specifies the forwarding service ID for a
         subscriber interface in a retailer context."
    DEFVAL      { 0 }
    ::= { vRtrIgmpGrpIfEntry 1 }

vRtrIgmpGrpIfRowStatus           OBJECT-TYPE
    SYNTAX      RowStatus
    MAX-ACCESS  read-create
    STATUS      current
    DESCRIPTION
        "The activation of a row enables IGMP on the group interface. The
         destruction of a row disables IGMP on the group interface. Before this
         row can be destroyed, vRtrIgmpGrpIfAdminState must have been set to
         'outOfService'."
    ::= { vRtrIgmpGrpIfEntry 2 }

vRtrIgmpGrpIfLastChangeTime      OBJECT-TYPE
    SYNTAX      TimeStamp
    MAX-ACCESS  read-only
    STATUS      current
    DESCRIPTION
        "The sysUpTime when this row was last modified."
    ::= { vRtrIgmpGrpIfEntry 3 }

vRtrIgmpGrpIfAdminState          OBJECT-TYPE
    SYNTAX      TmnxAdminState
    MAX-ACCESS  read-create
    STATUS      current
    DESCRIPTION
        "vRtrIgmpGrpIfAdminState specifies the desired administrative state for
         IGMP protocol on this group interface."
    DEFVAL      { inService }
    ::= { vRtrIgmpGrpIfEntry 4 }

vRtrIgmpGrpIfOperState           OBJECT-TYPE
    SYNTAX      TmnxOperState
    MAX-ACCESS  read-only
    STATUS      current
    DESCRIPTION
        "The current operational state of IGMP protocol on this group
         interface."
    ::= { vRtrIgmpGrpIfEntry 5 }

vRtrIgmpGrpIfSubHostsOnly        OBJECT-TYPE
    SYNTAX      TruthValue
    MAX-ACCESS  read-create
    STATUS      current
    DESCRIPTION
        "vRtrIgmpGrpIfSubHostsOnly is used to enable/disable handling of IGMP
         joins received from hosts that are not known in subscriber management
         or on which no IGMP policy is applied.

         If this flag is set to 'true', only traffic from IGMP enabled hosts is
         allowed."
    DEFVAL      { true }
    ::= { vRtrIgmpGrpIfEntry 6 }

vRtrIgmpGrpIfAdminVersion        OBJECT-TYPE
    SYNTAX      Unsigned32
    MAX-ACCESS  read-create
    STATUS      current
    DESCRIPTION
        "The configured version of IGMP which is running on SAPs belonging to
         this group-interface.

         This object can be used to configure a router capable of
         running either value.  For IGMP to function correctly, all
         routers on a LAN must be configured to run the same version
         of IGMP on that LAN."
    DEFVAL      { 3 }
    ::= { vRtrIgmpGrpIfEntry 7 }

vRtrIgmpGrpIfImportPolicy        OBJECT-TYPE
    SYNTAX      TPolicyStatementNameOrEmpty
    MAX-ACCESS  read-create
    STATUS      current
    DESCRIPTION
        "vRtrIgmpGrpIfImportPolicy specifies the policy that is to be applied
         on SAPs belonging to this group-interface."
    DEFVAL      { ''H }
    ::= { vRtrIgmpGrpIfEntry 8 }

vRtrIgmpGrpIfSubnetCheck         OBJECT-TYPE
    SYNTAX      TruthValue
    MAX-ACCESS  read-create
    STATUS      current
    DESCRIPTION
        "vRtrIgmpGrpIfSubnetCheck is used to enable/disable subnet checking for
         IGMP messages received on SAPs belonging to this group-interface.

         If this flag is set to 'true', subnet checking is enabled. All IGMP
         packets with a source address that is not in the local subnet are
         dropped."
    DEFVAL      { true }
    ::= { vRtrIgmpGrpIfEntry 9 }

vRtrIgmpGrpIfMcacPolicyName      OBJECT-TYPE
    SYNTAX      TPolicyStatementNameOrEmpty
    MAX-ACCESS  read-create
    STATUS      current
    DESCRIPTION
        "The value of vRtrIgmpGrpIfMcacPolicyName specifies the name of the
         multicast CAC policy.

         The multicast CAC policy applies to the group-interface CAC algorithm
         if the channel(group) on SAPs belonging to this group-interface is
         part of the policy as specified in vRtrIgmpGrpIfMcacPolicyName."
    DEFVAL      { "" }
    ::= { vRtrIgmpGrpIfEntry 10 }

vRtrIgmpGrpIfMcacUnconstrainedBW OBJECT-TYPE
    SYNTAX      Integer32 (-1 | 0..2147483647)
    UNITS       "kbps"
    MAX-ACCESS  read-create
    STATUS      current
    DESCRIPTION
        "The value of vRtrIgmpGrpIfMcacUnconstrainedBW specifies the bandwidth
         assigned for all SAPs belonging to this group-interface's multicast
         CAC policy traffic in kilo-bits per second(kbps).

         If the default value of '-1' is set, there is no constraint on
         bandwidth allocated to the group-interface.

         If the value of vRtrIgmpGrpIfMcacUnconstrainedBW is set to '0' and if
         a multicast CAC policy is assigned on the group-interface, then no
         group (channel) from that policy is allowed on a SAP belonging to that
         group-interface."
    DEFVAL      { -1 }
    ::= { vRtrIgmpGrpIfEntry 11 }

vRtrIgmpGrpIfMcacConstAdminState OBJECT-TYPE
    SYNTAX      TmnxAdminState
    MAX-ACCESS  read-create
    STATUS      current
    DESCRIPTION
        "The value of vRtrIgmpGrpIfMcacConstAdminState specifies the
         administrative state of the multicast CAC policy's constraints."
    DEFVAL      { inService }
    ::= { vRtrIgmpGrpIfEntry 12 }

vRtrIgmpGrpIfMcacPreRsvdMandBW   OBJECT-TYPE
    SYNTAX      Integer32 (-1 | 0..2147483647)
    UNITS       "kbps"
    MAX-ACCESS  read-create
    STATUS      current
    DESCRIPTION
        "The value of vRtrIgmpGrpIfMcacPreRsvdMandBW specifies the bandwidth
         pre-reserved for all the mandatory channels on all SAPs belonging to a
         given group-interface in kilo-bits per second(kbps).

         If the value of vRtrIgmpGrpIfMcacUnconstrainedBW is '0', no mandatory
         channels are allowed. If the value of vRtrIgmpGrpIfMcacUnconstrainedBW
         is '-1', then all mandatory and optional channels are allowed.

         If the value of vRtrIgmpGrpIfMcacPreRsvdMandBW is equal to the value
         of vRtrIgmpGrpIfMcacUnconstrainedBW, then all the unconstrained
         bandwidth on all SAPs belonging to a given group-interface is
         allocated to mandatory channels configured through multicast CAC
         policy on that group-interface and no optional groups (channels) are
         allowed.

         The value of vRtrIgmpGrpIfMcacPreRsvdMandBW should always be less than
         or equal to that of vRtrIgmpGrpIfMcacUnconstrainedBW. An attempt to
         set the value of vRtrIgmpGrpIfMcacPreRsvdMandBW greater than that of
         vRtrIgmpGrpIfMcacUnconstrainedBW will result in inconsistent value
         error."
    DEFVAL      { -1 }
    ::= { vRtrIgmpGrpIfEntry 13 }

vRtrIgmpGrpIfMcacinUseMandBw     OBJECT-TYPE
    SYNTAX      Unsigned32
    UNITS       "kbps"
    MAX-ACCESS  read-only
    STATUS      current
    DESCRIPTION
        "The value of vRtrIgmpGrpIfMcacinUseMandBw indicates the in-use
         bandwidth in kilo-bits per second(kbps) for the mandatory channels for
         all SAPs belonging to this protocol group-interface instance."
    ::= { vRtrIgmpGrpIfEntry 14 }

vRtrIgmpGrpIfMcacinUseOpnlBw     OBJECT-TYPE
    SYNTAX      Unsigned32
    UNITS       "kbps"
    MAX-ACCESS  read-only
    STATUS      current
    DESCRIPTION
        "The value of vRtrIgmpGrpIfMcacinUseOpnlBw indicates the in-use
         bandwidth in kilo-bits per second(kbps) for the optional channels for
         all SAPs belonging to this protocol group-interface instance."
    ::= { vRtrIgmpGrpIfEntry 15 }

vRtrIgmpGrpIfMcacAvailMandBw     OBJECT-TYPE
    SYNTAX      Unsigned32
    UNITS       "kbps"
    MAX-ACCESS  read-only
    STATUS      current
    DESCRIPTION
        "The value of vRtrIgmpGrpIfMcacAvailMandBw indicates the pre-reserved
         bandwidth in kilo-bits per second(kbps) for the mandatory channels for
         all SAPs belonging to this group-interface instance."
    ::= { vRtrIgmpGrpIfEntry 16 }

vRtrIgmpGrpIfMcacAvailOpnlBw     OBJECT-TYPE
    SYNTAX      Unsigned32
    UNITS       "kbps"
    MAX-ACCESS  read-only
    STATUS      current
    DESCRIPTION
        "The value of vRtrIgmpGrpIfMcacAvailOpnlBw indicates the available
         bandwidth in kilo-bits per second(kbps) for all SAPs belonging to this
         group-interface instance."
    ::= { vRtrIgmpGrpIfEntry 17 }

vRtrIgmpGrpIfMcacValuesInTransit OBJECT-TYPE
    SYNTAX      TruthValue
    MAX-ACCESS  read-only
    STATUS      current
    DESCRIPTION
        "The value of vRtrIgmpGrpIfMcacValuesInTransit indicates that the
         operational (available and in-use mandatory/optional) value for the
         following objects are in transition due to configuration change:

         vRtrIgmpGrpIfMcacAvailMandBw vRtrIgmpGrpIfMcacAvailOpnlBw
         vRtrIgmpGrpIfMcacinUseMandBw vRtrIgmpGrpIfMcacinUseOpnlBw

         When Multicast CAC Policy is applied on the group-interface for the
         join of the next channel, the operational values will be recalculated
         and applied to the above objects and the value for
         vRtrIgmpGrpIfMcacValuesInTransit will be set to 'false'.

         If the value of vRtrIgmpGrpIfMcacValuesInTransit is 'true' then the
         values are in transition."
    ::= { vRtrIgmpGrpIfEntry 18 }

vRtrIgmpGrpIfDisRtrAlertChk      OBJECT-TYPE
    SYNTAX      TruthValue
    MAX-ACCESS  read-create
    STATUS      current
    DESCRIPTION
        "vRtrIgmpGrpIfDisRtrAlertChk is used to enable/disable router alert
         checking for IGMP messages received on SAPs belonging to this
         group-interface.

         If this flag is set to 'true', checking is disabled."
    DEFVAL      { false }
    ::= { vRtrIgmpGrpIfEntry 19 }

vRtrIgmpGrpIfMaxGroups           OBJECT-TYPE
    SYNTAX      Unsigned32 (0 | 1..16000)
    MAX-ACCESS  read-create
    STATUS      current
    DESCRIPTION
        "The value of vRtrIgmpGrpIfMaxGroups specifies the maximum number of groups
         for which IGMP can have local receiver information based on received
         IGMP reports on a SAP belonging to this group-interface.  When this
         configuration is changed dynamically to a value lower than currently
         accepted number of groups, the groups that are already accepted are not
         deleted. Only new groups will not be allowed. When this object has a
         value of 0, there is no limit to the number of groups."
    DEFVAL      { 0 }
    ::= { vRtrIgmpGrpIfEntry 20 }

vRtrIgmpGrpIfMaxSources          OBJECT-TYPE
    SYNTAX      Unsigned32 (0 | 1..1000)
    MAX-ACCESS  read-create
    STATUS      current
    DESCRIPTION
        "The value of vRtrIgmpGrpIfMaxSources specifies the maximum number of sources
         for which IGMP can have local receiver information based on received
         IGMP reports on a SAP belonging to this group-interface.  When this
         configuration is changed dynamically to a value lower than currently
         accepted number of sources, the sources that are already accepted are not
         deleted. Only new sources will not be allowed. When this object has a
         value of 0, there is no limit to the number of sources."
    DEFVAL      { 0 }
    ::= { vRtrIgmpGrpIfEntry 21 }

vRtrIgmpGrpIfMaxGrpSources       OBJECT-TYPE
    SYNTAX      Unsigned32 (0 | 1..32000)
    MAX-ACCESS  read-create
    STATUS      current
    DESCRIPTION
        "The value of vRtrIgmpGrpIfMaxGrpSources specifies the maximum number
         of group sources for which IGMP can have local receiver information
         based on received IGMP reports on a SAP belonging to this
         group-interface. When this configuration is changed dynamically to a
         value lower than currently accepted number of group sources, the group
         sources that are already accepted are not deleted. Only new group
         sources will not be allowed. When this object has a value of 0, there
         is no limit to the number of group sources."
    DEFVAL      { 0 }
    ::= { vRtrIgmpGrpIfEntry 22 }

vRtrIgmpGrpIfQuerySrcIp          OBJECT-TYPE
    SYNTAX      IpAddress
    MAX-ACCESS  read-create
    STATUS      current
    DESCRIPTION
        "The value of vRtrIgmpGrpIfQuerySrcIp specifies the source IP address
         used when generating IGMP queries on this group interface."
    DEFVAL      { 0 }
    ::= { vRtrIgmpGrpIfEntry 23 }

vRtrIgmpGrpIfMcacIfPolicyName    OBJECT-TYPE
    SYNTAX      TPolicyStatementNameOrEmpty
    MAX-ACCESS  read-create
    STATUS      current
    DESCRIPTION
        "The value of vRtrIgmpGrpIfMcacIfPolicyName specifies the name of the
         multicast CAC interface policy.

         The multicast CAC policy applies to the group-interface CAC algorithm
         if the channel(group) on SAPs belonging to this group-interface is
         part of the policy as specified in vRtrIgmpGrpIfMcacIfPolicyName."
    DEFVAL      { "" }
    ::= { vRtrIgmpGrpIfEntry 24 }

vRtrIgmpGrpIfQueryInterval       OBJECT-TYPE
    SYNTAX      Unsigned32 (0 | 2..1024)
    UNITS       "seconds"
    MAX-ACCESS  read-create
    STATUS      current
    DESCRIPTION
        "The value of vRtrIgmpGrpIfQueryInterval specifies the frequency at
         which the IGMP Host-Query packets are transmitted on this interface."
    DEFVAL      { 0 }
    ::= { vRtrIgmpGrpIfEntry 25 }

vRtrIgmpGrpIfLastMembQueryIntvl  OBJECT-TYPE
    SYNTAX      Unsigned32 (0 | 1..1023)
    UNITS       "seconds"
    MAX-ACCESS  read-create
    STATUS      current
    DESCRIPTION
        "The value of vRtrIgmpGrpIfLastMembQueryIntvl specifies the Max Response
         Time inserted into Group-Specific Queries sent in response to
         Leave Group messages, and is also the amount of time between
         Group-Specific Query messages.  This value may be tuned to
         modify the leave latency of the network.  A reduced value
         results in reduced time to detect the loss of the last
         member of a group."
    DEFVAL      { 0 }
    ::= { vRtrIgmpGrpIfEntry 26 }

vRtrIgmpGrpIfQueryResponseIntvl  OBJECT-TYPE
    SYNTAX      Unsigned32 (0 | 1..1023)
    UNITS       "seconds"
    MAX-ACCESS  read-create
    STATUS      current
    DESCRIPTION
        "The value of vRtrIgmpGrpIfQueryResponseIntvl specifies maximum query
         response time advertised in Igmpv2 queries on this interface."
    DEFVAL      { 0 }
    ::= { vRtrIgmpGrpIfEntry 27 }

vRtrIgmpGrpIfHostGrpTable        OBJECT-TYPE
    SYNTAX      SEQUENCE OF VRtrIgmpGrpIfHostGrpEntry
    MAX-ACCESS  not-accessible
    STATUS      current
    DESCRIPTION
        "The table listing the IP multicast groups for which there are members
         on a particular host. This table represents the IGMP group database."
    ::= { vRtrIgmpHostObjs 4 }

vRtrIgmpGrpIfHostGrpEntry        OBJECT-TYPE
    SYNTAX      VRtrIgmpGrpIfHostGrpEntry
    MAX-ACCESS  not-accessible
    STATUS      current
    DESCRIPTION
        "An entry in the vRtrIgmpGrpIfHostGrpTable. Each entry represents a
         group address for which receivers are interested/not interested in
         receiving multicast traffic."
    INDEX       {
        vRtrID,
        vRtrIfFwdSvcId,
        vRtrGrpIfIndex,
        vRtrIgmpHostAddress,
        vRtrIgmpHostGroupAddress
    }
    ::= { vRtrIgmpGrpIfHostGrpTable 1 }

VRtrIgmpGrpIfHostGrpEntry        ::= SEQUENCE
{
    vRtrGrpIfIndex                   InterfaceIndex,
    vRtrIgmpHostGroupAddress         IpAddress,
    vRtrIgmpGrpIfHostGrpType         TmnxIgmpGroupType,
    vRtrIgmpGrpIfHostGrpUpTime       TimeInterval,
    vRtrIgmpGrpIfHostGrpExpiryTime   TimeInterval,
    vRtrIgmpGrpIfHostGrpVer1HostTmr  TimeInterval,
    vRtrIgmpGrpIfHostGrpMode         TmnxIgmpGroupFilterMode,
    vRtrIgmpGrpIfHostGrpCompatMode   Unsigned32,
    vRtrIgmpGrpIfHostGrpVer2HostTmr  TimeInterval,
    vRtrIgmpGrpIfHostGrpMRDstVrId    TmnxVRtrIDOrZero,
    vRtrIgmpGrpIfHostGrpMRDstIfId    InterfaceIndexOrZero,
    vRtrIgmpGrpIfHostGrpBondOwner    TruthValue,
    vRtrIgmpGrpIfHostGrpBondFwd      TruthValue
}

vRtrGrpIfIndex                   OBJECT-TYPE
    SYNTAX      InterfaceIndex
    MAX-ACCESS  not-accessible
    STATUS      current
    DESCRIPTION
        "The unique value which identifies this interface of this virtual
         router in the Tmnx system. This field provides an identifier for
         virtual router interfaces similar to the ifIndex values used in the
         mib-2 interfaces table for physical interfaces. The vRtrGrpIfIndex
         values can be reused for different virtual routers, but are unique
         within those entries with the same vRtrID.

         The vRtrGrpIfIndex value for each virtual interface must remain
         constant at least from one re-initialization of the system management
         processor to the next."
    ::= { vRtrIgmpGrpIfHostGrpEntry 1 }

vRtrIgmpHostGroupAddress         OBJECT-TYPE
    SYNTAX      IpAddress
    MAX-ACCESS  not-accessible
    STATUS      current
    DESCRIPTION
        "The IP multicast group address for which this entry contains
         information."
    ::= { vRtrIgmpGrpIfHostGrpEntry 2 }

vRtrIgmpGrpIfHostGrpType         OBJECT-TYPE
    SYNTAX      TmnxIgmpGroupType
    MAX-ACCESS  read-only
    STATUS      current
    DESCRIPTION
        "vRtrIgmpGrpIfHostGrpType indicates how this group entry was learned.
         If this group entry was learned by IGMP, it will be set to 'dynamic'.
         For statically configured groups, the value will be set to 'static'."
    ::= { vRtrIgmpGrpIfHostGrpEntry 3 }

vRtrIgmpGrpIfHostGrpUpTime       OBJECT-TYPE
    SYNTAX      TimeInterval
    MAX-ACCESS  read-only
    STATUS      current
    DESCRIPTION
        "The time elapsed since this entry was created."
    ::= { vRtrIgmpGrpIfHostGrpEntry 4 }

vRtrIgmpGrpIfHostGrpExpiryTime   OBJECT-TYPE
    SYNTAX      TimeInterval
    MAX-ACCESS  read-only
    STATUS      current
    DESCRIPTION
        "The minimum amount of time remaining before this entry will be aged
         out. A value of 0 indicates that the entry is only present because
         igmpCacheSelf is true and that if the router left the group, this
         entry would be aged out immediately. Note that some implementations
         may process membership reports from the local system in the same way
         as reports from other hosts, so a value of 0 is not required."
    ::= { vRtrIgmpGrpIfHostGrpEntry 5 }

vRtrIgmpGrpIfHostGrpVer1HostTmr  OBJECT-TYPE
    SYNTAX      TimeInterval
    MAX-ACCESS  read-only
    STATUS      current
    DESCRIPTION
        "The time remaining until the local router will assume that
         there are no longer any IGMP version 1 members on the IP
         subnet attached to this host.  Upon hearing any IGMPv1
         Membership Report, this value is reset to the group
         membership timer.  While this time remaining is non-zero,
         the local router ignores any IGMPv2 Leave messages for this
         group that it receives on this host."
    ::= { vRtrIgmpGrpIfHostGrpEntry 6 }

vRtrIgmpGrpIfHostGrpMode         OBJECT-TYPE
    SYNTAX      TmnxIgmpGroupFilterMode
    MAX-ACCESS  read-only
    STATUS      current
    DESCRIPTION
        "vRtrIgmpGrpIfHostGrpMode is based on the type of membership report(s)
         received on the host for the group. In the 'include' mode, reception
         of packets sent to the specified multicast address is requested only
         from those IP source addresses listed in the source-list parameter of
         the IGMP membership report. In 'exclude' mode, reception of packets
         sent to the given multicast address is requested from all IP source
         addresses except those listed in the source-list parameter.
         vRtrIgmpGrpIfHostGrpSrcTable lists the sources corresponding to this
         group, if any."
    ::= { vRtrIgmpGrpIfHostGrpEntry 7 }

vRtrIgmpGrpIfHostGrpCompatMode   OBJECT-TYPE
    SYNTAX      Unsigned32
    MAX-ACCESS  read-only
    STATUS      current
    DESCRIPTION
        "vRtrIgmpGrpIfHostGrpCompatMode is used in order for routers to be
         compatible with older version routers. IGMPv3 hosts MUST operate
         in version 1 and version 2 compatibility modes.  IGMPv3 hosts MUST
         keep state per local host regarding the compatibility mode of
         each attached network.  A host's compatibility mode is determined
         from the Host Compatibility Mode variable which can be in
         one of three states:  IGMPv1, IGMPv2 or IGMPv3.  This variable is
         kept per interface and is dependent on the version of General Queries
         heard on that host as well as the Older Version Querier Present
         timers for the host."
    ::= { vRtrIgmpGrpIfHostGrpEntry 8 }

vRtrIgmpGrpIfHostGrpVer2HostTmr  OBJECT-TYPE
    SYNTAX      TimeInterval
    MAX-ACCESS  read-only
    STATUS      current
    DESCRIPTION
        "The time remaining until the local router will assume that
         there are no longer any IGMP version 2 members on the IP
         subnet attached to this host.  Upon hearing any IGMPv2
         Membership Report, this value is reset to the group
         membership timer.  While this time remaining is non-zero,
         the local router ignores any IGMPv3 Leave messages for this
         group that it receives on this host."
    ::= { vRtrIgmpGrpIfHostGrpEntry 9 }

vRtrIgmpGrpIfHostGrpMRDstVrId    OBJECT-TYPE
    SYNTAX      TmnxVRtrIDOrZero
    MAX-ACCESS  read-only
    STATUS      current
    DESCRIPTION
        "The value of vRtrIgmpGrpIfHostGrpMRDstVrId indicates the vRtrID of the
         service where to redirect IGMP multicast traffic to.

         The value zero means that no multicast redirection is configured."
    ::= { vRtrIgmpGrpIfHostGrpEntry 10 }

vRtrIgmpGrpIfHostGrpMRDstIfId    OBJECT-TYPE
    SYNTAX      InterfaceIndexOrZero
    MAX-ACCESS  read-only
    STATUS      current
    DESCRIPTION
        "The value of vRtrIgmpGrpIfHostGrpMRDstIfId indicates the interface
         index of the interface where to redirect IGMP multicast traffic to.

         The value zero means that no multicast redirection is configured."
    ::= { vRtrIgmpGrpIfHostGrpEntry 11 }

vRtrIgmpGrpIfHostGrpBondOwner    OBJECT-TYPE
    SYNTAX      TruthValue
    MAX-ACCESS  read-only
    STATUS      current
    DESCRIPTION
        "The value of vRtrIgmpGrpIfHostGrpBondOwner indicates the
         vRtrIgmpHostBondingConnIndex of the host that was the first to receive
         a join for this group.

         A value of 0 indicates this session is not part of a bonding context."
    ::= { vRtrIgmpGrpIfHostGrpEntry 12 }

vRtrIgmpGrpIfHostGrpBondFwd      OBJECT-TYPE
    SYNTAX      TruthValue
    MAX-ACCESS  read-only
    STATUS      current
    DESCRIPTION
        "The value of vRtrIgmpGrpIfHostGrpBondFwd indicates whether this host
         will be used to egress traffic for this group.

         This is only valid if vRtrIgmpHostGrpBondOwner is non zero."
    ::= { vRtrIgmpGrpIfHostGrpEntry 13 }

vRtrIgmpGrpIfHostGrpSrcTable     OBJECT-TYPE
    SYNTAX      SEQUENCE OF VRtrIgmpGrpIfHostGrpSrcEntry
    MAX-ACCESS  not-accessible
    STATUS      current
    DESCRIPTION
        "The table listing the IP multicast sources corresponding to the IP
         multicast groups for which there are members on a particular host.
         This table represents IGMP source, group database."
    ::= { vRtrIgmpHostObjs 5 }

vRtrIgmpGrpIfHostGrpSrcEntry     OBJECT-TYPE
    SYNTAX      VRtrIgmpGrpIfHostGrpSrcEntry
    MAX-ACCESS  not-accessible
    STATUS      current
    DESCRIPTION
        "An entry in the vRtrIgmpGrpIfHostGrpSrcTable. Each entry represents a
         source address from which receivers are interested/not interested in
         receiving multicast traffic from. "
    INDEX       {
        vRtrID,
        vRtrIfFwdSvcId,
        vRtrGrpIfIndex,
        vRtrIgmpHostAddress,
        vRtrIgmpHostGroupAddress,
        vRtrIgmpHostGrpSrcAddress
    }
    ::= { vRtrIgmpGrpIfHostGrpSrcTable 1 }

VRtrIgmpGrpIfHostGrpSrcEntry     ::= SEQUENCE
{
    vRtrIgmpHostGrpSrcAddress        IpAddress,
    vRtrIgmpGrpIfHostGrpSrcExpTime   TimeInterval,
    vRtrIgmpGrpIfHostGrpSrcType      TmnxIgmpGroupType,
    vRtrIgmpGrpIfHostGrpSrcMRDstVrId TmnxVRtrIDOrZero,
    vRtrIgmpGrpIfHostGrpSrcMRDstIfId InterfaceIndexOrZero,
    vRtrIgmpGrpIfHostGrpSrcBondOwner TruthValue,
    vRtrIgmpGrpIfHostGrpSrcBondFwd   TruthValue
}

vRtrIgmpHostGrpSrcAddress        OBJECT-TYPE
    SYNTAX      IpAddress
    MAX-ACCESS  not-accessible
    STATUS      current
    DESCRIPTION
        "The address of the source sending multicast traffic to the group
         identified by tmnxSubIgmpHostGroupAddress."
    ::= { vRtrIgmpGrpIfHostGrpSrcEntry 1 }

vRtrIgmpGrpIfHostGrpSrcExpTime   OBJECT-TYPE
    SYNTAX      TimeInterval
    MAX-ACCESS  read-only
    STATUS      current
    DESCRIPTION
        "The minimum amount of time remaining before this entry will be aged
         out. If the value of vRtrIgmpGrpIfHostGrpSrcExpTime is non-zero and
         the value of vRtrIgmpGrpIfHostGrpMode corresponding to this entry is
         'include', it means that there are currently one or more systems which
         desire to receive multicast traffic for this source. If this timer
         expires and the value of vRtrIgmpGrpIfHostGrpMode is 'include', the
         router concludes that traffic from this particular source is no longer
         desired on the attached network, and deletes this entry. This timer is
         treated differently when the value of vRtrIgmpGrpIfHostGrpMode is
         'exclude'. If the value of vRtrIgmpGrpIfHostGrpSrcExpTime is non-zero
         and router filter-mode for the group is 'exclude', it means that at
         least one system desires to receive multicast traffic from this
         source. It should therefore be forwarded by a router on the network."
    ::= { vRtrIgmpGrpIfHostGrpSrcEntry 2 }

vRtrIgmpGrpIfHostGrpSrcType      OBJECT-TYPE
    SYNTAX      TmnxIgmpGroupType
    MAX-ACCESS  read-only
    STATUS      current
    DESCRIPTION
        "vRtrIgmpGrpIfHostGrpSrcType indicates how this source entry was
         learned. If this source entry was learned by IGMP, it will be set to
         'dynamic'. For statically configured sources, the value will be set to
         'static'."
    ::= { vRtrIgmpGrpIfHostGrpSrcEntry 3 }

vRtrIgmpGrpIfHostGrpSrcMRDstVrId OBJECT-TYPE
    SYNTAX      TmnxVRtrIDOrZero
    MAX-ACCESS  read-only
    STATUS      current
    DESCRIPTION
        "The value of vRtrIgmpGrpIfHostGrpSrcMRDstVrId indicates the vRtrID of
         the service where to redirect IGMP multicast traffic to.

         The value zero means that no multicast redirection is configured."
    ::= { vRtrIgmpGrpIfHostGrpSrcEntry 4 }

vRtrIgmpGrpIfHostGrpSrcMRDstIfId OBJECT-TYPE
    SYNTAX      InterfaceIndexOrZero
    MAX-ACCESS  read-only
    STATUS      current
    DESCRIPTION
        "The value of vRtrIgmpGrpIfHostGrpSrcMRDstIfId indicates the interface
         index of the interface where to redirect IGMP multicast traffic to.

         The value zero means that no multicast redirection is configured."
    ::= { vRtrIgmpGrpIfHostGrpSrcEntry 5 }

vRtrIgmpGrpIfHostGrpSrcBondOwner OBJECT-TYPE
    SYNTAX      TruthValue
    MAX-ACCESS  read-only
    STATUS      current
    DESCRIPTION
        "The value of vRtrIgmpGrpIfHostGrpSrcBondOwner indicates the
         vRtrIgmpHostBondingConnIndex of the host that was the first to receive
         a join for this group.

         A value of 0 indicates this session is not part of a bonding context."
    ::= { vRtrIgmpGrpIfHostGrpSrcEntry 6 }

vRtrIgmpGrpIfHostGrpSrcBondFwd   OBJECT-TYPE
    SYNTAX      TruthValue
    MAX-ACCESS  read-only
    STATUS      current
    DESCRIPTION
        "The value of vRtrIgmpGrpIfHostGrpSrcBondFwd indicates whether this
         host will be used to egress traffic for this group.

         This is only valid if vRtrIgmpHostGrpBondOwner is non zero."
    ::= { vRtrIgmpGrpIfHostGrpSrcEntry 7 }

vRtrIgmpGrpSrcHostTable          OBJECT-TYPE
    SYNTAX      SEQUENCE OF VRtrIgmpGrpSrcHostEntry
    MAX-ACCESS  not-accessible
    STATUS      current
    DESCRIPTION
        "The table listing the IP multicast sources corresponding to the IP
         multicast groups per host. This table represents the host IGMP source,
         group database."
    ::= { vRtrIgmpHostObjs 6 }

vRtrIgmpGrpSrcHostEntry          OBJECT-TYPE
    SYNTAX      VRtrIgmpGrpSrcHostEntry
    MAX-ACCESS  not-accessible
    STATUS      current
    DESCRIPTION
        "An entry in the vRtrIgmpGrpSrcHostTable. Each entry represents a
         source address from which receivers are interested/not interested in
         receiving multicast traffic. "
    INDEX       {
        vRtrID,
        vRtrIgmpGrpSrcGroupAddress,
        vRtrIgmpGrpSrcSourceAddress,
        vRtrIgmpGrpSrcFwdOrBlk,
        vRtrIgmpHostAddress
    }
    ::= { vRtrIgmpGrpSrcHostTable 1 }

VRtrIgmpGrpSrcHostEntry          ::= SEQUENCE
{ vRtrIgmpGrpSrcHostUpTime         Unsigned32 }

vRtrIgmpGrpSrcHostUpTime         OBJECT-TYPE
    SYNTAX      Unsigned32
    UNITS       "seconds"
    MAX-ACCESS  read-only
    STATUS      current
    DESCRIPTION
        "vRtrIgmpGrpSrcHostUpTime indicates the time since this source group
         entry got created."
    ::= { vRtrIgmpGrpSrcHostEntry 1 }

vRtrIgmpHostGrpSrcTable          OBJECT-TYPE
    SYNTAX      SEQUENCE OF VRtrIgmpHostGrpSrcEntry
    MAX-ACCESS  not-accessible
    STATUS      current
    DESCRIPTION
        "The table listing the IP multicast sources corresponding to the IP
         multicast groups for which there are members on a particular host.
         This table represents IGMP host source, group database."
    ::= { vRtrIgmpHostObjs 7 }

vRtrIgmpHostGrpSrcEntry          OBJECT-TYPE
    SYNTAX      VRtrIgmpHostGrpSrcEntry
    MAX-ACCESS  not-accessible
    STATUS      current
    DESCRIPTION
        "An entry in the vRtrIgmpHostGrpSrcTable. Each entry represents a
         source address from which receivers are interested/not interested in
         receiving multicast traffic from. "
    INDEX       {
        vRtrID,
        vRtrIgmpHostAddress,
        vRtrIgmpHostGroupAddress,
        vRtrIgmpHostGrpSrcAddress
    }
    ::= { vRtrIgmpHostGrpSrcTable 1 }

VRtrIgmpHostGrpSrcEntry          ::= SEQUENCE
{
    vRtrIgmpHostGrpSrcExpiryTime     TimeInterval,
    vRtrIgmpHostGrpSrcType           TmnxIgmpGroupType,
    vRtrIgmpHostGrpSrcMcRdrDstVRtrID TmnxVRtrIDOrZero,
    vRtrIgmpHostGrpSrcMcRdrDstIfIdx  InterfaceIndexOrZero,
    vRtrIgmpHostGrpSrcBondOwner      TruthValue,
    vRtrIgmpHostGrpSrcBondFwd        TruthValue
}

vRtrIgmpHostGrpSrcExpiryTime     OBJECT-TYPE
    SYNTAX      TimeInterval
    MAX-ACCESS  read-only
    STATUS      current
    DESCRIPTION
        "The minimum amount of time remaining before this entry will be aged
         out. If the value of vRtrIgmpHostGrpSrcExpiryTime is non-zero and the
         value of vRtrIgmpIfGroupMode corresponding to this entry is 'include',
         it means that there are currently one or more systems which desire to
         receive multicast traffic for this source. If this timer expires and
         the value of vRtrIgmpIfGroupMode is 'include', the router concludes
         that traffic from this particular source is no longer desired on the
         attached network, and deletes this entry. This timer is treated
         differently when the value of vRtrIgmpIfGroupMode is 'exclude'. If the
         value of vRtrIgmpHostGrpSrcExpiryTime is non-zero and router
         filter-mode for the group is 'exclude', it means that at least one
         system desires to receive multicast traffic from this source. It
         should therefore be forwarded by a router on the network."
    ::= { vRtrIgmpHostGrpSrcEntry 1 }

vRtrIgmpHostGrpSrcType           OBJECT-TYPE
    SYNTAX      TmnxIgmpGroupType
    MAX-ACCESS  read-only
    STATUS      current
    DESCRIPTION
        "vRtrIgmpHostGrpSrcType indicates how this source entry was learned. If
         this source entry was learned by IGMP, it will be set to 'dynamic'.
         For statically configured sources, the value will be set to 'static'."
    ::= { vRtrIgmpHostGrpSrcEntry 2 }

vRtrIgmpHostGrpSrcMcRdrDstVRtrID OBJECT-TYPE
    SYNTAX      TmnxVRtrIDOrZero
    MAX-ACCESS  read-only
    STATUS      current
    DESCRIPTION
        "The value of vRtrIgmpHostGrpSrcMcRdrDstVRtrID indicates the vRtrID of
         the service where to redirect IGMP multicast traffic to.

         The value zero means that no multicast redirection is configured."
    ::= { vRtrIgmpHostGrpSrcEntry 3 }

vRtrIgmpHostGrpSrcMcRdrDstIfIdx  OBJECT-TYPE
    SYNTAX      InterfaceIndexOrZero
    MAX-ACCESS  read-only
    STATUS      current
    DESCRIPTION
        "The value of vRtrIgmpHostGrpSrcMcRdrDstIfIdx indicates the interface
         index of the interface where to redirect IGMP multicast traffic to.

         The value zero means that no multicast redirection is configured."
    ::= { vRtrIgmpHostGrpSrcEntry 4 }

vRtrIgmpHostGrpSrcBondOwner      OBJECT-TYPE
    SYNTAX      TruthValue
    MAX-ACCESS  read-only
    STATUS      current
    DESCRIPTION
        "The value of vRtrIgmpHostGrpSrcBondOwner indicates the
         vRtrIgmpHostBondingConnIndex of the host that was the first to receive
         a join for this group.

         A value of 0 indicates this session is not part of a bonding context."
    ::= { vRtrIgmpHostGrpSrcEntry 5 }

vRtrIgmpHostGrpSrcBondFwd        OBJECT-TYPE
    SYNTAX      TruthValue
    MAX-ACCESS  read-only
    STATUS      current
    DESCRIPTION
        "The value of vRtrIgmpHostGrpSrcBondFwd indicates whether this host
         will be used to egress traffic for this group.

         This is only valid if vRtrIgmpHostGrpBondOwner is non zero."
    ::= { vRtrIgmpHostGrpSrcEntry 6 }

vRtrIgmpHostGrpTable             OBJECT-TYPE
    SYNTAX      SEQUENCE OF VRtrIgmpHostGrpEntry
    MAX-ACCESS  not-accessible
    STATUS      current
    DESCRIPTION
        "The table listing the IP multicast groups for which there are members
         on a particular host. This table represents the IGMP group database."
    ::= { vRtrIgmpHostObjs 8 }

vRtrIgmpHostGrpEntry             OBJECT-TYPE
    SYNTAX      VRtrIgmpHostGrpEntry
    MAX-ACCESS  not-accessible
    STATUS      current
    DESCRIPTION
        "An entry in the vRtrIgmpHostGrpTable. Each entry represents a group
         address for which receivers are interested/not interested in receiving
         multicast traffic."
    INDEX       {
        vRtrID,
        vRtrIgmpHostAddress,
        vRtrIgmpHostGroupAddress
    }
    ::= { vRtrIgmpHostGrpTable 1 }

VRtrIgmpHostGrpEntry             ::= SEQUENCE
{
    vRtrIgmpHostGrpType              TmnxIgmpGroupType,
    vRtrIgmpHostGrpUpTime            TimeInterval,
    vRtrIgmpHostGrpExpiryTime        TimeInterval,
    vRtrIgmpHostGrpVer1HostTmr       TimeInterval,
    vRtrIgmpHostGrpMode              TmnxIgmpGroupFilterMode,
    vRtrIgmpHostGrpCompatMode        Unsigned32,
    vRtrIgmpHostGrpVer2HostTmr       TimeInterval,
    vRtrIgmpHostGrpMcRdrDstVrId      TmnxVRtrIDOrZero,
    vRtrIgmpHostGrpMcRdrDstIfId      InterfaceIndexOrZero,
    vRtrIgmpHostGrpBondOwner         TruthValue,
    vRtrIgmpHostGrpBondFwd           TruthValue
}

vRtrIgmpHostGrpType              OBJECT-TYPE
    SYNTAX      TmnxIgmpGroupType
    MAX-ACCESS  read-only
    STATUS      current
    DESCRIPTION
        "vRtrIgmpHostGrpType indicates how this group entry was learned. If
         this group entry was learned by IGMP, it will be set to 'dynamic'. For
         statically configured groups, the value will be set to 'static'."
    ::= { vRtrIgmpHostGrpEntry 1 }

vRtrIgmpHostGrpUpTime            OBJECT-TYPE
    SYNTAX      TimeInterval
    MAX-ACCESS  read-only
    STATUS      current
    DESCRIPTION
        "The time elapsed since this entry was created."
    ::= { vRtrIgmpHostGrpEntry 2 }

vRtrIgmpHostGrpExpiryTime        OBJECT-TYPE
    SYNTAX      TimeInterval
    MAX-ACCESS  read-only
    STATUS      current
    DESCRIPTION
        "The minimum amount of time remaining before this entry will be aged
         out. A value of 0 indicates that the entry is only present because
         igmpCacheSelf is true and that if the router left the group, this
         entry would be aged out immediately. Note that some implementations
         may process membership reports from the local system in the same way
         as reports from other hosts, so a value of 0 is not required."
    ::= { vRtrIgmpHostGrpEntry 3 }

vRtrIgmpHostGrpVer1HostTmr       OBJECT-TYPE
    SYNTAX      TimeInterval
    MAX-ACCESS  read-only
    STATUS      current
    DESCRIPTION
        "The time remaining until the local router will assume that
         there are no longer any IGMP version 1 members on the IP
         subnet attached to this host.  Upon hearing any IGMPv1
         Membership Report, this value is reset to the group
         membership timer.  While this time remaining is non-zero,
         the local router ignores any IGMPv2 Leave messages for this
         group that it receives on this host."
    ::= { vRtrIgmpHostGrpEntry 4 }

vRtrIgmpHostGrpMode              OBJECT-TYPE
    SYNTAX      TmnxIgmpGroupFilterMode
    MAX-ACCESS  read-only
    STATUS      current
    DESCRIPTION
        "vRtrIgmpHostGrpMode is based on the type of membership report(s)
         received on the host for the group. In the 'include' mode, reception
         of packets sent to the specified multicast address is requested only
         from those IP source addresses listed in the source-list parameter of
         the IGMP membership report. In 'exclude' mode, reception of packets
         sent to the given multicast address is requested from all IP source
         addresses except those listed in the source-list parameter.
         vRtrIgmpHostGrpSrcTable lists the sources corresponding to this group,
         if any."
    ::= { vRtrIgmpHostGrpEntry 5 }

vRtrIgmpHostGrpCompatMode        OBJECT-TYPE
    SYNTAX      Unsigned32
    MAX-ACCESS  read-only
    STATUS      current
    DESCRIPTION
        "vRtrIgmpHostGrpCompatMode is used in order for routers to be
         compatible with older version routers. IGMPv3 hosts MUST operate
         in version 1 and version 2 compatibility modes.  IGMPv3 hosts MUST
         keep state per local host regarding the compatibility mode of
         each attached network.  A host's compatibility mode is determined
         from the Host Compatibility Mode variable which can be in
         one of three states:  IGMPv1, IGMPv2 or IGMPv3.  This variable is
         kept per interface and is dependent on the version of General Queries
         heard on that host as well as the Older Version Querier Present
         timers for the host."
    ::= { vRtrIgmpHostGrpEntry 6 }

vRtrIgmpHostGrpVer2HostTmr       OBJECT-TYPE
    SYNTAX      TimeInterval
    MAX-ACCESS  read-only
    STATUS      current
    DESCRIPTION
        "The time remaining until the local router will assume that
         there are no longer any IGMP version 2 members on the IP
         subnet attached to this host.  Upon hearing any IGMPv2
         Membership Report, this value is reset to the group
         membership timer.  While this time remaining is non-zero,
         the local router ignores any IGMPv3 Leave messages for this
         group that it receives on this host."
    ::= { vRtrIgmpHostGrpEntry 7 }

vRtrIgmpHostGrpMcRdrDstVrId      OBJECT-TYPE
    SYNTAX      TmnxVRtrIDOrZero
    MAX-ACCESS  read-only
    STATUS      current
    DESCRIPTION
        "The value of vRtrIgmpHostGrpMcRdrDstVrId indicates the vRtrID of the
         service where to redirect IGMP multicast traffic to.

         The value zero means that no multicast redirection is configured."
    ::= { vRtrIgmpHostGrpEntry 8 }

vRtrIgmpHostGrpMcRdrDstIfId      OBJECT-TYPE
    SYNTAX      InterfaceIndexOrZero
    MAX-ACCESS  read-only
    STATUS      current
    DESCRIPTION
        "The value of vRtrIgmpHostGrpMcRdrDstIfId indicates the interface index
         of the interface where to redirect IGMP multicast traffic to.

         The value zero means that no multicast redirection is configured."
    ::= { vRtrIgmpHostGrpEntry 9 }

vRtrIgmpHostGrpBondOwner         OBJECT-TYPE
    SYNTAX      TruthValue
    MAX-ACCESS  read-only
    STATUS      current
    DESCRIPTION
        "The value of vRtrIgmpHostGrpBondOwner indicates the
         vRtrIgmpHostBondingConnIndex of the host that was the first to receive
         a join for this group.

         A value of 0 indicates this session is not part of a bonding context."
    ::= { vRtrIgmpHostGrpEntry 10 }

vRtrIgmpHostGrpBondFwd           OBJECT-TYPE
    SYNTAX      TruthValue
    MAX-ACCESS  read-only
    STATUS      current
    DESCRIPTION
        "The value of vRtrIgmpHostGrpBondFwd indicates whether this host will
         be used to egress traffic for this group.

         This is only valid if vRtrIgmpHostGrpBondOwner is non zero."
    ::= { vRtrIgmpHostGrpEntry 11 }

vRtrIgmpGrpIfHostTable           OBJECT-TYPE
    SYNTAX      SEQUENCE OF VRtrIgmpGrpIfHostEntry
    MAX-ACCESS  not-accessible
    STATUS      current
    DESCRIPTION
        "The table listing the IP multicast groups for which there are members
         on a particular host. This table represents the IGMP group interface
         database."
    ::= { vRtrIgmpHostObjs 9 }

vRtrIgmpGrpIfHostEntry           OBJECT-TYPE
    SYNTAX      VRtrIgmpGrpIfHostEntry
    MAX-ACCESS  not-accessible
    STATUS      current
    DESCRIPTION
        "An entry in the vRtrIgmpGrpIfHostTable. Each entry represents a host
         which is interested/not interested in receiving multicast traffic."
    INDEX       {
        vRtrID,
        vRtrIfFwdSvcId,
        vRtrGrpIfIndex,
        vRtrIgmpHostAddress
    }
    ::= { vRtrIgmpGrpIfHostTable 1 }

VRtrIgmpGrpIfHostEntry           ::= SEQUENCE
{
    vRtrIgmpGrpIfHostLastChangeTime  TimeStamp,
    vRtrIgmpGrpIfHostOperState       IgmpGrpItfOperState
}

vRtrIgmpGrpIfHostLastChangeTime  OBJECT-TYPE
    SYNTAX      TimeStamp
    MAX-ACCESS  read-only
    STATUS      current
    DESCRIPTION
        "The sysUpTime when this row was last modified."
    ::= { vRtrIgmpGrpIfHostEntry 1 }

vRtrIgmpGrpIfHostOperState       OBJECT-TYPE
    SYNTAX      IgmpGrpItfOperState
    MAX-ACCESS  read-only
    STATUS      current
    DESCRIPTION
        "The current operational state of IGMP protocol for this host."
    ::= { vRtrIgmpGrpIfHostEntry 2 }

vRtrIgmpHostMcRDstStatTable      OBJECT-TYPE
    SYNTAX      SEQUENCE OF VRtrIgmpHostMcRDstStatEntry
    MAX-ACCESS  not-accessible
    STATUS      current
    DESCRIPTION
        "The vRtrIgmpHostMcRDstStatTable shows mcast reporting destination
         statistics information for IGMP hosts."
    ::= { vRtrIgmpHostObjs 10 }

vRtrIgmpHostMcRDstStatEntry      OBJECT-TYPE
    SYNTAX      VRtrIgmpHostMcRDstStatEntry
    MAX-ACCESS  not-accessible
    STATUS      current
    DESCRIPTION
        "Each row entry represents mcast reporting destination statistics
         information for a particular IGMP host.

         Rows are created or removed automatically by the system.

         Rows are only created where the statistics value is nonzero; this
         allows faster walking through this table; hence, it is recommended to
         perform only get-next-request operations to retrieve information from
         this table."
    INDEX       {
        vRtrID,
        vRtrIgmpHostAddress,
        vRtrIgmpHostMcRDstStatType
    }
    ::= { vRtrIgmpHostMcRDstStatTable 1 }

VRtrIgmpHostMcRDstStatEntry      ::= SEQUENCE
{
    vRtrIgmpHostMcRDstStatType       VRtrIgmpHostMcRDstStatType,
    vRtrIgmpHostMcRDstStatVal        Counter32
}

vRtrIgmpHostMcRDstStatType       OBJECT-TYPE
    SYNTAX      VRtrIgmpHostMcRDstStatType
    MAX-ACCESS  not-accessible
    STATUS      current
    DESCRIPTION
        "The value of vRtrIgmpHostMcRDstStatType indicates the type of mcast
         reporting destination statistics contained in
         vRtrIgmpHostMcRDstStatVal."
    ::= { vRtrIgmpHostMcRDstStatEntry 1 }

vRtrIgmpHostMcRDstStatVal        OBJECT-TYPE
    SYNTAX      Counter32
    MAX-ACCESS  read-only
    STATUS      current
    DESCRIPTION
        "The value of vRtrIgmpHostMcRDstStatVal indicates the value of the
         mcast reporting destination statistics of the type indicated by
         vRtrIgmpHostMcRDstStatType."
    ::= { vRtrIgmpHostMcRDstStatEntry 2 }

vRtrIgmpGrpIfObjs                OBJECT IDENTIFIER ::= { tmnxIgmpObjs 5 }

vRtrIgmpGrpIfSapTable            OBJECT-TYPE
    SYNTAX      SEQUENCE OF VRtrIgmpGrpIfSapEntry
    MAX-ACCESS  not-accessible
    STATUS      current
    DESCRIPTION
        "The table listing the SAPs for which IGMP protocol operation is
         active."
    ::= { vRtrIgmpGrpIfObjs 1 }

vRtrIgmpGrpIfSapEntry            OBJECT-TYPE
    SYNTAX      VRtrIgmpGrpIfSapEntry
    MAX-ACCESS  not-accessible
    STATUS      current
    DESCRIPTION
        "Each row entry in the vRtrIgmpGrpIfSapTable represents a SAP on this
         router that participates in the IGMP protocol."
    INDEX       {
        vRtrID,
        vRtrIfFwdSvcId,
        vRtrGrpIfIndex,
        sapPortId,
        sapEncapValue
    }
    ::= { vRtrIgmpGrpIfSapTable 1 }

VRtrIgmpGrpIfSapEntry            ::= SEQUENCE
{
    vRtrIgmpGrpIfSapLastChangeTime   TimeStamp,
    vRtrIgmpGrpIfSapOperState        IgmpGrpItfOperState,
    vRtrIgmpGrpIfSapAdminVersion     Unsigned32,
    vRtrIgmpGrpIfSapOperVersion      Unsigned32,
    vRtrIgmpGrpIfSapGroupCount       Unsigned32,
    vRtrIgmpGrpIfSapNextGenQueryTime Unsigned32,
    vRtrIgmpGrpIfSapMaxGroups        Unsigned32,
    vRtrIgmpGrpIfSapMaxGroupsTillNow Counter32,
    vRtrIgmpGrpIfSapMaxSources       Unsigned32,
    vRtrIgmpGrpIfSapMaxGrpSources    Unsigned32,
    vRtrIgmpGrpIfSapQryInterval      Unsigned32,
    vRtrIgmpGrpIfSapLastMembQryIntvl Unsigned32,
    vRtrIgmpGrpIfSapQryResponseIntvl Unsigned32
}

vRtrIgmpGrpIfSapLastChangeTime   OBJECT-TYPE
    SYNTAX      TimeStamp
    MAX-ACCESS  read-only
    STATUS      current
    DESCRIPTION
        "The sysUpTime when this row was last modified."
    ::= { vRtrIgmpGrpIfSapEntry 1 }

vRtrIgmpGrpIfSapOperState        OBJECT-TYPE
    SYNTAX      IgmpGrpItfOperState
    MAX-ACCESS  read-only
    STATUS      current
    DESCRIPTION
        "The current operational state of IGMP protocol for this SAP."
    ::= { vRtrIgmpGrpIfSapEntry 2 }

vRtrIgmpGrpIfSapAdminVersion     OBJECT-TYPE
    SYNTAX      Unsigned32
    MAX-ACCESS  read-only
    STATUS      current
    DESCRIPTION
        "The configured version of IGMP which is running for this SAP.

         For IGMP to function correctly, all routers on a LAN must be
         configured to run the same version of IGMP on that LAN."
    DEFVAL      { 3 }
    ::= { vRtrIgmpGrpIfSapEntry 3 }

vRtrIgmpGrpIfSapOperVersion      OBJECT-TYPE
    SYNTAX      Unsigned32
    MAX-ACCESS  read-only
    STATUS      current
    DESCRIPTION
        "The operational version of IGMP which is running for this SAP.

         If the value of vRtrIgmpIfAdminVersion is configured as '3' but all of
         the routers in the local subnet of this interface use IGMP version v1
         or v2, the operational version will be v1 or v2."
    ::= { vRtrIgmpGrpIfSapEntry 4 }

vRtrIgmpGrpIfSapGroupCount       OBJECT-TYPE
    SYNTAX      Unsigned32
    MAX-ACCESS  read-only
    STATUS      current
    DESCRIPTION
        "vRtrIgmpGrpIfSapGroupCount is the number of multicast groups which
         have been learned by the router for this SAP."
    ::= { vRtrIgmpGrpIfSapEntry 5 }

vRtrIgmpGrpIfSapNextGenQueryTime OBJECT-TYPE
    SYNTAX      Unsigned32
    UNITS       "seconds"
    MAX-ACCESS  read-only
    STATUS      current
    DESCRIPTION
        "If this router is the querier (vRtrIgmpIfQuerier is a local address),
         vRtrIgmpGrpIfSapNextGenQueryTime is the time remaining before the
         general query is sent for this SAP.

         If this router is not the querier for the SAP, the value of this
         object will be zero."
    ::= { vRtrIgmpGrpIfSapEntry 6 }

vRtrIgmpGrpIfSapMaxGroups        OBJECT-TYPE
    SYNTAX      Unsigned32 (0 | 1..16000)
    MAX-ACCESS  read-only
    STATUS      current
    DESCRIPTION
        "The value of vRtrIgmpGrpIfSapMaxGroups specifies the maximum number of
         groups for which IGMP can have local receiver information based on
         received IGMP reports on this SAP.

         When this configuration is changed dynamically to a value lower than
         currently accepted number of groups, the groups that are already
         accepted are not deleted.

         Only new groups will not be allowed. When this object has a value of
         0, there is no limit to the number of groups."
    DEFVAL      { 0 }
    ::= { vRtrIgmpGrpIfSapEntry 7 }

vRtrIgmpGrpIfSapMaxGroupsTillNow OBJECT-TYPE
    SYNTAX      Counter32
    MAX-ACCESS  read-only
    STATUS      current
    DESCRIPTION
        "The value of vRtrIgmpGrpIfSapMaxGroupsTillNow indicates the highest
         value that vRtrIgmpGrpIfSapMaxGroups had till now."
    ::= { vRtrIgmpGrpIfSapEntry 8 }

vRtrIgmpGrpIfSapMaxSources       OBJECT-TYPE
    SYNTAX      Unsigned32 (0 | 1..1000)
    MAX-ACCESS  read-only
    STATUS      current
    DESCRIPTION
        "The value of vRtrIgmpGrpIfSapMaxSources specifies the maximum number
         of sources per group for which IGMP can have local receiver
         information based on received IGMP reports on this SAP.

         When this configuration is changed dynamically to a value lower than
         currently accepted number of sources, the sources that are already
         accepted are not deleted.

         Only new sources will not be allowed. When this object has a value of
         0, there is no limit to the number of sources."
    DEFVAL      { 0 }
    ::= { vRtrIgmpGrpIfSapEntry 9 }

vRtrIgmpGrpIfSapMaxGrpSources    OBJECT-TYPE
    SYNTAX      Unsigned32 (0 | 1..32000)
    MAX-ACCESS  read-only
    STATUS      current
    DESCRIPTION
        "The value of vRtrIgmpGrpIfSapMaxGrpSources specifies the maximum
         number of group sources per group for which IGMP can have local
         receiver information based on received IGMP reports on this SAP.

         When this configuration is changed dynamically to a value lower than
         currently accepted number of sources, the sources that are already
         accepted are not deleted.

         Only new sources will not be allowed. When this object has a value of
         0, there is no limit to the number of sources."
    DEFVAL      { 0 }
    ::= { vRtrIgmpGrpIfSapEntry 10 }

vRtrIgmpGrpIfSapQryInterval      OBJECT-TYPE
    SYNTAX      Unsigned32 (0 | 2..1024)
    UNITS       "seconds"
    MAX-ACCESS  read-only
    STATUS      current
    DESCRIPTION
        "The value of vRtrIgmpGrpIfSapQryInterval indicates the frequency at
         which the IGMP Host-Query packets are transmitted on this SAP."
    ::= { vRtrIgmpGrpIfSapEntry 11 }

vRtrIgmpGrpIfSapLastMembQryIntvl OBJECT-TYPE
    SYNTAX      Unsigned32 (0 | 1..1023)
    UNITS       "seconds"
    MAX-ACCESS  read-only
    STATUS      current
    DESCRIPTION
        "The value of vRtrIgmpGrpIfSapLastMembQryIntvl indicates the Max Response
         Time inserted into Group-Specific Queries sent in response to
         Leave Group messages, and is also the amount of time between
         Group-Specific Query messages.  This value may be tuned to
         modify the leave latency of the network.  A reduced value
         results in reduced time to detect the loss of the last
         member of a group."
    ::= { vRtrIgmpGrpIfSapEntry 12 }

vRtrIgmpGrpIfSapQryResponseIntvl OBJECT-TYPE
    SYNTAX      Unsigned32 (0 | 1..1023)
    UNITS       "seconds"
    MAX-ACCESS  read-only
    STATUS      current
    DESCRIPTION
        "The value of vRtrIgmpGrpIfSapQryResponseIntvl indicates the maximum
         query response time advertised in Igmpv2 queries on this SAP."
    ::= { vRtrIgmpGrpIfSapEntry 13 }

vRtrIgmpGrpIfSapStatsTable       OBJECT-TYPE
    SYNTAX      SEQUENCE OF VRtrIgmpGrpIfSapStatsEntry
    MAX-ACCESS  not-accessible
    STATUS      current
    DESCRIPTION
        "The table listing the IGMP statistics for a particular SAP on a
         group-interface."
    ::= { vRtrIgmpGrpIfObjs 2 }

vRtrIgmpGrpIfSapStatsEntry       OBJECT-TYPE
    SYNTAX      VRtrIgmpGrpIfSapStatsEntry
    MAX-ACCESS  not-accessible
    STATUS      current
    DESCRIPTION
        "An entry in the vRtrIgmpGrpIfSapStatsTable."
    INDEX       {
        vRtrID,
        vRtrIfFwdSvcId,
        vRtrGrpIfIndex,
        sapPortId,
        sapEncapValue
    }
    ::= { vRtrIgmpGrpIfSapStatsTable 1 }

VRtrIgmpGrpIfSapStatsEntry       ::= SEQUENCE
{
    vRtrIgmpGrpIfSapTxGenQueries     Counter32,
    vRtrIgmpGrpIfSapTxGrpQueries     Counter32,
    vRtrIgmpGrpIfSapTxGrpSrcQueries  Counter32,
    vRtrIgmpGrpIfSapTxV1Reports      Counter32,
    vRtrIgmpGrpIfSapTxV2Reports      Counter32,
    vRtrIgmpGrpIfSapTxV3Reports      Counter32,
    vRtrIgmpGrpIfSapTxLeaves         Counter32,
    vRtrIgmpGrpIfSapTxErrors         Counter32,
    vRtrIgmpGrpIfSapRxGenQueries     Counter32,
    vRtrIgmpGrpIfSapRxGrpQueries     Counter32,
    vRtrIgmpGrpIfSapRxGrpSrcQueries  Counter32,
    vRtrIgmpGrpIfSapRxV1Reports      Counter32,
    vRtrIgmpGrpIfSapRxV2Reports      Counter32,
    vRtrIgmpGrpIfSapRxV3Reports      Counter32,
    vRtrIgmpGrpIfSapRxLeaves         Counter32,
    vRtrIgmpGrpIfSapRxBadLenPkts     Counter32,
    vRtrIgmpGrpIfSapRxBadChksumPkts  Counter32,
    vRtrIgmpGrpIfSapRxUnknTypePkts   Counter32,
    vRtrIgmpGrpIfSapRxBadRecvIfPkts  Counter32,
    vRtrIgmpGrpIfSapRxNonLocal       Counter32,
    vRtrIgmpGrpIfSapRxWrongVersions  Counter32,
    vRtrIgmpGrpIfSapImportPlcyDrops  Counter32,
    vRtrIgmpGrpIfSapRxNoRtrAlertPkts Counter32,
    vRtrIgmpGrpIfSapRxBadEncodings   Counter32,
    vRtrIgmpGrpIfSapRxPktDrops       Counter32,
    vRtrIgmpGrpIfSapStatsStarGTypes  Gauge32,
    vRtrIgmpGrpIfSapStatsSGTypes     Gauge32,
    vRtrIgmpGrpIfSapStatsMcacPlcyDrp Counter32,
    vRtrIgmpGrpIfSapRxLocalScopePkts Counter32,
    vRtrIgmpGrpIfSapRxRsvdScopePkts  Counter32
}

vRtrIgmpGrpIfSapTxGenQueries     OBJECT-TYPE
    SYNTAX      Counter32
    MAX-ACCESS  read-only
    STATUS      current
    DESCRIPTION
        "The value of vRtrIgmpGrpIfSapTxGenQueries indicates the number of IGMP
         General Queries transmitted for this SAP."
    ::= { vRtrIgmpGrpIfSapStatsEntry 1 }

vRtrIgmpGrpIfSapTxGrpQueries     OBJECT-TYPE
    SYNTAX      Counter32
    MAX-ACCESS  read-only
    STATUS      current
    DESCRIPTION
        "The value of vRtrIgmpGrpIfSapTxGrpQueries indicates the number of IGMP
         Group Specific Queries transmitted for this SAP."
    ::= { vRtrIgmpGrpIfSapStatsEntry 2 }

vRtrIgmpGrpIfSapTxGrpSrcQueries  OBJECT-TYPE
    SYNTAX      Counter32
    MAX-ACCESS  read-only
    STATUS      current
    DESCRIPTION
        "The value of vRtrIgmpGrpIfSapTxGrpSrcQueries indicates the number of
         IGMP Group and Source Specific Queries transmitted for this SAP."
    ::= { vRtrIgmpGrpIfSapStatsEntry 3 }

vRtrIgmpGrpIfSapTxV1Reports      OBJECT-TYPE
    SYNTAX      Counter32
    MAX-ACCESS  read-only
    STATUS      current
    DESCRIPTION
        "The value of vRtrIgmpGrpIfSapTxV1Reports indicates the total number of
         IGMP V1 Reports transmitted for this SAP."
    ::= { vRtrIgmpGrpIfSapStatsEntry 4 }

vRtrIgmpGrpIfSapTxV2Reports      OBJECT-TYPE
    SYNTAX      Counter32
    MAX-ACCESS  read-only
    STATUS      current
    DESCRIPTION
        "The value of vRtrIgmpGrpIfSapTxV2Reports indicates the total number of
         IGMP V2 Reports transmitted for this SAP."
    ::= { vRtrIgmpGrpIfSapStatsEntry 5 }

vRtrIgmpGrpIfSapTxV3Reports      OBJECT-TYPE
    SYNTAX      Counter32
    MAX-ACCESS  read-only
    STATUS      current
    DESCRIPTION
        "The value of vRtrIgmpGrpIfSapTxV3Reports indicates the total number of
         IGMP V3 Reports transmitted for this SAP."
    ::= { vRtrIgmpGrpIfSapStatsEntry 6 }

vRtrIgmpGrpIfSapTxLeaves         OBJECT-TYPE
    SYNTAX      Counter32
    MAX-ACCESS  read-only
    STATUS      current
    DESCRIPTION
        "The value of vRtrIgmpGrpIfSapTxLeaves indicates the total number of
         IGMP Leaves transmitted for this SAP."
    ::= { vRtrIgmpGrpIfSapStatsEntry 7 }

vRtrIgmpGrpIfSapTxErrors         OBJECT-TYPE
    SYNTAX      Counter32
    MAX-ACCESS  read-only
    STATUS      current
    DESCRIPTION
        "The value of vRtrIgmpGrpIfSapTxErrors indicates the total number of
         times there was an error transmitting IGMP packets for this SAP."
    ::= { vRtrIgmpGrpIfSapStatsEntry 8 }

vRtrIgmpGrpIfSapRxGenQueries     OBJECT-TYPE
    SYNTAX      Counter32
    MAX-ACCESS  read-only
    STATUS      current
    DESCRIPTION
        "The value of vRtrIgmpGrpIfSapRxGenQueries indicates the total number
         of IGMP General Queries received for this SAP."
    ::= { vRtrIgmpGrpIfSapStatsEntry 9 }

vRtrIgmpGrpIfSapRxGrpQueries     OBJECT-TYPE
    SYNTAX      Counter32
    MAX-ACCESS  read-only
    STATUS      current
    DESCRIPTION
        "The value of vRtrIgmpGrpIfSapRxGrpQueries indicates the number of IGMP
         Group Specific Queries received for this SAP."
    ::= { vRtrIgmpGrpIfSapStatsEntry 10 }

vRtrIgmpGrpIfSapRxGrpSrcQueries  OBJECT-TYPE
    SYNTAX      Counter32
    MAX-ACCESS  read-only
    STATUS      current
    DESCRIPTION
        "The value of vRtrIgmpGrpIfSapRxGrpSrcQueries indicates the number of
         IGMP Group and Source Specific Queries received for this SAP."
    ::= { vRtrIgmpGrpIfSapStatsEntry 11 }

vRtrIgmpGrpIfSapRxV1Reports      OBJECT-TYPE
    SYNTAX      Counter32
    MAX-ACCESS  read-only
    STATUS      current
    DESCRIPTION
        "The value of vRtrIgmpGrpIfSapRxV1Reports indicates the total number of
         IGMP V1 Reports received for this SAP."
    ::= { vRtrIgmpGrpIfSapStatsEntry 12 }

vRtrIgmpGrpIfSapRxV2Reports      OBJECT-TYPE
    SYNTAX      Counter32
    MAX-ACCESS  read-only
    STATUS      current
    DESCRIPTION
        "The value of vRtrIgmpGrpIfSapRxV2Reports indicates the total number of
         IGMP V2 Reports received for this SAP."
    ::= { vRtrIgmpGrpIfSapStatsEntry 13 }

vRtrIgmpGrpIfSapRxV3Reports      OBJECT-TYPE
    SYNTAX      Counter32
    MAX-ACCESS  read-only
    STATUS      current
    DESCRIPTION
        "The value of vRtrIgmpGrpIfSapRxV3Reports indicates the total number of
         IGMP V3 Reports received for this SAP."
    ::= { vRtrIgmpGrpIfSapStatsEntry 14 }

vRtrIgmpGrpIfSapRxLeaves         OBJECT-TYPE
    SYNTAX      Counter32
    MAX-ACCESS  read-only
    STATUS      current
    DESCRIPTION
        "The value of vRtrIgmpGrpIfSapRxLeaves indicates the total number of
         IGMP V2 Leaves received for this SAP."
    ::= { vRtrIgmpGrpIfSapStatsEntry 15 }

vRtrIgmpGrpIfSapRxBadLenPkts     OBJECT-TYPE
    SYNTAX      Counter32
    MAX-ACCESS  read-only
    STATUS      current
    DESCRIPTION
        "The value of vRtrIgmpGrpIfSapRxBadLenPkts indicates the total number
         of IGMP packets with bad length received for this SAP."
    ::= { vRtrIgmpGrpIfSapStatsEntry 16 }

vRtrIgmpGrpIfSapRxBadChksumPkts  OBJECT-TYPE
    SYNTAX      Counter32
    MAX-ACCESS  read-only
    STATUS      current
    DESCRIPTION
        "The value of vRtrIgmpGrpIfSapRxBadChksumPkts indicates the total
         number of IGMP packets with bad checksum received for this SAP."
    ::= { vRtrIgmpGrpIfSapStatsEntry 17 }

vRtrIgmpGrpIfSapRxUnknTypePkts   OBJECT-TYPE
    SYNTAX      Counter32
    MAX-ACCESS  read-only
    STATUS      current
    DESCRIPTION
        "The value of vRtrIgmpGrpIfSapRxUnknTypePkts indicates the total number
         of IGMP packets with unknown type received for this SAP."
    ::= { vRtrIgmpGrpIfSapStatsEntry 18 }

vRtrIgmpGrpIfSapRxBadRecvIfPkts  OBJECT-TYPE
    SYNTAX      Counter32
    MAX-ACCESS  read-only
    STATUS      current
    DESCRIPTION
        "The value of vRtrIgmpGrpIfSapRxBadRecvIfPkts indicates the total
         number of IGMP packets incorrectly received for this SAP."
    ::= { vRtrIgmpGrpIfSapStatsEntry 19 }

vRtrIgmpGrpIfSapRxNonLocal       OBJECT-TYPE
    SYNTAX      Counter32
    MAX-ACCESS  read-only
    STATUS      current
    DESCRIPTION
        "The value of vRtrIgmpGrpIfSapRxNonLocal indicates the total number of
         IGMP packets received from a non-local sender."
    ::= { vRtrIgmpGrpIfSapStatsEntry 20 }

vRtrIgmpGrpIfSapRxWrongVersions  OBJECT-TYPE
    SYNTAX      Counter32
    MAX-ACCESS  read-only
    STATUS      current
    DESCRIPTION
        "The value of vRtrIgmpGrpIfSapRxWrongVersions indicates the total
         number of IGMP packets with wrong versions received for this SAP."
    ::= { vRtrIgmpGrpIfSapStatsEntry 21 }

vRtrIgmpGrpIfSapImportPlcyDrops  OBJECT-TYPE
    SYNTAX      Counter32
    MAX-ACCESS  read-only
    STATUS      current
    DESCRIPTION
        "The value of vRtrIgmpGrpIfSapImportPlcyDrops indicates the total
         number of times IGMP protocol instance matched the host IP address or
         group/source addresses specified in the import policy
         tmnxSubIgmpPlcyImportPolicy."
    ::= { vRtrIgmpGrpIfSapStatsEntry 22 }

vRtrIgmpGrpIfSapRxNoRtrAlertPkts OBJECT-TYPE
    SYNTAX      Counter32
    MAX-ACCESS  read-only
    STATUS      current
    DESCRIPTION
        "The value of vRtrIgmpGrpIfSapRxNoRtrAlertPkts indicates the total
         number of IGMPv3 packets received for this SAP which did not have the
         router alert flag set."
    ::= { vRtrIgmpGrpIfSapStatsEntry 23 }

vRtrIgmpGrpIfSapRxBadEncodings   OBJECT-TYPE
    SYNTAX      Counter32
    MAX-ACCESS  read-only
    STATUS      current
    DESCRIPTION
        "The value of vRtrIgmpGrpIfSapRxBadEncodings indicates the total number
         of IGMP packets received for this SAP which were not encoded
         correctly."
    ::= { vRtrIgmpGrpIfSapStatsEntry 24 }

vRtrIgmpGrpIfSapRxPktDrops       OBJECT-TYPE
    SYNTAX      Counter32
    MAX-ACCESS  read-only
    STATUS      current
    DESCRIPTION
        "The value of vRtrIgmpGrpIfSapRxPktDrops indicates the total number of
         IGMP packets that were received for this SAP but were dropped."
    ::= { vRtrIgmpGrpIfSapStatsEntry 25 }

vRtrIgmpGrpIfSapStatsStarGTypes  OBJECT-TYPE
    SYNTAX      Gauge32
    MAX-ACCESS  read-only
    STATUS      current
    DESCRIPTION
        "vRtrIgmpGrpIfSapStatsStarGTypes indicates the number of entries for
         this SAP for which the source type is 'starG'."
    ::= { vRtrIgmpGrpIfSapStatsEntry 26 }

vRtrIgmpGrpIfSapStatsSGTypes     OBJECT-TYPE
    SYNTAX      Gauge32
    MAX-ACCESS  read-only
    STATUS      current
    DESCRIPTION
        "The value of vRtrIgmpGrpIfSapStatsSGTypes indicates the number of
         entries for this SAP for which the source type is 'sg'."
    ::= { vRtrIgmpGrpIfSapStatsEntry 27 }

vRtrIgmpGrpIfSapStatsMcacPlcyDrp OBJECT-TYPE
    SYNTAX      Counter32
    MAX-ACCESS  read-only
    STATUS      current
    DESCRIPTION
        "The value of the object vRtrIgmpGrpIfSapStatsMcacPlcyDrp indicates the
         number times an IGMP Group is dropped because of applying a multicast
         CAC policy for this SAP."
    ::= { vRtrIgmpGrpIfSapStatsEntry 28 }

vRtrIgmpGrpIfSapRxLocalScopePkts OBJECT-TYPE
    SYNTAX      Counter32
    MAX-ACCESS  read-only
    STATUS      current
    DESCRIPTION
        "The value of the object vRtrIgmpGrpIfSapRxLocalScopePkts indicates the
         number of IGMP packets received on the link-local scope IPv4 multicast
         address."
    ::= { vRtrIgmpGrpIfSapStatsEntry 29 }

vRtrIgmpGrpIfSapRxRsvdScopePkts  OBJECT-TYPE
    SYNTAX      Counter32
    MAX-ACCESS  read-only
    STATUS      current
    DESCRIPTION
        "The value of the object vRtrIgmpGrpIfSapRxRsvdScopePkts indicates the
         number of IGMP packets received on the reserved scope IPv4 multicast
         address."
    ::= { vRtrIgmpGrpIfSapStatsEntry 30 }

vRtrIgmpGrpIfSapGrpTable         OBJECT-TYPE
    SYNTAX      SEQUENCE OF VRtrIgmpGrpIfSapGrpEntry
    MAX-ACCESS  not-accessible
    STATUS      current
    DESCRIPTION
        "The table listing the IP multicast groups for which there are members
         on a particular SAP. This table represents the IGMP group database."
    ::= { vRtrIgmpGrpIfObjs 3 }

vRtrIgmpGrpIfSapGrpEntry         OBJECT-TYPE
    SYNTAX      VRtrIgmpGrpIfSapGrpEntry
    MAX-ACCESS  not-accessible
    STATUS      current
    DESCRIPTION
        "An entry in the vRtrIgmpGrpIfSapGrpTable. Each entry represents a
         group address for which receivers are interested/not interested in
         receiving multicast traffic."
    INDEX       {
        vRtrID,
        vRtrIfFwdSvcId,
        vRtrGrpIfIndex,
        sapPortId,
        sapEncapValue,
        vRtrIgmpGrpIfSapGroupAddress
    }
    ::= { vRtrIgmpGrpIfSapGrpTable 1 }

VRtrIgmpGrpIfSapGrpEntry         ::= SEQUENCE
{
    vRtrIgmpGrpIfSapGroupAddress     IpAddress,
    vRtrIgmpGrpIfSapGrpType          TmnxIgmpGroupType,
    vRtrIgmpGrpIfSapGrpUpTime        TimeInterval,
    vRtrIgmpGrpIfSapGrpExpiryTime    TimeInterval,
    vRtrIgmpGrpIfSapGrpVer1HostTmr   TimeInterval,
    vRtrIgmpGrpIfSapGrpMode          TmnxIgmpGroupFilterMode,
    vRtrIgmpGrpIfSapGrpCompatMode    Unsigned32,
    vRtrIgmpGrpIfSapGrpVer2HostTmr   TimeInterval
}

vRtrIgmpGrpIfSapGroupAddress     OBJECT-TYPE
    SYNTAX      IpAddress
    MAX-ACCESS  not-accessible
    STATUS      current
    DESCRIPTION
        "The IP multicast group address for which this entry contains
         information."
    ::= { vRtrIgmpGrpIfSapGrpEntry 1 }

vRtrIgmpGrpIfSapGrpType          OBJECT-TYPE
    SYNTAX      TmnxIgmpGroupType
    MAX-ACCESS  read-only
    STATUS      current
    DESCRIPTION
        "vRtrIgmpGrpIfSapGrpType indicates how this group entry was learned. If
         this group entry was learned by IGMP, it will be set to 'dynamic'. For
         statically configured groups, the value will be set to 'static'."
    ::= { vRtrIgmpGrpIfSapGrpEntry 2 }

vRtrIgmpGrpIfSapGrpUpTime        OBJECT-TYPE
    SYNTAX      TimeInterval
    MAX-ACCESS  read-only
    STATUS      current
    DESCRIPTION
        "The time elapsed since this entry was created."
    ::= { vRtrIgmpGrpIfSapGrpEntry 3 }

vRtrIgmpGrpIfSapGrpExpiryTime    OBJECT-TYPE
    SYNTAX      TimeInterval
    MAX-ACCESS  read-only
    STATUS      current
    DESCRIPTION
        "The minimum amount of time remaining before this entry will be aged
         out. A value of 0 indicates that the entry is only present because
         igmpCacheSelf is true and that if the router left the group, this
         entry would be aged out immediately.

         Note that some implementations may process membership reports from the
         local system in the same way as reports from other SAPs, so a value of
         0 is not required."
    ::= { vRtrIgmpGrpIfSapGrpEntry 4 }

vRtrIgmpGrpIfSapGrpVer1HostTmr   OBJECT-TYPE
    SYNTAX      TimeInterval
    MAX-ACCESS  read-only
    STATUS      current
    DESCRIPTION
        "The time remaining until the local router will assume that
         there are no longer any IGMP version 1 members on the IP
         subnet attached to this SAP.  Upon hearing any IGMPv1
         Membership Report, this value is reset to the group
         membership timer.  While this time remaining is non-zero,
         the local router ignores any IGMPv2 Leave messages for this
         group that it receives on this SAP."
    ::= { vRtrIgmpGrpIfSapGrpEntry 5 }

vRtrIgmpGrpIfSapGrpMode          OBJECT-TYPE
    SYNTAX      TmnxIgmpGroupFilterMode
    MAX-ACCESS  read-only
    STATUS      current
    DESCRIPTION
        "vRtrIgmpGrpIfHostGrpMode is based on the type of membership report(s)
         received on the SAP for the group. In the 'include' mode, reception of
         packets sent to the specified multicast address is requested only from
         those IP source addresses listed in the source-list parameter of the
         IGMP membership report.

         In 'exclude' mode, reception of packets sent to the given multicast
         address is requested from all IP source addresses except those listed
         in the source-list parameter.

         vRtrIgmpGrpIfSapGrpSrcTable lists the sources corresponding to this
         group, if any."
    ::= { vRtrIgmpGrpIfSapGrpEntry 6 }

vRtrIgmpGrpIfSapGrpCompatMode    OBJECT-TYPE
    SYNTAX      Unsigned32
    MAX-ACCESS  read-only
    STATUS      current
    DESCRIPTION
        "vRtrIgmpGrpIfSapGrpCompatMode is used in order for routers to be
         compatible with older version routers. IGMPv3 hosts MUST operate
         in version 1 and version 2 compatibility modes.  IGMPv3 SAPs MUST
         keep state per local SAP regarding the compatibility mode of
         each attached network.  A SAPs compatibility mode is determined
         from the Host Compatibility Mode variable which can be in
         one of three states:  IGMPv1, IGMPv2 or IGMPv3.  This variable is
         kept per interface and is dependent on the version of General Queries
         heard on that SAP as well as the Older Version Querier Present
         timers for the SAP."
    ::= { vRtrIgmpGrpIfSapGrpEntry 7 }

vRtrIgmpGrpIfSapGrpVer2HostTmr   OBJECT-TYPE
    SYNTAX      TimeInterval
    MAX-ACCESS  read-only
    STATUS      current
    DESCRIPTION
        "The time remaining until the local router will assume that
         there are no longer any IGMP version 2 members on the IP
         subnet attached to this SAP.  Upon hearing any IGMPv2
         Membership Report, this value is reset to the group
         membership timer.  While this time remaining is non-zero,
         the local router ignores any IGMPv3 Leave messages for this
         group that it receives on this SAP."
    ::= { vRtrIgmpGrpIfSapGrpEntry 8 }

vRtrIgmpGrpIfSapGrpSrcTable      OBJECT-TYPE
    SYNTAX      SEQUENCE OF VRtrIgmpGrpIfSapGrpSrcEntry
    MAX-ACCESS  not-accessible
    STATUS      current
    DESCRIPTION
        "The table listing the IP multicast sources corresponding to the IP
         multicast groups for which there are members on a particular SAP. This
         table represents IGMP source, group database."
    ::= { vRtrIgmpGrpIfObjs 4 }

vRtrIgmpGrpIfSapGrpSrcEntry      OBJECT-TYPE
    SYNTAX      VRtrIgmpGrpIfSapGrpSrcEntry
    MAX-ACCESS  not-accessible
    STATUS      current
    DESCRIPTION
        "An entry in the vRtrIgmpGrpIfSapGrpSrcTable. Each entry represents a
         source address from which receivers are interested/not interested in
         receiving multicast traffic from."
    INDEX       {
        vRtrID,
        vRtrIfFwdSvcId,
        vRtrGrpIfIndex,
        sapPortId,
        sapEncapValue,
        vRtrIgmpGrpIfSapGroupAddress,
        vRtrIgmpGrpIfSapGrpSrcAddress
    }
    ::= { vRtrIgmpGrpIfSapGrpSrcTable 1 }

VRtrIgmpGrpIfSapGrpSrcEntry      ::= SEQUENCE
{
    vRtrIgmpGrpIfSapGrpSrcAddress    IpAddress,
    vRtrIgmpGrpIfSapGrpSrcExpTime    TimeInterval,
    vRtrIgmpGrpIfSapGrpSrcType       TmnxIgmpGroupType
}

vRtrIgmpGrpIfSapGrpSrcAddress    OBJECT-TYPE
    SYNTAX      IpAddress
    MAX-ACCESS  not-accessible
    STATUS      current
    DESCRIPTION
        "The address of the source sending multicast traffic to the group
         identified by vRtrIgmpGrpIfSapGroupAddress."
    ::= { vRtrIgmpGrpIfSapGrpSrcEntry 1 }

vRtrIgmpGrpIfSapGrpSrcExpTime    OBJECT-TYPE
    SYNTAX      TimeInterval
    MAX-ACCESS  read-only
    STATUS      current
    DESCRIPTION
        "The minimum amount of time remaining before this entry will be aged
         out. If the value of vRtrIgmpGrpIfSapGrpSrcExpTime is non-zero and the
         value of vRtrIgmpGrpIfSapGrpMode corresponding to this entry is
         'include', it means that there are currently one or more systems which
         desire to receive multicast traffic for this source. If this timer
         expires and the value of vRtrIgmpGrpIfHostGrpMode is 'include', the
         router concludes that traffic from this particular source is no longer
         desired on the attached network, and deletes this entry.

         This timer is treated differently when the value of
         vRtrIgmpGrpIfSapGrpMode is 'exclude'. If the value of
         vRtrIgmpGrpIfSapGrpSrcExpTime is non-zero and router filter-mode for
         the group is 'exclude', it means that at least one system desires to
         receive multicast traffic from this source. It should therefore be
         forwarded by a router on the network."
    ::= { vRtrIgmpGrpIfSapGrpSrcEntry 2 }

vRtrIgmpGrpIfSapGrpSrcType       OBJECT-TYPE
    SYNTAX      TmnxIgmpGroupType
    MAX-ACCESS  read-only
    STATUS      current
    DESCRIPTION
        "vRtrIgmpGrpIfSapGrpSrcType indicates how this source entry was
         learned. If this source entry was learned by IGMP, it will be set to
         'dynamic'. For statically configured sources, the value will be set to
         'static'."
    ::= { vRtrIgmpGrpIfSapGrpSrcEntry 3 }

vRtrIgmpGrpSrcGrpIfSapTable      OBJECT-TYPE
    SYNTAX      SEQUENCE OF VRtrIgmpGrpSrcGrpIfSapEntry
    MAX-ACCESS  not-accessible
    STATUS      current
    DESCRIPTION
        "The table listing the IP multicast sources corresponding to the IP
         multicast groups per SAP. This table represents the host IGMP source,
         group database."
    ::= { vRtrIgmpGrpIfObjs 5 }

vRtrIgmpGrpSrcGrpIfSapEntry      OBJECT-TYPE
    SYNTAX      VRtrIgmpGrpSrcGrpIfSapEntry
    MAX-ACCESS  not-accessible
    STATUS      current
    DESCRIPTION
        "An entry in the vRtrIgmpGrpSrcGrpIfSapTable. Each entry represents a
         source address from which receivers are interested/not interested in
         receiving multicast traffic. "
    INDEX       {
        vRtrID,
        vRtrIgmpGrpSrcGroupAddress,
        vRtrIgmpGrpSrcSourceAddress,
        vRtrIgmpGrpSrcFwdOrBlk,
        vRtrIfFwdSvcId,
        vRtrGrpIfIndex,
        sapPortId,
        sapEncapValue
    }
    ::= { vRtrIgmpGrpSrcGrpIfSapTable 1 }

VRtrIgmpGrpSrcGrpIfSapEntry      ::= SEQUENCE
{ vRtrIgmpGrpSrcGrpIfSapUpTime     Unsigned32 }

vRtrIgmpGrpSrcGrpIfSapUpTime     OBJECT-TYPE
    SYNTAX      Unsigned32
    UNITS       "seconds"
    MAX-ACCESS  read-only
    STATUS      current
    DESCRIPTION
        "vRtrIgmpGrpSrcGrpIfSapUpTime indicates the time since this source
         group entry got created."
    ::= { vRtrIgmpGrpSrcGrpIfSapEntry 1 }

tmnxIgmpConformance              OBJECT IDENTIFIER ::= { tmnxSRConfs 23 }

tmnxIgmpCompliances              OBJECT IDENTIFIER ::= { tmnxIgmpConformance 1 }

tmnxIgmpCompliance               MODULE-COMPLIANCE
    STATUS      obsolete
    DESCRIPTION
        "The compliance statement for management of extended IGMP protocol on
         Nokia SROS series systems."
    MODULE
        MANDATORY-GROUPS {
            tmnxIgmpGlobalGroup,
            tmnxIgmpNotificationGroup,
            tmnxIgmpIfV4v0Group
        }
    ::= { tmnxIgmpCompliances 1 }

tmnxIgmpV5v0Compliance           MODULE-COMPLIANCE
    STATUS      obsolete
    DESCRIPTION
        "The compliance statement for management of extended IGMP protocol on
         Nokia SROS series systems."
    MODULE
        MANDATORY-GROUPS {
            tmnxIgmpGlobalGroup,
            tmnxIgmpNotificationV5v0Group,
            tmnxIgmpIfV5v0Group
        }
    ::= { tmnxIgmpCompliances 2 }

tmnxIgmpV6v1Compliance           MODULE-COMPLIANCE
    STATUS      obsolete
    DESCRIPTION
        "The compliance statement for management of extended IGMP protocol on
         Nokia SROS series systems."
    MODULE
        MANDATORY-GROUPS {
            tmnxIgmpGlobalGroup,
            tmnxIgmpNotificationV5v0Group,
            tmnxIgmpIfV5v0Group,
            tmnxIgmpIfV6v1Group
        }
    ::= { tmnxIgmpCompliances 3 }

tmnxIgmpV7v0Compliance           MODULE-COMPLIANCE
    STATUS      obsolete
    DESCRIPTION
        "The compliance statement for management of extended IGMP protocol on
         Nokia SROS series systems."
    MODULE
        MANDATORY-GROUPS {
            tmnxIgmpGlobalGroup,
            tmnxIgmpNotificationV5v0Group,
            tmnxIgmpIfV5v0Group,
            tmnxIgmpIfV6v1Group,
            tmnxIgmpIfV7v0Group
        }
    ::= { tmnxIgmpCompliances 4 }

tmnxIgmpV8v0Compliance           MODULE-COMPLIANCE
    STATUS      obsolete
    DESCRIPTION
        "The compliance statement for management of extended IGMP protocol on
         Nokia SROS series systems."
    MODULE
        MANDATORY-GROUPS {
            tmnxIgmpGlobalGroup,
            tmnxIgmpNotificationV8v0Group,
            tmnxIgmpIfV5v0Group,
            tmnxIgmpIfV6v1Group,
            tmnxIgmpIfV7v0Group,
            tmnxIgmpIfV8v0Group
        }
    ::= { tmnxIgmpCompliances 5 }

tmnxIgmpV9v0Compliance           MODULE-COMPLIANCE
    STATUS      obsolete
    DESCRIPTION
        "The compliance statement for management of extended IGMP protocol on
         Nokia SROS series 9.0 systems."
    MODULE
        MANDATORY-GROUPS {
            tmnxIgmpGlobalGroup,
            tmnxIgmpNotificationV8v0Group,
            tmnxIgmpIfV5v0Group,
            tmnxIgmpIfV6v1Group,
            tmnxIgmpIfV7v0Group,
            tmnxIgmpIfV8v0Group,
            tmnxIgmpIfV9v0Group
        }
    ::= { tmnxIgmpCompliances 6 }

tmnxIgmpV10v0Compliance          MODULE-COMPLIANCE
    STATUS      obsolete
    DESCRIPTION
        "The compliance statement for management of extended IGMP protocol on
         Nokia SROS series 10.0 systems."
    MODULE
        MANDATORY-GROUPS {
            tmnxIgmpGlobalGroup,
            tmnxIgmpGlobalV10v0Group,
            tmnxIgmpIfV5v0Group,
            tmnxIgmpIfV6v1Group,
            tmnxIgmpIfV7v0Group,
            tmnxIgmpIfV8v0Group,
            tmnxIgmpIfV9v0Group,
            tmnxIgmpIfV10v0Group,
            tmnxIgmpNotificationV10v0Group
        }
    ::= { tmnxIgmpCompliances 7 }

tmnxIgmpV11v0Compliance          MODULE-COMPLIANCE
    STATUS      obsolete
    DESCRIPTION
        "The compliance statement for management of extended IGMP protocol on
         Nokia SROS series 11.0 systems."
    MODULE
        MANDATORY-GROUPS {
            tmnxIgmpGlobalGroup,
            tmnxIgmpGlobalV10v0Group,
            tmnxIgmpIfV5v0Group,
            tmnxIgmpIfV6v1Group,
            tmnxIgmpIfV7v0Group,
            tmnxIgmpIfV8v0Group,
            tmnxIgmpIfV9v0Group,
            tmnxIgmpIfV10v0Group,
            tmnxIgmpIfV11v0Group,
            tmnxIgmpNotificationV11v0Group
        }
    ::= { tmnxIgmpCompliances 8 }

tmnxIgmpV12v0Compliance          MODULE-COMPLIANCE
    STATUS      obsolete
    DESCRIPTION
        "The compliance statement for management of extended IGMP protocol on
         Nokia SROS series 12.0 systems."
    MODULE
        MANDATORY-GROUPS {
            tmnxIgmpGlobalGroup,
            tmnxIgmpGlobalV10v0Group,
            tmnxIgmpIfV5v0Group,
            tmnxIgmpIfV6v1Group,
            tmnxIgmpIfV7v0Group,
            tmnxIgmpIfV8v0Group,
            tmnxIgmpIfV9v0Group,
            tmnxIgmpIfV10v0Group,
            tmnxIgmpIfV11v0Group,
            tmnxIgmpIfV12v0Group,
            tmnxIgmpNotificationV11v0Group
        }
    ::= { tmnxIgmpCompliances 9 }

tmnxIgmpV14v0Compliance          MODULE-COMPLIANCE
    STATUS      current
    DESCRIPTION
        "The compliance statement for management of extended IGMP protocol on
         Nokia SROS series 14.0 systems."
    MODULE
        MANDATORY-GROUPS {
            tmnxIgmpGlobalGroup,
            tmnxIgmpGlobalV10v0Group,
            tmnxIgmpIfV5v0Group,
            tmnxIgmpIfV6v1Group,
            tmnxIgmpIfV7v0Group,
            tmnxIgmpIfV8v0Group,
            tmnxIgmpIfV9v0Group,
            tmnxIgmpIfV10v0Group,
            tmnxIgmpIfV11v0Group,
            tmnxIgmpIfV12v0Group,
            tmnxIgmpIfV14v0Group,
            tmnxIgmpNotificationV11v0Group,
            tmnxIgmpNotificationV14v0Group
        }
    ::= { tmnxIgmpCompliances 10 }

tmnxIgmpV15v0Compliance          MODULE-COMPLIANCE
    STATUS      current
    DESCRIPTION
        "The compliance statement for management of extended IGMP protocol on
         Nokia SROS series 15.0 systems."
    MODULE
        MANDATORY-GROUPS {
            tmnxIgmpIfV15v0Group
        }
    ::= { tmnxIgmpCompliances 11 }

tmnxIgmpGroups                   OBJECT IDENTIFIER ::= { tmnxIgmpConformance 2 }

tmnxIgmpGlobalGroup              OBJECT-GROUP
    OBJECTS     {
        vRtrIgmpGenQueryInterval,
        vRtrIgmpGenLastMembQueryIntvl,
        vRtrIgmpGenQueryResponseIntvl,
        vRtrIgmpGenRobustCount,
        vRtrIgmpGenLastChange,
        vRtrIgmpGenAdminState,
        vRtrIgmpGenOperState,
        vRtrIgmpGrpSrcFwdOrBlk,
        vRtrIgmpGrpSrcUpTime,
        vRtrIgmpSSMTranslateRowStatus,
        vRtrIgmpGenStatsStarGTypes,
        vRtrIgmpGenStatsSGTypes
    }
    STATUS      current
    DESCRIPTION
        "The group of objects supporting management of extended IGMP general
         capabilities on Nokia SROS series systems."
    ::= { tmnxIgmpGroups 1 }

tmnxIgmpNotifyObjsGroup          OBJECT-GROUP
    OBJECTS     {
        vRtrIgmpNotifyQueryVersion
    }
    STATUS      obsolete
    DESCRIPTION
        "The group of objects supporting IGMP notifications on Nokia SROS
         series systems."
    ::= { tmnxIgmpGroups 3 }

tmnxIgmpNotificationGroup        NOTIFICATION-GROUP
    NOTIFICATIONS {
        vRtrIgmpIfRxQueryVerMismatch,
        vRtrIgmpIfCModeRxQueryMismatch,
        vRtrIgmpMaxGrpsLimitExceeded
    }
    STATUS      obsolete
    DESCRIPTION
        "The group of notifications supporting the IGMP feature on Nokia SROS
         series systems."
    ::= { tmnxIgmpGroups 4 }

tmnxIgmpIfV4v0Group              OBJECT-GROUP
    OBJECTS     {
        vRtrIgmpIfRowStatus,
        vRtrIgmpIfLastChangeTime,
        vRtrIgmpIfAdminState,
        vRtrIgmpIfOperState,
        vRtrIgmpIfAdminVersion,
        vRtrIgmpIfOperVersion,
        vRtrIgmpIfQuerier,
        vRtrIgmpIfImportPolicy,
        vRtrIgmpIfGroupCount,
        vRtrIgmpIfQuerierUpTime,
        vRtrIgmpIfQuerierExpiryTime,
        vRtrIgmpIfNextGenQueryTime,
        vRtrIgmpIfSubnetCheck,
        vRtrIgmpIfGroupType,
        vRtrIgmpIfGroupUpTime,
        vRtrIgmpIfGroupExpiryTime,
        vRtrIgmpIfGroupVersion1HostTimer,
        vRtrIgmpIfGroupMode,
        vRtrIgmpIfGroupCompatMode,
        vRtrIgmpIfGroupVersion2HostTimer,
        vRtrIgmpIfGroupLastReporter,
        vRtrIgmpIfGrpSrcExpiryTime,
        vRtrIgmpIfGrpSrcType,
        vRtrIgmpIfStaticGrpSrcRowStatus,
        vRtrIgmpIfTxGenQueries,
        vRtrIgmpIfTxGrpQueries,
        vRtrIgmpIfTxGrpSrcQueries,
        vRtrIgmpIfTxV1Reports,
        vRtrIgmpIfTxV2Reports,
        vRtrIgmpIfTxV3Reports,
        vRtrIgmpIfTxLeaves,
        vRtrIgmpIfTxErrors,
        vRtrIgmpIfRxGenQueries,
        vRtrIgmpIfRxGrpQueries,
        vRtrIgmpIfRxGrpSrcQueries,
        vRtrIgmpIfRxV1Reports,
        vRtrIgmpIfRxV2Reports,
        vRtrIgmpIfRxV3Reports,
        vRtrIgmpIfRxLeaves,
        vRtrIgmpIfRxBadLenPkts,
        vRtrIgmpIfRxBadChecksumPkts,
        vRtrIgmpIfRxUnknownTypePkts,
        vRtrIgmpIfRxBadReceiveIfPkts,
        vRtrIgmpIfRxNonLocal,
        vRtrIgmpIfRxWrongVersions,
        vRtrIgmpIfImportPolicyDrops,
        vRtrIgmpIfRxNoRtrAlertPkts,
        vRtrIgmpIfRxBadEncodings,
        vRtrIgmpIfRxPktDrops,
        vRtrIgmpIfStatsStarGTypes,
        vRtrIgmpIfStatsSGTypes,
        vRtrIgmpIfMaxGroups,
        vRtrIgmpIfMaxGroupsTillNow
    }
    STATUS      obsolete
    DESCRIPTION
        "The group of objects supporting management of extended IGMP interfaces
         on Nokia SROS series systems."
    ::= { tmnxIgmpGroups 5 }

tmnxIgmpIfV5v0Group              OBJECT-GROUP
    OBJECTS     {
        vRtrIgmpIfRowStatus,
        vRtrIgmpIfLastChangeTime,
        vRtrIgmpIfAdminState,
        vRtrIgmpIfOperState,
        vRtrIgmpIfAdminVersion,
        vRtrIgmpIfOperVersion,
        vRtrIgmpIfQuerier,
        vRtrIgmpIfImportPolicy,
        vRtrIgmpIfGroupCount,
        vRtrIgmpIfQuerierUpTime,
        vRtrIgmpIfQuerierExpiryTime,
        vRtrIgmpIfNextGenQueryTime,
        vRtrIgmpIfSubnetCheck,
        vRtrIgmpIfGroupType,
        vRtrIgmpIfGroupUpTime,
        vRtrIgmpIfGroupExpiryTime,
        vRtrIgmpIfGroupVersion1HostTimer,
        vRtrIgmpIfGroupMode,
        vRtrIgmpIfGroupCompatMode,
        vRtrIgmpIfGroupVersion2HostTimer,
        vRtrIgmpIfGroupLastReporter,
        vRtrIgmpIfGrpSrcExpiryTime,
        vRtrIgmpIfGrpSrcType,
        vRtrIgmpIfStaticGrpSrcRowStatus,
        vRtrIgmpIfTxGenQueries,
        vRtrIgmpIfTxGrpQueries,
        vRtrIgmpIfTxGrpSrcQueries,
        vRtrIgmpIfTxV1Reports,
        vRtrIgmpIfTxV2Reports,
        vRtrIgmpIfTxV3Reports,
        vRtrIgmpIfTxLeaves,
        vRtrIgmpIfTxErrors,
        vRtrIgmpIfRxGenQueries,
        vRtrIgmpIfRxGrpQueries,
        vRtrIgmpIfRxGrpSrcQueries,
        vRtrIgmpIfRxV1Reports,
        vRtrIgmpIfRxV2Reports,
        vRtrIgmpIfRxV3Reports,
        vRtrIgmpIfRxLeaves,
        vRtrIgmpIfRxBadLenPkts,
        vRtrIgmpIfRxBadChecksumPkts,
        vRtrIgmpIfRxUnknownTypePkts,
        vRtrIgmpIfRxBadReceiveIfPkts,
        vRtrIgmpIfRxNonLocal,
        vRtrIgmpIfRxWrongVersions,
        vRtrIgmpIfImportPolicyDrops,
        vRtrIgmpIfRxNoRtrAlertPkts,
        vRtrIgmpIfRxBadEncodings,
        vRtrIgmpIfRxPktDrops,
        vRtrIgmpIfStatsStarGTypes,
        vRtrIgmpIfStatsSGTypes,
        vRtrIgmpIfMaxGroups,
        vRtrIgmpIfMaxGroupsTillNow,
        vRtrIgmpIfMcacPolicyName,
        vRtrIgmpIfMcacUnconstrainedBW,
        vRtrIgmpIfMcacConstAdminState,
        vRtrIgmpIfMcacLevelRowStatus,
        vRtrIgmpIfMcacLevelBW,
        vRtrIgmpIfMcacLagRowStatus,
        vRtrIgmpIfMcacLagLevel,
        vRtrIgmpIfStatsMcacPolicyDrops,
        vRtrIgmpIfRxLocalScopePkts,
        vRtrIgmpIfRxRsvdScopePkts,
        vRtrIgmpIfMcacPreRsvdMandBW,
        vRtrIgmpIfMcacinUseMandBw,
        vRtrIgmpIfMcacinUseOpnlBw,
        vRtrIgmpIfMcacAvailMandBw,
        vRtrIgmpIfMcacAvailOpnlBw,
        vRtrIgmpIfMcacValuesInTransit
    }
    STATUS      current
    DESCRIPTION
        "The group of objects supporting management of extended IGMP interfaces
         on Nokia SROS series systems."
    ::= { tmnxIgmpGroups 6 }

tmnxIgmpNotifyObjsV5v0Group      OBJECT-GROUP
    OBJECTS     {
        vRtrIgmpNotifyQueryVersion,
        vRtrIgmpNotifyGrpAddrType,
        vRtrIgmpNotifyGrpAddr
    }
    STATUS      obsolete
    DESCRIPTION
        "The group of objects supporting IGMP notifications on Nokia SROS
         series systems 5.0 release."
    ::= { tmnxIgmpGroups 7 }

tmnxIgmpNotificationV5v0Group    NOTIFICATION-GROUP
    NOTIFICATIONS {
        vRtrIgmpIfRxQueryVerMismatch,
        vRtrIgmpIfCModeRxQueryMismatch,
        vRtrIgmpMaxGrpsLimitExceeded,
        vRtrIgmpMcacPlcyDropped
    }
    STATUS      obsolete
    DESCRIPTION
        "The group of notifications supporting the IGMP feature on Nokia SROS
         series systems 5.0 release."
    ::= { tmnxIgmpGroups 8 }

tmnxIgmpIfV6v1Group              OBJECT-GROUP
    OBJECTS     {
        vRtrIgmpIfSSMTltTableLastChanged,
        vRtrIgmpIfSSMTransRowStatus
    }
    STATUS      current
    DESCRIPTION
        "The group of objects supporting management of SSM Translate feature on
         extended IGMP interfaces on 6.1 release Nokia SROS series systems."
    ::= { tmnxIgmpGroups 9 }

tmnxIgmpIfV7v0Group              OBJECT-GROUP
    OBJECTS     {
        vRtrIgmpRsvpIfRowStatus,
        vRtrIgmpRsvpIfIndex
    }
    STATUS      current
    DESCRIPTION
        "The group of objects supporting IGMP protocol tunnel interfaces on
         Nokia SROS series systems."
    ::= { tmnxIgmpGroups 10 }

tmnxIgmpIfV8v0Group              OBJECT-GROUP
    OBJECTS     {
        vRtrIgmpLdpIfTableLastChanged,
        vRtrIgmpRsvpIfBfdEnable,
        vRtrIgmpRsvpIfAdminState,
        vRtrIgmpRsvpIfOperState,
        vRtrIgmpLdpIfRowStatus,
        vRtrIgmpLdpIfLastChanged,
        vRtrIgmpLdpIfIndex,
        vRtrIgmpLdpIfAdminState,
        vRtrIgmpLdpIfOperState,
        vRtrIgmpHostLastChangeTime,
        vRtrIgmpHostOperState,
        vRtrIgmpHostOperVersion,
        vRtrIgmpHostGroupCount,
        vRtrIgmpHostNextGenQueryTime,
        vRtrIgmpHostMaxGroupsTillNow,
        vRtrIgmpHostFwdSvcId,
        vRtrIgmpHostGrpIfId,
        vRtrIgmpHostPppoeSessionId,
        vRtrIgmpHostSubscriberId,
        vRtrIgmpHostMacAddress,
        vRtrIgmpHostIgmpPolicy,
        vRtrIgmpHostMaxGroups,
        vRtrIgmpHostAdminVersion,
        vRtrIgmpHostTxGenQueries,
        vRtrIgmpHostTxGrpQueries,
        vRtrIgmpHostTxGrpSrcQueries,
        vRtrIgmpHostTxV1Reports,
        vRtrIgmpHostTxV2Reports,
        vRtrIgmpHostTxV3Reports,
        vRtrIgmpHostTxLeaves,
        vRtrIgmpHostTxErrors,
        vRtrIgmpHostRxGenQueries,
        vRtrIgmpHostRxGrpQueries,
        vRtrIgmpHostRxGrpSrcQueries,
        vRtrIgmpHostRxV1Reports,
        vRtrIgmpHostRxV2Reports,
        vRtrIgmpHostRxV3Reports,
        vRtrIgmpHostRxLeaves,
        vRtrIgmpHostRxBadLenPkts,
        vRtrIgmpHostRxBadChecksumPkts,
        vRtrIgmpHostRxUnknownTypePkts,
        vRtrIgmpHostRxBadReceiveIfPkts,
        vRtrIgmpHostRxNonLocal,
        vRtrIgmpHostRxWrongVersions,
        vRtrIgmpHostImportPolicyDrops,
        vRtrIgmpHostRxNoRtrAlertPkts,
        vRtrIgmpHostRxBadEncodings,
        vRtrIgmpHostRxPktDrops,
        vRtrIgmpHostStatsStarGTypes,
        vRtrIgmpHostStatsSGTypes,
        vRtrIgmpHostStatsMcacPolicyDrops,
        vRtrIgmpHostRxLocalScopePkts,
        vRtrIgmpHostRxRsvdScopePkts,
        vRtrIgmpHostRedirectionDrops,
        vRtrIgmpGrpIfRowStatus,
        vRtrIgmpGrpIfLastChangeTime,
        vRtrIgmpGrpIfAdminState,
        vRtrIgmpGrpIfOperState,
        vRtrIgmpGrpIfHostGrpType,
        vRtrIgmpGrpIfHostGrpUpTime,
        vRtrIgmpGrpIfHostGrpExpiryTime,
        vRtrIgmpGrpIfHostGrpVer1HostTmr,
        vRtrIgmpGrpIfHostGrpMode,
        vRtrIgmpGrpIfHostGrpCompatMode,
        vRtrIgmpGrpIfHostGrpVer2HostTmr,
        vRtrIgmpGrpIfHostGrpSrcExpTime,
        vRtrIgmpGrpIfHostGrpSrcType,
        vRtrIgmpGrpIfHostGrpSrcMRDstVrId,
        vRtrIgmpGrpIfHostGrpSrcMRDstIfId,
        vRtrIgmpGrpSrcHostUpTime,
        vRtrIgmpHostGrpSrcExpiryTime,
        vRtrIgmpHostGrpSrcType,
        vRtrIgmpHostGrpSrcMcRdrDstVRtrID,
        vRtrIgmpHostGrpSrcMcRdrDstIfIdx,
        vRtrIgmpHostGrpType,
        vRtrIgmpHostGrpUpTime,
        vRtrIgmpHostGrpExpiryTime,
        vRtrIgmpHostGrpVer1HostTmr,
        vRtrIgmpHostGrpMode,
        vRtrIgmpHostGrpCompatMode,
        vRtrIgmpHostGrpVer2HostTmr,
        vRtrIgmpGrpIfHostLastChangeTime,
        vRtrIgmpGrpIfHostOperState,
        vRtrIgmpIfDisRtrAlertChk
    }
    STATUS      current
    DESCRIPTION
        "The group of objects supporting IGMP protocol tunnel interfaces on
         Nokia SROS series systems 8.0 release."
    ::= { tmnxIgmpGroups 11 }

tmnxIgmpNotifyObjsV8v0Group      OBJECT-GROUP
    OBJECTS     {
        vRtrIgmpNotifyQueryVersion,
        vRtrIgmpNotifyGrpAddrType,
        vRtrIgmpNotifyGrpAddr,
        vRtrIgmpNotifyDescription,
        vRtrIgmpNotifyMcacPolicyName
    }
    STATUS      current
    DESCRIPTION
        "The group of objects supporting IGMP notifications on Nokia SROS
         series systems 5.0 release."
    ::= { tmnxIgmpGroups 12 }

tmnxIgmpNotificationV8v0Group    NOTIFICATION-GROUP
    NOTIFICATIONS {
        vRtrIgmpIfRxQueryVerMismatch,
        vRtrIgmpIfCModeRxQueryMismatch,
        vRtrIgmpMaxGrpsLimitExceeded,
        vRtrIgmpMcacPlcyDropped,
        vRtrIgmpHostInstantiationFail,
        vRtrIgmpHostMaxGrpsLimitExceeded,
        vRtrIgmpHostMcacPlcyDropped,
        vRtrIgmpHostCModeRxQueryMismatch,
        vRtrIgmpHostRxQueryVerMismatch
    }
    STATUS      obsolete
    DESCRIPTION
        "The group of notifications supporting the IGMP feature on Nokia SROS
         series systems 8.0 release."
    ::= { tmnxIgmpGroups 13 }

tmnxIgmpIfV9v0Group              OBJECT-GROUP
    OBJECTS     {
        vRtrIgmpGrpIfSubHostsOnly,
        vRtrIgmpGrpIfAdminVersion,
        vRtrIgmpGrpIfImportPolicy,
        vRtrIgmpGrpIfSubnetCheck,
        vRtrIgmpGrpIfMcacPolicyName,
        vRtrIgmpGrpIfMcacUnconstrainedBW,
        vRtrIgmpGrpIfMcacConstAdminState,
        vRtrIgmpGrpIfMcacPreRsvdMandBW,
        vRtrIgmpGrpIfMcacinUseMandBw,
        vRtrIgmpGrpIfMcacinUseOpnlBw,
        vRtrIgmpGrpIfMcacAvailMandBw,
        vRtrIgmpGrpIfMcacAvailOpnlBw,
        vRtrIgmpGrpIfMcacValuesInTransit,
        vRtrIgmpGrpIfDisRtrAlertChk,
        vRtrIgmpGrpIfMaxGroups,
        vRtrIgmpGrpIfSapLastChangeTime,
        vRtrIgmpGrpIfSapOperState,
        vRtrIgmpGrpIfSapAdminVersion,
        vRtrIgmpGrpIfSapOperVersion,
        vRtrIgmpGrpIfSapGroupCount,
        vRtrIgmpGrpIfSapNextGenQueryTime,
        vRtrIgmpGrpIfSapMaxGroups,
        vRtrIgmpGrpIfSapMaxGroupsTillNow,
        vRtrIgmpGrpIfSapTxGenQueries,
        vRtrIgmpGrpIfSapTxGrpQueries,
        vRtrIgmpGrpIfSapTxGrpSrcQueries,
        vRtrIgmpGrpIfSapTxV1Reports,
        vRtrIgmpGrpIfSapTxV2Reports,
        vRtrIgmpGrpIfSapTxV3Reports,
        vRtrIgmpGrpIfSapTxLeaves,
        vRtrIgmpGrpIfSapTxErrors,
        vRtrIgmpGrpIfSapRxGenQueries,
        vRtrIgmpGrpIfSapRxGrpQueries,
        vRtrIgmpGrpIfSapRxGrpSrcQueries,
        vRtrIgmpGrpIfSapRxV1Reports,
        vRtrIgmpGrpIfSapRxV2Reports,
        vRtrIgmpGrpIfSapRxV3Reports,
        vRtrIgmpGrpIfSapRxLeaves,
        vRtrIgmpGrpIfSapRxBadLenPkts,
        vRtrIgmpGrpIfSapRxBadChksumPkts,
        vRtrIgmpGrpIfSapRxUnknTypePkts,
        vRtrIgmpGrpIfSapRxBadRecvIfPkts,
        vRtrIgmpGrpIfSapRxNonLocal,
        vRtrIgmpGrpIfSapRxWrongVersions,
        vRtrIgmpGrpIfSapImportPlcyDrops,
        vRtrIgmpGrpIfSapRxNoRtrAlertPkts,
        vRtrIgmpGrpIfSapRxBadEncodings,
        vRtrIgmpGrpIfSapRxPktDrops,
        vRtrIgmpGrpIfSapStatsStarGTypes,
        vRtrIgmpGrpIfSapStatsSGTypes,
        vRtrIgmpGrpIfSapStatsMcacPlcyDrp,
        vRtrIgmpGrpIfSapRxLocalScopePkts,
        vRtrIgmpGrpIfSapRxRsvdScopePkts,
        vRtrIgmpGrpIfSapGrpType,
        vRtrIgmpGrpIfSapGrpUpTime,
        vRtrIgmpGrpIfSapGrpExpiryTime,
        vRtrIgmpGrpIfSapGrpVer1HostTmr,
        vRtrIgmpGrpIfSapGrpMode,
        vRtrIgmpGrpIfSapGrpCompatMode,
        vRtrIgmpGrpIfSapGrpVer2HostTmr,
        vRtrIgmpGrpIfSapGrpSrcExpTime,
        vRtrIgmpGrpIfSapGrpSrcType,
        vRtrIgmpGrpSrcGrpIfSapUpTime,
        vRtrIgmpHostMcRDstStatVal,
        vRtrIgmpGrpIfHostGrpMRDstVrId,
        vRtrIgmpGrpIfHostGrpMRDstIfId,
        vRtrIgmpHostGrpMcRdrDstVrId,
        vRtrIgmpHostGrpMcRdrDstIfId,
        vRtrIgmpGrpSrcSummFwdInterfaces,
        vRtrIgmpGrpSrcSummBlkInterfaces,
        vRtrIgmpGrpSrcSummFwdHosts,
        vRtrIgmpGrpSrcSummBlkHosts,
        vRtrIgmpGrpSrcSummFwdGrpIfSaps,
        vRtrIgmpGrpSrcSummBlkGrpIfSaps
    }
    STATUS      current
    DESCRIPTION
        "The group of objects supporting IGMP protocol tunnel interfaces on
         Nokia SROS series systems 9.0 release."
    ::= { tmnxIgmpGroups 14 }

tmnxIgmpIfV10v0Group             OBJECT-GROUP
    OBJECTS     {
        vRtrIgmpIfMaxSources,
        vRtrIgmpGrpIfMaxSources,
        vRtrIgmpHostMaxSources,
        vRtrIgmpGrpIfSapMaxSources,
        vRtrIgmpGrpIfQuerySrcIp
    }
    STATUS      current
    DESCRIPTION
        "The group of objects supporting IGMP protocol tunnel interfaces on
         Nokia SROS series systems 10.0 release."
    ::= { tmnxIgmpGroups 15 }

tmnxIgmpNotificationV10v0Group   NOTIFICATION-GROUP
    NOTIFICATIONS {
        vRtrIgmpIfRxQueryVerMismatch,
        vRtrIgmpIfCModeRxQueryMismatch,
        vRtrIgmpMaxGrpsLimitExceeded,
        vRtrIgmpMcacPlcyDropped,
        vRtrIgmpHostInstantiationFail,
        vRtrIgmpHostMaxGrpsLimitExceeded,
        vRtrIgmpHostMcacPlcyDropped,
        vRtrIgmpHostCModeRxQueryMismatch,
        vRtrIgmpHostRxQueryVerMismatch,
        vRtrIgmpHostMaxSrcsLimitExceeded,
        vRtrIgmpMaxSrcsLimitExceeded,
        vRtrIgmpGrpIfSapMaxGrpsLimExceed,
        vRtrIgmpGrpIfSapMaxSrcsLimExceed,
        vRtrIgmpGrpIfSapMcacPlcyDropped,
        vRtrIgmpGrpIfSapCModeRxQueryMism,
        vRtrIgmpGrpIfSapRxQueryVerMism
    }
    STATUS      obsolete
    DESCRIPTION
        "The group of notifications supporting the IGMP feature on Nokia SROS
         series systems 10.0 release."
    ::= { tmnxIgmpGroups 16 }

tmnxIgmpGlobalV10v0Group         OBJECT-GROUP
    OBJECTS     {
        vRtrIgmpGenGrpIfQuerySrcIp
    }
    STATUS      current
    DESCRIPTION
        "The group of objects supporting management of extended IGMP general
         capabilities on Nokia SROS series systems 10.0 releaae."
    ::= { tmnxIgmpGroups 17 }

tmnxIgmpIfV11v0Group             OBJECT-GROUP
    OBJECTS     {
        vRtrIgmpIfMaxGrpSources,
        vRtrIgmpGrpIfMaxGrpSources,
        vRtrIgmpHostMaxGrpSources,
        vRtrIgmpGrpIfSapMaxGrpSources
    }
    STATUS      current
    DESCRIPTION
        "The group of objects supporting IGMP protocol tunnel interfaces on
         Nokia SROS series systems 11.0 release."
    ::= { tmnxIgmpGroups 18 }

tmnxIgmpNotificationV11v0Group   NOTIFICATION-GROUP
    NOTIFICATIONS {
        vRtrIgmpIfRxQueryVerMismatch,
        vRtrIgmpIfCModeRxQueryMismatch,
        vRtrIgmpMaxGrpsLimitExceeded,
        vRtrIgmpMcacPlcyDropped,
        vRtrIgmpHostInstantiationFail,
        vRtrIgmpHostMaxGrpsLimitExceeded,
        vRtrIgmpHostMcacPlcyDropped,
        vRtrIgmpHostCModeRxQueryMismatch,
        vRtrIgmpHostRxQueryVerMismatch,
        vRtrIgmpHostMaxSrcsLimitExceeded,
        vRtrIgmpMaxSrcsLimitExceeded,
        vRtrIgmpGrpIfSapMaxGrpsLimExceed,
        vRtrIgmpGrpIfSapMaxSrcsLimExceed,
        vRtrIgmpGrpIfSapMcacPlcyDropped,
        vRtrIgmpGrpIfSapCModeRxQueryMism,
        vRtrIgmpGrpIfSapRxQueryVerMism,
        vRtrIgmpHostMaxGrpSrcsLimitExcd,
        vRtrIgmpMaxGrpSrcsLimitExceeded,
        vRtrIgmpGrpIfSapMaxGrpSrcLimExcd
    }
    STATUS      current
    DESCRIPTION
        "The group of notifications supporting the IGMP feature on Nokia SROS
         series systems 11.0 release."
    ::= { tmnxIgmpGroups 19 }

tmnxIgmpIfV12v0Group             OBJECT-GROUP
    OBJECTS     {
        vRtrIgmpIfQueryInterval,
        vRtrIgmpIfLastMembQueryIntvl,
        vRtrIgmpIfQueryResponseIntvl,
        vRtrIgmpIfMcacUseLagPortWeight,
        vRtrIgmpIfRedundantMcast,
        vRtrIgmpIfRedundantMcastFwding
    }
    STATUS      current
    DESCRIPTION
        "The group of objects supporting IGMP protocol tunnel interfaces on
         Nokia SROS series systems 12.0 release."
    ::= { tmnxIgmpGroups 20 }

tmnxIgmpNotifyObjsV12v0Group     OBJECT-GROUP
    OBJECTS     {
        vRtrIgmpNotifySrcAddrType,
        vRtrIgmpNotifySrcAddr
    }
    STATUS      current
    DESCRIPTION
        "The group of objects supporting IGMP notifications on Nokia SROS
         series systems 12.0 release."
    ::= { tmnxIgmpGroups 21 }

tmnxIgmpIfV14v0Group             OBJECT-GROUP
    OBJECTS     {
        vRtrIgmpIfMcacIfPolicyName,
        vRtrIgmpGrpIfMcacIfPolicyName,
        vRtrIgmpIfSGrpRangeSrcTblLstChgd,
        vRtrIgmpIfSGrpRangeSrcRowStatus,
        vRtrIgmpIfSGrpRangeLastChanged,
        vRtrIgmpIfSGrpRangeGrpCount,
        vRtrIgmpGrpIfQueryInterval,
        vRtrIgmpGrpIfLastMembQueryIntvl,
        vRtrIgmpGrpIfQueryResponseIntvl,
        vRtrIgmpHostQueryInterval,
        vRtrIgmpHostLastMembQueryIntvl,
        vRtrIgmpHostQueryResponseIntvl,
        vRtrIgmpHostDisRtrAlertChk,
        vRtrIgmpGrpIfSapQryInterval,
        vRtrIgmpGrpIfSapLastMembQryIntvl,
        vRtrIgmpGrpIfSapQryResponseIntvl
    }
    STATUS      current
    DESCRIPTION
        "The group of objects supporting IGMP protocol tunnel interfaces on
         Nokia SROS series systems 14.0 release."
    ::= { tmnxIgmpGroups 22 }

tmnxIgmpNotificationV14v0Group   NOTIFICATION-GROUP
    NOTIFICATIONS {
        vRtrIgmpHostQryIntervalConflict
    }
    STATUS      current
    DESCRIPTION
        "The group of notifications supporting the IGMP feature on Nokia SROS
         series systems 14.0 release."
    ::= { tmnxIgmpGroups 23 }

tmnxIgmpIfV15v0Group             OBJECT-GROUP
    OBJECTS     {
        vRtrIgmpHostBondingConnIndex,
        vRtrIgmpHostBondingId,
        vRtrIgmpGrpIfHostGrpBondOwner,
        vRtrIgmpGrpIfHostGrpBondFwd,
        vRtrIgmpGrpIfHostGrpSrcBondOwner,
        vRtrIgmpGrpIfHostGrpSrcBondFwd,
        vRtrIgmpHostGrpBondOwner,
        vRtrIgmpHostGrpBondFwd,
        vRtrIgmpHostGrpSrcBondOwner,
        vRtrIgmpHostGrpSrcBondFwd
    }
    STATUS      current
    DESCRIPTION
        "The group of objects supporting IGMP protocol tunnel interfaces on
         Nokia SROS series systems 15.0 release."
    ::= { tmnxIgmpGroups 24 }

vRtrIgmpNotifyPrefix             OBJECT IDENTIFIER ::= { tmnxSRNotifyPrefix 23 }

vRtrIgmpNotifications            OBJECT IDENTIFIER ::= { vRtrIgmpNotifyPrefix 0 }

vRtrIgmpIfRxQueryVerMismatch     NOTIFICATION-TYPE
    OBJECTS     {
        vRtrID,
        vRtrIfIndex,
        vRtrIgmpIfAdminVersion,
        vRtrIgmpNotifyQueryVersion
    }
    STATUS      current
    DESCRIPTION
        "A vRtrIgmpIfRxQueryVerMismatch notification is generated when the IGMP
         interface is configured as IGMPv3 but the router receives a IGMPv1
         Query or IGMPv2 General Query on the interface.

         vRtrIfIndex will identify the router interface on which the query is
         received. vRtrIgmpIfAdminVersion will contain the configured version
         of the interface and vRtrIgmpNotifyQueryVersion will contain the
         version of the received query."
    ::= { vRtrIgmpNotifications 1 }

vRtrIgmpIfCModeRxQueryMismatch   NOTIFICATION-TYPE
    OBJECTS     {
        vRtrID,
        vRtrIfIndex,
        vRtrIgmpIfOperVersion,
        vRtrIgmpNotifyQueryVersion
    }
    STATUS      current
    DESCRIPTION
        "A vRtrIgmpIfCModeRxQueryMismatch notification is generated when there
         is a mismatch between the compatible mode of the interface and the
         version of the received query.

         It is generated when the IGMP interface is in IGMPv1 compatible mode
         but it receives a IGMPv2 or IGMPv3 Query on the interface. It is also
         generated when the compatibility mode of the interface is IGMPv2 but
         the query received is IGMPv3.

         vRtrIfIndex will identify the router interface on which the query is
         received. vRtrIgmpIfOperVersion will indicate the compatibility mode
         of the interface and vRtrIgmpNotifyQueryVersion will contain the
         version of the received query."
    ::= { vRtrIgmpNotifications 2 }

vRtrIgmpMaxGrpsLimitExceeded     NOTIFICATION-TYPE
    OBJECTS     {
        vRtrIgmpIfMaxGroups
    }
    STATUS      current
    DESCRIPTION
        "The vRtrIgmpMaxGrpsLimitExceeded event is generated when an attempt is
         made to configure a group when vRtrIgmpIfGroupCount, the number of
         groups configured on the PIM interface, is equal to
         vRtrIgmpIfMaxGroups, the maximum number of groups supported on the
         interface."
    ::= { vRtrIgmpNotifications 3 }

vRtrIgmpMcacPlcyDropped          NOTIFICATION-TYPE
    OBJECTS     {
        vRtrIgmpIfMcacPolicyName,
        vRtrIgmpNotifyGrpAddrType,
        vRtrIgmpNotifyGrpAddr,
        vRtrIgmpNotifySrcAddrType,
        vRtrIgmpNotifySrcAddr,
        vRtrIgmpNotifyDescription
    }
    STATUS      current
    DESCRIPTION
        "The vRtrIgmpMcacPlcyDropped event is generated when an IGMP group is
         dropped on a given interface because of applying a multicast CAC
         policy given by vRtrIgmpIfMcacPolicyName."
    ::= { vRtrIgmpNotifications 4 }

vRtrIgmpHostInstantiationFail    NOTIFICATION-TYPE
    OBJECTS     {
        vRtrIgmpGrpIfHostLastChangeTime,
        vRtrIgmpNotifyDescription
    }
    STATUS      current
    DESCRIPTION
        "The vRtrIgmpHostInstantiationFail event is generated when a host is
         eligible for running IGMP, but IGMP cannot be started on the host."
    ::= { vRtrIgmpNotifications 5 }

vRtrIgmpHostMaxGrpsLimitExceeded NOTIFICATION-TYPE
    OBJECTS     {
        vRtrIgmpHostFwdSvcId,
        vRtrIgmpHostGrpIfId,
        vRtrIgmpHostMaxGroups
    }
    STATUS      current
    DESCRIPTION
        "The vRtrIgmpMaxGrpsLimitExceeded event is generated when an attempt is
         made to configure a group when vRtrIgmpHostGroupCount, the number of
         groups configured on the PIM interface, is equal to
         vRtrIgmpHostMaxGroups, the maximum number of groups supported on the
         host."
    ::= { vRtrIgmpNotifications 6 }

vRtrIgmpHostMcacPlcyDropped      NOTIFICATION-TYPE
    OBJECTS     {
        vRtrIgmpHostSubscriberId,
        vRtrIgmpNotifyMcacPolicyName,
        vRtrIgmpNotifyGrpAddrType,
        vRtrIgmpNotifyGrpAddr,
        vRtrIgmpNotifySrcAddrType,
        vRtrIgmpNotifySrcAddr,
        vRtrIgmpNotifyDescription
    }
    STATUS      current
    DESCRIPTION
        "The vRtrIgmpHostMcacPlcyDropped event is generated when an IGMP group
         is dropped on a given Host because of applying a multicast CAC policy
         given by vRtrIgmpNotifyMcacPolicyName."
    ::= { vRtrIgmpNotifications 7 }

vRtrIgmpHostCModeRxQueryMismatch NOTIFICATION-TYPE
    OBJECTS     {
        vRtrIgmpHostOperVersion,
        vRtrIgmpNotifyQueryVersion
    }
    STATUS      current
    DESCRIPTION
        "A vRtrIgmpHostCModeRxQueryMismatch notification is generated when
         there is a mismatch between the compatible mode of the IGMP Host and
         the version of the received query.

         It is generated when the Host is in IGMPv1 compatible mode but it
         receives a IGMPv2 or IGMPv3 Query. It is also generated when the
         compatibility mode of the Host is IGMPv2 but the query received is
         IGMPv3.

         vRtrIgmpHostAddress will identify the Host on which the query is
         received. vRtrIgmpHostOperVersion will indicate the compatibility mode
         of the Host and vRtrIgmpNotifyQueryVersion will contain the version of
         the received query."
    ::= { vRtrIgmpNotifications 8 }

vRtrIgmpHostRxQueryVerMismatch   NOTIFICATION-TYPE
    OBJECTS     {
        vRtrIgmpHostAdminVersion,
        vRtrIgmpNotifyQueryVersion
    }
    STATUS      current
    DESCRIPTION
        "A vRtrIgmpHostRxQueryVerMismatch notification is generated when the
         IGMP host is configured as IGMPv3 but receives a IGMPv1 Query or
         IGMPv2 General Query on the host.

         vRtrIgmpHostAddress will identify the Host on which the query is
         received. vRtrIgmpHostAdminVersion will contain the configured version
         of the Host and vRtrIgmpNotifyQueryVersion will contain the version of
         the received query."
    ::= { vRtrIgmpNotifications 9 }

vRtrIgmpHostMaxSrcsLimitExceeded NOTIFICATION-TYPE
    OBJECTS     {
        vRtrIgmpHostFwdSvcId,
        vRtrIgmpHostGrpIfId,
        vRtrIgmpHostMaxSources
    }
    STATUS      current
    DESCRIPTION
        "The vRtrIgmpHostMaxSrcsLimitExceeded event is generated when an
         attempt is made to configure a source for a group when the number of
         sources for this group is equal to vRtrIgmpHostMaxSources, the maximum
         number of sources per group supported on the host."
    ::= { vRtrIgmpNotifications 10 }

vRtrIgmpMaxSrcsLimitExceeded     NOTIFICATION-TYPE
    OBJECTS     {
        vRtrIgmpIfMaxSources
    }
    STATUS      current
    DESCRIPTION
        "The vRtrIgmpMaxSrcsLimitExceeded event is generated when an attempt is
         made to configure a source for a group when the number of sources for
         this group is equal to vRtrIgmpIfMaxSources, the maximum number of
         sources per group supported on the interface."
    ::= { vRtrIgmpNotifications 11 }

vRtrIgmpGrpIfSapMaxGrpsLimExceed NOTIFICATION-TYPE
    OBJECTS     {
        vRtrIgmpGrpIfSapMaxGroups
    }
    STATUS      current
    DESCRIPTION
        "The vRtrIgmpGrpIfSapMaxGrpsLimExceed event is generated when an
         attempt is made to configure a group when vRtrIgmpGrpIfSapGroupCount,
         the number of groups configured on the SAP, is equal to
         vRtrIgmpGrpIfSapMaxGroups, the maximum number of groups supported on
         the SAP."
    ::= { vRtrIgmpNotifications 12 }

vRtrIgmpGrpIfSapMaxSrcsLimExceed NOTIFICATION-TYPE
    OBJECTS     {
        vRtrIgmpGrpIfSapMaxSources
    }
    STATUS      current
    DESCRIPTION
        "The vRtrIgmpGrpIfSapMaxSrcsLimExceed event is generated when an
         attempt is made to configure a source for a group when the number of
         sources for this group is equal to vRtrIgmpGrpIfSapMaxSources, the
         maximum number of sources per group supported on the SAP."
    ::= { vRtrIgmpNotifications 13 }

vRtrIgmpGrpIfSapMcacPlcyDropped  NOTIFICATION-TYPE
    OBJECTS     {
        vRtrIgmpGrpIfSapLastChangeTime,
        vRtrIgmpNotifyMcacPolicyName,
        vRtrIgmpNotifyGrpAddrType,
        vRtrIgmpNotifyGrpAddr,
        vRtrIgmpNotifySrcAddrType,
        vRtrIgmpNotifySrcAddr,
        vRtrIgmpNotifyDescription
    }
    STATUS      current
    DESCRIPTION
        "The vRtrIgmpGrpIfSapMcacPlcyDropped event is generated when an IGMP
         group is dropped on a given SAP because of applying a multicast CAC
         policy given by vRtrIgmpNotifyMcacPolicyName."
    ::= { vRtrIgmpNotifications 14 }

vRtrIgmpGrpIfSapCModeRxQueryMism NOTIFICATION-TYPE
    OBJECTS     {
        vRtrIgmpGrpIfSapOperVersion,
        vRtrIgmpNotifyQueryVersion
    }
    STATUS      current
    DESCRIPTION
        "A vRtrIgmpGrpIfSapCModeRxQueryMism notification is generated when
         there is a mismatch between the compatible mode of the IGMP SAP and
         the version of the received query.

         It is generated when the SAP is in IGMPv1 compatible mode but it
         receives a IGMPv2 or IGMPv3 Query. It is also generated when the
         compatibility mode of the SAP is IGMPv2 but the query received is
         IGMPv3.

         sapPortId and sapEncapValue will identify the SAP on which the query
         is received. vRtrIgmpGrpIfSapOperVersion will indicate the
         compatibility mode of the SAP and vRtrIgmpNotifyQueryVersion will
         contain the version of the received query."
    ::= { vRtrIgmpNotifications 15 }

vRtrIgmpGrpIfSapRxQueryVerMism   NOTIFICATION-TYPE
    OBJECTS     {
        vRtrIgmpGrpIfSapAdminVersion,
        vRtrIgmpNotifyQueryVersion
    }
    STATUS      current
    DESCRIPTION
        "A vRtrIgmpGrpIfSapRxQueryVerMism notification is generated when the
         IGMP host SAP is configured as IGMPv3 but receives a IGMPv1 Query or
         IGMPv2 General Query on the host.

         sapPortId and sapEncapValue will identify the SAP on which the query
         is received. vRtrIgmpGrpIfSapAdminVersion will contain the configured
         version of the SAP and vRtrIgmpNotifyQueryVersion will contain the
         version of the received query."
    ::= { vRtrIgmpNotifications 16 }

vRtrIgmpHostMaxGrpSrcsLimitExcd  NOTIFICATION-TYPE
    OBJECTS     {
        vRtrIgmpHostFwdSvcId,
        vRtrIgmpHostGrpIfId,
        vRtrIgmpHostMaxGrpSources
    }
    STATUS      current
    DESCRIPTION
        "The vRtrIgmpHostMaxGrpSrcsLimitExcd event is generated when an attempt
         is made to configure a source for a group when the number of group
         sources is equal to vRtrIgmpHostMaxGrpSources, the maximum number of
         group sources per group supported on the host."
    ::= { vRtrIgmpNotifications 17 }

vRtrIgmpMaxGrpSrcsLimitExceeded  NOTIFICATION-TYPE
    OBJECTS     {
        vRtrIgmpIfMaxGrpSources
    }
    STATUS      current
    DESCRIPTION
        "The vRtrIgmpMaxGrpSrcsLimitExceeded event is generated when an attempt
         is made to configure a group source for a group when the number of
         group sources is equal to vRtrIgmpIfMaxGrpSources, the maximum number
         of group sources per group supported on the interface."
    ::= { vRtrIgmpNotifications 18 }

vRtrIgmpGrpIfSapMaxGrpSrcLimExcd NOTIFICATION-TYPE
    OBJECTS     {
        vRtrIgmpGrpIfSapMaxGrpSources
    }
    STATUS      current
    DESCRIPTION
        "The vRtrIgmpGrpIfSapMaxGrpSrcLimExcd event is generated when an
         attempt is made to configure a group source for a group when the
         number of group sources is equal to vRtrIgmpGrpIfSapMaxGrpSources, the
         maximum number of group sources per group supported on the SAP."
    ::= { vRtrIgmpNotifications 19 }

vRtrIgmpHostQryIntervalConflict  NOTIFICATION-TYPE
    OBJECTS     {
        vRtrIgmpHostFwdSvcId,
        vRtrIgmpHostGrpIfId,
        vRtrIgmpNotifyDescription
    }
    STATUS      current
    DESCRIPTION
        "The vRtrIgmpHostQryIntervalConflict event is generated when one of the
         IGMP-policy query intervals violates restrictions, we fall back to the
         node query intervals."
    ::= { vRtrIgmpNotifications 20 }

END
